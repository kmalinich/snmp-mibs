CTRON-ROUTERS-MIB DEFINITIONS ::= BEGIN

--  ctron-routers-mib.txt
--  Revision: 1.01.00
--  Part Number:  2170988
--  Date: June 5, 1995

--  Cabletron Systems, Inc.
--  35 Industrial Way, P.O. Box 5005
--  Rochester, NH 03867-0505
--  (603) 332-9400
--  support@ctron.com

--  This module provides authoritative definitions for Cabletron's
--  enterprise specific Routing Services MIB.  This MIB contains
--  objects which provide a high-level view of the routed and routing
--  protocols for the Cabletron Router.  Essentially, this MIB
--  allows for the dynamic "discovery" of routing services within
--  Cabletron devices.

--  This module will be extended, as needed.
--

--  Cabletron Systems reserves the right to make changes in
--  specifications and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.

--  Copyright August 92 Cabletron Systems



IMPORTS
        OBJECT-TYPE
                FROM RFC-1212
        DisplayString
                FROM RFC1213-MIB
        nwRouter, nwRtrMibs, nwRtrHighLevelView, nwRtrProtoSuites
                FROM ROUTER-OIDS
        Counter, TimeTicks
                FROM RFC1155-SMI;



nwRtrMibRevision                OBJECT IDENTIFIER ::= { nwRtrMibs 1 }
nwRtrStandardMibs               OBJECT IDENTIFIER ::= { nwRtrMibs 2 }

nwRtrApplicationView            OBJECT IDENTIFIER ::= { nwRtrHighLevelView 1 }
nwRtrRoutingView                OBJECT IDENTIFIER ::= { nwRtrHighLevelView 2 }
nwRtrComponentView              OBJECT IDENTIFIER ::= { nwRtrHighLevelView 3 }
nwRtrCountersView               OBJECT IDENTIFIER ::= { nwRtrHighLevelView 4 }

nwRtrApplicationSystem          OBJECT IDENTIFIER ::= { nwRtrApplicationView 1 }
nwRtrApplicationInterfaces      OBJECT IDENTIFIER ::= { nwRtrApplicationView 2 }

nwRtrRoutingSystem              OBJECT IDENTIFIER ::= { nwRtrRoutingView 1 }
nwRtrRoutingInterfaces          OBJECT IDENTIFIER ::= { nwRtrRoutingView 2 }

nwRtrComponentSystem            OBJECT IDENTIFIER ::= { nwRtrComponentView 1 }
nwRtrComponentInterfaces        OBJECT IDENTIFIER ::= { nwRtrComponentView 2 }

nwRtrCountersControl            OBJECT IDENTIFIER ::= { nwRtrCountersView 1 }
nwRtrInterfaceCounters          OBJECT IDENTIFIER ::= { nwRtrCountersView 2 }




--  The Router MIB Revision Group.
--  This group contains information about the revision level of this
--  MIB within the device.  It allows verification of the released
--  version without having to read other objects.


nwRtrMibRevText OBJECT-TYPE
        SYNTAX  DisplayString
        ACCESS  read-only
        STATUS  mandatory
        DESCRIPTION
                "Indicates the current revision level of the Cabletron Routing
                services High Level MIB in textual format. Read the value of
                this object to determine the revision of the CTRouter MIB
                operating on the routing services enabled device."
        ::= { nwRtrMibRevision 1 }


--  The Router Standard MIB Table.
--  This table contains a list of all the Standard MIBs instanciated
--  in the Cabletron Routing Services.

nwRtrStdMibTable  OBJECT-TYPE
        SYNTAX    SEQUENCE OF NwRtrStdMibEntry
        ACCESS    not-accessible
        STATUS    mandatory
        DESCRIPTION
                "This table includes entries for all of the Standard MIBs
                present within the routing services enabled device. Read the
                entries in this table to determine which standard MIBs are
                present. An entry exists for each standard MIB that is
                present. The index into this table is an arbitrary ordinal
                value."
        ::= { nwRtrStandardMibs 1 }

nwRtrStdMibEntry  OBJECT-TYPE
        SYNTAX    NwRtrStdMibEntry
        ACCESS    not-accessible
        STATUS    mandatory
        DESCRIPTION
                "Each entry identifies the starting OID for the standard MIB for which
                the entry exists."
        INDEX   { nwRtrStdMibIndex }
        ::= { nwRtrStdMibTable 1 }

NwRtrStdMibEntry ::=
        SEQUENCE {
                nwRtrStdMibIndex        INTEGER,
                nwRtrStdMibIdentifier   OBJECT IDENTIFIER
                }

nwRtrStdMibIndex  OBJECT-TYPE
        SYNTAX    INTEGER
        ACCESS    read-only
        STATUS    mandatory
        DESCRIPTION
                "This is the index into the Standard MIB index within the
                Standard MIB Table."
        ::= { nwRtrStdMibEntry 1 }

nwRtrStdMibIdentifier  OBJECT-TYPE
        SYNTAX         OBJECT IDENTIFIER
        ACCESS         read-only
        STATUS         mandatory
        DESCRIPTION
                "The OID that identifies the starting point of the standard MIB
                for which the entry exists."
        ::= { nwRtrStdMibEntry 2 }


--  The Router High-Level View Group.
--  This group provides a high-level Configuration Change Flag to indicate
--  whether further device interrogation is required and a version number
--  indicating the version of Cabletron Routing services.  This group also
--  provides tables to discover the routed protocols, routing protocols and
--  components which are dynamically instanciated at device power up.
--  These tables allow discovery of routing components on both the system and
--  the interface, or router port, level.

nwRtrAdminChanges       OBJECT-TYPE
        SYNTAX          Counter
        ACCESS          read-only
        STATUS          mandatory
        DESCRIPTION
                "Indicates the number of times, configuration changes have
                been made to the routing services recorded by this MIB. Each
                time a change is made this counter is increments by 1. Read
                the value of this entry to determine if any values in this
                MIB have changed."
        ::= { nwRtrApplicationSystem 1 }


--  The Router System Table.
--  This table shows all of the Routing Protocols that make up the  routing
--  services, and their respective configurations in the device. A high-level
--  view can be achieved without having to access each of the individual
--  router mibs.


nwRouterSystemTable   OBJECT-TYPE
        SYNTAX  SEQUENCE OF NwRouterEntry
        ACCESS  not-accessible
        STATUS  mandatory
        DESCRIPTION
                "This table contains an entry for each routing service present
                within the routing services enabled device."
        ::= { nwRtrApplicationSystem 2 }

nwRouterEntry   OBJECT-TYPE
        SYNTAX  NwRouterEntry
        ACCESS  not-accessible
        STATUS  mandatory
        DESCRIPTION
                "Each entry describes the routing service for which the entry
                exists."
        INDEX   { nwRouterInstance }
        ::= { nwRouterSystemTable 1 }

NwRouterEntry ::=
        SEQUENCE {
                nwRouterInstance        INTEGER,
                nwRouterAdminStatus     INTEGER,
                nwRouterOperStatus              INTEGER,
                nwRouterOperationalTime TimeTicks,
                nwRouterEntMibGroup     OBJECT IDENTIFIER,
        nwRouterName            DisplayString,
                nwRouterVersion         DisplayString,
                nwRouterIdentifier      OBJECT IDENTIFIER
                }

nwRouterInstance        OBJECT-TYPE
        SYNTAX  INTEGER
        ACCESS  read-only
        STATUS  mandatory
        DESCRIPTION
                "An ordinal value assigned to the routing service for which
                the entry exists."
        ::= { nwRouterEntry 1 }

nwRouterAdminStatus     OBJECT-TYPE
        SYNTAX  INTEGER {
                        other(1),             --  none of the following
                        disabled(2),          --  not running
                        enabled(3)            --  running
                }
        ACCESS  read-only
        STATUS  mandatory
        DESCRIPTION
                "Indicates the current administrative state of the routing
                service for which the entry exists."
        ::= { nwRouterEntry 2 }

nwRouterOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
                "Indicates the current operating condition  of the
                routing services for which the entry exists."
        ::= { nwRouterEntry 3 }

nwRouterOperationalTime  OBJECT-TYPE
        SYNTAX  TimeTicks
        ACCESS  read-only
        STATUS  mandatory
        DESCRIPTION
                "Indicates how long this Routing Service has been in its
                current administrative state for which the entry exists."
        ::= { nwRouterEntry 4 }

nwRouterEntMibGroup OBJECT-TYPE
        SYNTAX  OBJECT IDENTIFIER
        ACCESS  read-only
        STATUS  mandatory
        DESCRIPTION
                "Identifies the starting OID for the Cabletron Enterprise MIB
                that implements the managed objects for the routing service for
                which the entry exists."
        ::= { nwRouterEntry 5 }

nwRouterName OBJECT-TYPE
        SYNTAX  DisplayString
        ACCESS  read-only
        STATUS  mandatory
        DESCRIPTION
                "Indicates the name of the routing service in textual format
                for which the entry exists."
        ::= { nwRouterEntry 6 }

nwRouterVersion  OBJECT-TYPE
        SYNTAX  DisplayString
        ACCESS  read-only
        STATUS  mandatory
        DESCRIPTION
                "Indicates the current revision level of the routing service,
                in textual format for which the entry exists."
        ::= { nwRouterEntry 7 }

nwRouterIdentifier  OBJECT-TYPE
        SYNTAX  OBJECT IDENTIFIER
        ACCESS  read-only
        STATUS  mandatory
        DESCRIPTION
                "Identifies the OID in the Cabletron ctNetwork naming tree
                MIB used to uniquely identify the routing service for which the
                entry exists. Read the value indicated to obtain the name of the
                routing service for which this entry exists."
        ::= { nwRouterEntry 8 }

--
-- The Cabletron Routing Services version number is specified by CM.
--
nwRtrVersion    OBJECT-TYPE
        SYNTAX  DisplayString
        ACCESS  read-only
        STATUS  mandatory
        DESCRIPTION
                "Indicates the current revision level of Cabletron
                routing services in textual format."
        ::= { nwRtrApplicationSystem 3 }


--  The Router Interface Table.
--  This table shows all of the Routing Protocol suites that make up the
--  routing services that are on each router port.  This high-level view
--  can be acheived without having to access each of the individual router
--  MIB's.

nwRouterIfTable   OBJECT-TYPE
        SYNTAX  SEQUENCE OF NwRouterIfEntry
        ACCESS  not-accessible
        STATUS  mandatory
        DESCRIPTION
                "This table contains an entry for each routing service running
                on each router port. Essentially, this table gives a
                high-level view of the configuration and administrative state
                of each of the routing service running on each router port."
        ::= { nwRtrApplicationInterfaces 1 }

nwRouterIfEntry   OBJECT-TYPE
        SYNTAX  NwRouterIfEntry
        ACCESS  not-accessible
        STATUS  mandatory
        DESCRIPTION
                "Each entry describes the routing service operating on the
                router port for which the entry exists."
        INDEX   { nwRouterIfIndex, nwRouterIfInstance }
        ::= { nwRouterIfTable 1 }

NwRouterIfEntry ::=
        SEQUENCE {
                nwRouterIfIndex                 INTEGER,
                nwRouterIfInstance              INTEGER,
                nwRouterIfAdminStatus           INTEGER,
                                nwRouterIfOperStatus            INTEGER,
                                nwRouterIfOperationalTime   TimeTicks,
                nwRouterIfName                  DisplayString
                }

nwRouterIfIndex          OBJECT-TYPE
        SYNTAX  INTEGER
        ACCESS  read-only
        STATUS  mandatory
        DESCRIPTION
                "Indicates the value in MIB 2 ifIndex, which identifies the
                router port for which the entry exists."
        ::= { nwRouterIfEntry 1 }

nwRouterIfInstance        OBJECT-TYPE
        SYNTAX  INTEGER
        ACCESS  read-only
        STATUS  mandatory
        DESCRIPTION
                "Indicates the value of nwRouterInstance as established in
                nwRouterSystemTable. Essentially, indicating which routing
                service is running on the router port for which the entry
                exists. All router ports running the same routing service
                will have the same value for nwRouterIfInstance."
        ::= { nwRouterIfEntry 2 }

nwRouterIfAdminStatus     OBJECT-TYPE
        SYNTAX  INTEGER {
                        other(1),             --  none of the following
                        disabled(2),          --  not running
                        enabled(3)            --  running
                }
        ACCESS  read-only
        STATUS  mandatory
        DESCRIPTION
                "Indicates the current administrative state of the routing
                service on the router port for which the entry exists."
        ::= { nwRouterIfEntry 3 }

nwRouterIfOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
              "Indicates the current operating condition of the routing
               service on the router port for which the entry exists."
        ::= { nwRouterIfEntry 4 }

nwRouterIfOperationalTime  OBJECT-TYPE
        SYNTAX  TimeTicks
        ACCESS  read-only
        STATUS  mandatory
        DESCRIPTION
                "Indicates how long the routing service has been in its
                current administrative state on the router port for which
                the entry exists."
        ::= { nwRouterIfEntry 5 }

nwRouterIfName OBJECT-TYPE
        SYNTAX  DisplayString
        ACCESS  read-only
        STATUS  mandatory
        DESCRIPTION
                "Indicates the name of the routing service that is operating on
                 the router port for which the entry exists."
        ::= { nwRouterIfEntry 6 }



--  The Router Routing Protocols Table.
--  This table shows all of the Routing Protocols that make up the routing
--  services.  Essentially,this table gives a high-level view of the
--  configuration and state of each of the Routing protocols running within the
--  Routing Services.


nwRtgProtocolTable   OBJECT-TYPE
        SYNTAX  SEQUENCE OF NwRtgProtocolEntry
        ACCESS  not-accessible
        STATUS  mandatory
        DESCRIPTION
                "This table contains an entry for each routing protocol
                supported by the routing service running on the enabled
                device. Each entry is indexed by the parent routing service,
                nwRtgProtocolRtrInstance. All routing protocols that are
                supported by the same routing service will have the same value
                for nwRtgProtocolRtrInstance. The table is also indexed by an
                ordinal value, nwRtgProtocolInstance, which is assigned to
                each routing protocol as it is instantiated.  Together, these
                two instances show the hierarchical relationship between each
                routing service and its supported routing protocols."
        ::= { nwRtrRoutingSystem 1 }

nwRtgProtocolEntry   OBJECT-TYPE
        SYNTAX  NwRtgProtocolEntry
        ACCESS  not-accessible
        STATUS  mandatory
        DESCRIPTION
                "Each entry identifies a routing protocol and the routing
                service that it is a part of."
        INDEX   { nwRtgProtocolRtrInstance, nwRtgProtocolInstance }
        ::= { nwRtgProtocolTable 1 }

NwRtgProtocolEntry ::=
        SEQUENCE {
                nwRtgProtocolRtrInstance        INTEGER,
                nwRtgProtocolInstance           INTEGER,
                nwRtgProtocolAdminStatus        INTEGER,
                                nwRtgProtocolOperStatus         INTEGER,
                                nwRtgProtocolOperationalTime    TimeTicks,
                nwRtgProtocolEntMibGroup        OBJECT IDENTIFIER,
                                nwRtgProtocolName               DisplayString,
                nwRtgProtocolVersion            DisplayString,
                nwRtgProtocolIdentifier         OBJECT IDENTIFIER
                }


nwRtgProtocolRtrInstance  OBJECT-TYPE
        SYNTAX  INTEGER
        ACCESS  read-only
        STATUS  mandatory
        DESCRIPTION
                "This ordinal value indicates the value of nwRouterInstance
                as established in the nwRouterSystemTable. This essentially
                is the key that maps all routing protocols supported by the
                same routing service to the same value for
                nwRtgProtocolRtrInstance."
        ::= { nwRtgProtocolEntry 1 }

nwRtgProtocolInstance        OBJECT-TYPE
        SYNTAX  INTEGER
        ACCESS  read-only
        STATUS  mandatory
        DESCRIPTION
                "An ordinal value assigned to the routing protocol for which
                the entry exists, which is used to uniquely identify each routing
                protocol."
        ::= { nwRtgProtocolEntry 2 }

nwRtgProtocolAdminStatus     OBJECT-TYPE
        SYNTAX  INTEGER {
                        other(1),             --  none of the following
                        disabled(2),          --  not running
                        enabled(3)            --  running
                }
        ACCESS  read-only
        STATUS  mandatory
        DESCRIPTION
                "Indicates the current administrative state of the routing
                protocol for which the entry exists."
        ::= { nwRtgProtocolEntry 3 }

nwRtgProtocolOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
                "Indicates the current operating condition of the routing
                protocol for which the entry exists."
        ::= { nwRtgProtocolEntry 4 }

nwRtgProtocolOperationalTime  OBJECT-TYPE
        SYNTAX  TimeTicks
        ACCESS  read-only
        STATUS  mandatory
        DESCRIPTION
                "Indicates how long this Routing protocol has been in its
                current state for which the entry exists."
        ::= { nwRtgProtocolEntry 5 }

nwRtgProtocolEntMibGroup OBJECT-TYPE
        SYNTAX  OBJECT IDENTIFIER
        ACCESS  read-only
        STATUS  mandatory
        DESCRIPTION
                "Identifies the starting OID of the subtree or branch of
                                the Cabletron Enterprise MIB that implements the
                managed objects for the routing service for which the entry
                exists."
        ::= { nwRtgProtocolEntry 6 }


nwRtgProtocolName OBJECT-TYPE
        SYNTAX  DisplayString
        ACCESS  read-only
        STATUS  mandatory
        DESCRIPTION
                "Names the routing protocol in textual format for which the
                entry exists."
        ::= { nwRtgProtocolEntry 7 }


nwRtgProtocolVersion  OBJECT-TYPE
        SYNTAX  DisplayString
        ACCESS  read-only
        STATUS  mandatory
        DESCRIPTION
                "Indicates the current revision level of the routing protocol,
                in textual format, for which the entry exists."
        ::= { nwRtgProtocolEntry 8 }

nwRtgProtocolIdentifier  OBJECT-TYPE
        SYNTAX  OBJECT IDENTIFIER
        ACCESS  read-only
        STATUS  mandatory
        DESCRIPTION
                "Specifies the OID from the Cabletron ctNetwork naming tree
                used to uniquely identify the routing protocol for which the
                entry exists."
        ::= { nwRtgProtocolEntry 9 }


--  The Interfaces Table
--  This shows Routing Services Routing Protocol information on a per
--  interface, or router port basis.

nwRtgProtocolIfTable   OBJECT-TYPE
        SYNTAX  SEQUENCE OF NwRtgProtocolIfEntry
        ACCESS  not-accessible
        STATUS  mandatory
        DESCRIPTION
                "This table contains an entry for each routing protocol
                running on each router port of the routing
                services enabled device."
        ::= { nwRtrRoutingInterfaces 1 }


nwRtgProtocolIfEntry   OBJECT-TYPE
        SYNTAX  NwRtgProtocolIfEntry
        ACCESS  not-accessible
        STATUS  mandatory
        DESCRIPTION
                "Each entry describes a routing protocols that is running on
                the router port for which the entry exists."
        INDEX   { nwRtgProtocolIfIndex, nwRtgProtocolIfRtrInstance,
                nwRtgProtocolIfInstance }
        ::= { nwRtgProtocolIfTable 1 }

NwRtgProtocolIfEntry ::=
        SEQUENCE {
                nwRtgProtocolIfIndex            INTEGER,
                nwRtgProtocolIfRtrInstance      INTEGER,
                nwRtgProtocolIfInstance         INTEGER,
                nwRtgProtocolIfAdminStatus      INTEGER,
                nwRtgProtocolIfOperStatus       INTEGER,
                nwRtgProtocolIfOperationalTime  TimeTicks,
                nwRtgProtocolIfName             DisplayString
                }

nwRtgProtocolIfIndex          OBJECT-TYPE
        SYNTAX  INTEGER
        ACCESS  read-only
        STATUS  mandatory
        DESCRIPTION
                "This ordinal value identifies the MIB2 ifIndex which
                identifies the router port for which the entry exists.
                All entries for the same router port will have the same
                value in nwRtgProtocolIfIndex."
        ::= { nwRtgProtocolIfEntry 1 }


nwRtgProtocolIfRtrInstance  OBJECT-TYPE
        SYNTAX  INTEGER
        ACCESS  read-only
        STATUS  mandatory
        DESCRIPTION
                "This ordinal value indicates the value of nwRouterInstance
                as established in nwRouterSystemTable, running on the router
                port for which the entry exists. All router ports running
                the same routing services will have the same value for
                nwRtgProtocolIfRtrInstance."
        ::= { nwRtgProtocolIfEntry 2 }

nwRtgProtocolIfInstance        OBJECT-TYPE
        SYNTAX  INTEGER
        ACCESS  read-only
        STATUS  mandatory
        DESCRIPTION
                "This ordinal value indicates the value of
                nwRtgProtocolInstance as established in nwRtgProtocolTable,
                supported by the routing service, running on the router port
                for which the entry exists. All router ports running the same
                routing protocol will have the same value for
                nwRtgProtocolIfInstance."
        ::= { nwRtgProtocolIfEntry 3 }

nwRtgProtocolIfAdminStatus     OBJECT-TYPE
        SYNTAX  INTEGER {
                        other(1),             --  none of the following
                        disabled(2),          --  not running
                        enabled(3)            --  running
                }
        ACCESS  read-only
        STATUS  mandatory
        DESCRIPTION
                "Indicates the current administrative state of the routing
                protocol on the router port for which the entry exists."
        ::= { nwRtgProtocolIfEntry 4 }

nwRtgProtocolIfOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
                "Indicates the current operating condition of the routing
                protocol on this router port for which the entry exists."
::= { nwRtgProtocolIfEntry 5 }

nwRtgProtocolIfOperationalTime  OBJECT-TYPE
        SYNTAX  TimeTicks
        ACCESS  read-only
        STATUS  mandatory
        DESCRIPTION
                "This shows how long this Router protocol has been in its
                current state on this router port for which the entry
                exists."
        ::= { nwRtgProtocolIfEntry 6 }

nwRtgProtocolIfName OBJECT-TYPE
        SYNTAX  DisplayString
        ACCESS  read-only
        STATUS  mandatory
        DESCRIPTION
                "The name of the routing protocol, in textual format,
                running on the router port for which the entry exists."
        ::= { nwRtgProtocolIfEntry 7 }


--  The Router Component Table.
--  This table shows all of the components that make up the Routing
--  Services.  Essentially,this table gives a high-level view of the
--  configuration and state of each of the components running within the
--  routing services enabled device.  This high-level view can be acheived
--  without having to load each of the individual router MIB's.


nwComponentTable   OBJECT-TYPE
        SYNTAX  SEQUENCE OF NwComponentEntry
        ACCESS  not-accessible
        STATUS  mandatory
        DESCRIPTION
                "This table contains an entry for each of the component
                protocols that make-up a particular routing service.
                Essentially, this table gives a high-level view of the
                configuration and state of each of the component protocol
                running within each routing service."
        ::= { nwRtrComponentSystem 1 }

nwComponentEntry   OBJECT-TYPE
        SYNTAX  NwComponentEntry
        ACCESS  not-accessible
        STATUS  mandatory
        DESCRIPTION
                "Each entry describes a component protocol."
        INDEX   { nwComponentRtrInstance, nwComponentInstance }
        ::= { nwComponentTable 1 }

NwComponentEntry ::=
        SEQUENCE {
                nwComponentRtrInstance          INTEGER,
                nwComponentInstance             INTEGER,
                nwComponentAdminStatus          INTEGER,
                nwComponentOperStatus           INTEGER,
                nwComponentOperationalTime      TimeTicks,
                nwComponentEntMibGroup          OBJECT IDENTIFIER,
                nwComponentName                 DisplayString,
                nwComponentVersion              DisplayString,
                nwComponentIdentifier           OBJECT IDENTIFIER
                }

nwComponentRtrInstance  OBJECT-TYPE
        SYNTAX  INTEGER
        ACCESS  read-only
        STATUS  mandatory
        DESCRIPTION
               "This ordinal value indicates the value of nwRouterInstance
                as established in nwRouterSystemTable for which the entry
                exists. This essentially is the key that maps all components
                of the same routing service to the same value for
                nwComponentRtrInstance."
        ::= { nwComponentEntry 1 }

nwComponentInstance        OBJECT-TYPE
        SYNTAX  INTEGER
        ACCESS  read-only
        STATUS  mandatory
        DESCRIPTION
                "An ordinal value assigned to each component for which the
                entry exists.."
        ::= { nwComponentEntry 2 }

nwComponentAdminStatus     OBJECT-TYPE
        SYNTAX  INTEGER {
                        other(1),             --  none of the following
                        disabled(2),          --  not running
                        enabled(3)            --  running
                }
        ACCESS  read-only
        STATUS  mandatory
        DESCRIPTION
                "Indicates the current administrative state of the component
                for which the entry exists."
        ::= { nwComponentEntry 3 }

nwComponentOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
                "Indicates the current operating condition of the routing
                component for which the entry exists."
        ::= { nwComponentEntry 4 }

nwComponentOperationalTime  OBJECT-TYPE
        SYNTAX  TimeTicks
        ACCESS  read-only
        STATUS  mandatory
        DESCRIPTION
                "Indicates how long this Router Component, for which the entry
                exists, has been in its current administrative state."
        ::= { nwComponentEntry 5 }

nwComponentEntMibGroup OBJECT-TYPE
        SYNTAX  OBJECT IDENTIFIER
        ACCESS  read-only
        STATUS  mandatory
        DESCRIPTION
                "Identifies the Cabletron Enterprise MIB that implements the
                managed objects for the routing service for which the entry
                exists. Essentially, this is a pointer to the OID of the
                routing service's enterprise MIB. For example, IPX is a
                routing service that has its own enterprise MIB, which is
                identified by the value of nwComponentEntMibGroup."
        ::= { nwComponentEntry 6 }

nwComponentName OBJECT-TYPE
        SYNTAX  DisplayString
        ACCESS  read-only
        STATUS  mandatory
        DESCRIPTION
                "Names the component in textual format for which the entry
                exists."
        ::= { nwComponentEntry 7 }


nwComponentVersion  OBJECT-TYPE
        SYNTAX  DisplayString
        ACCESS  read-only
        STATUS  mandatory
        DESCRIPTION
                "Indicates the current revision level of the component in
                textual format for which the entry exists."
        ::= { nwComponentEntry 8 }

nwComponentIdentifier  OBJECT-TYPE
        SYNTAX  OBJECT IDENTIFIER
        ACCESS  read-only
        STATUS  mandatory
        DESCRIPTION
                "The OID from the Cabletron ctNetwork naming tree MIB used to
                uniquely identify the component for which the entry exists."
        ::= { nwComponentEntry 9 }


--  The Interface Table.
--  The Interface table shows Router Component information on a per
--  network interface, or router port, basis.


nwComponentIfTable   OBJECT-TYPE
    SYNTAX  SEQUENCE OF NwComponentIfEntry
        ACCESS  not-accessible
        STATUS  mandatory
        DESCRIPTION
                "This table contains an entry for each component that is part
                of each routing service in each router port on the
                routing services enabled device."
        ::= { nwRtrComponentInterfaces 1 }

nwComponentIfEntry   OBJECT-TYPE
    SYNTAX  NwComponentIfEntry
        ACCESS  not-accessible
        STATUS  mandatory
        DESCRIPTION
                "Each entry describes a component that is running on the
                router port for which the entry exists."
        INDEX   { nwComponentIfIndex, nwComponentIfRtrInstance,
                  nwComponentIfInstance }
        ::= { nwComponentIfTable 1 }

NwComponentIfEntry ::=
        SEQUENCE {
                nwComponentIfIndex              INTEGER,
                nwComponentIfRtrInstance        INTEGER,
                nwComponentIfInstance           INTEGER,
                nwComponentIfAdminStatus        INTEGER,
                nwComponentIfOperStatus         INTEGER,
                nwComponentIfOperationalTime    TimeTicks,
                nwComponentIfName               DisplayString
                }

nwComponentIfIndex          OBJECT-TYPE
        SYNTAX  INTEGER
        ACCESS  read-only
        STATUS  mandatory
        DESCRIPTION
                "The value of this index identifies the MIB-2 ifIndex which
                identifies the router port for which the entry exists."
        ::= { nwComponentIfEntry 1 }

nwComponentIfRtrInstance  OBJECT-TYPE
        SYNTAX  INTEGER
        ACCESS  read-only
        STATUS  mandatory
        DESCRIPTION
               "This ordinal value indicates the value of nwRouterInstance
                as established in the nwRouterSystemTable.  This essentially
                is the key that maps all components of the same routing
                service to the same value for nwComponentIfRtrInstance."
        ::= { nwComponentIfEntry 2 }

nwComponentIfInstance        OBJECT-TYPE
        SYNTAX  INTEGER
        ACCESS  read-only
        STATUS  mandatory
        DESCRIPTION
                "Indicates the value of nwComponentInstance as established in
                nwComponentTable.  It is used to uniquely order each component
                within each routing service, on each router port for which the
                entry exists."
        ::= { nwComponentIfEntry 3 }

nwComponentIfAdminStatus     OBJECT-TYPE
        SYNTAX  INTEGER {
                        other(1),             --  none of the following
                        disabled(2),          --  not running
                        enabled(3)            --  running
                }
        ACCESS  read-only
        STATUS  mandatory
        DESCRIPTION
                "Indicates the current administrative status of the component
                on the router port for which the entry exists."
        ::= { nwComponentIfEntry 4 }

nwComponentIfOperStatus     OBJECT-TYPE
        SYNTAX  INTEGER {
                        other(1),             --  none of the following
                        disabled(2),          --  not running
                        enabled(3),           --  running
                        pending-disable(4),   --  shut-down in progress
                        pending-enable(5),    --  start-up in progress
                        invalid-config(6)     --  not running,invalid config
                }
        ACCESS  read-only
        STATUS  mandatory
        DESCRIPTION
                "Indicates the current operating condition of the
                components on the router port for which the entry exists."
        ::= { nwComponentIfEntry 5 }

nwComponentIfOperationalTime  OBJECT-TYPE
        SYNTAX  TimeTicks
        ACCESS  read-only
        STATUS  mandatory
        DESCRIPTION
                "Indicates how long the Router Component has been in its
                administrative state for which the entry exists."
        ::= { nwComponentIfEntry 6 }

nwComponentIfName OBJECT-TYPE
        SYNTAX  DisplayString
        ACCESS  read-only
        STATUS  mandatory
        DESCRIPTION
                "The name of the component in textual format for which the
                entry exists."
        ::= { nwComponentIfEntry 7 }


--
--
-- All Routed Protocol Forwarding Interfaces Counter Table
-- This table contains the objects that specify the packet and byte counters
-- on all configured router ports.

 nwRtrIfFwdCtrTable         OBJECT-TYPE
    SYNTAX      SEQUENCE OF NwRtrIfFwdCtrEntry
        ACCESS          not-accessible
        STATUS          mandatory
        DESCRIPTION
         "This table contains the packet and byte counters for each
                  router port configured on this device."
        ::= { nwRtrInterfaceCounters 1 }

 nwRtrIfFwdCtrEntry         OBJECT-TYPE
    SYNTAX      NwRtrIfFwdCtrEntry
        ACCESS      not-accessible
        STATUS          mandatory
        DESCRIPTION
         "Specifies the aggregate packet and byte counters for the
                  router port for which this entry exists."
        INDEX { nwRtrIfFwdCtrIfIndex }
        ::= {  nwRtrIfFwdCtrTable 1 }

 NwRtrIfFwdCtrEntry ::=
        SEQUENCE {
                 nwRtrIfFwdCtrIfIndex               INTEGER,
                 nwRtrIfFwdCtrOperStatus                    INTEGER,
                 nwRtrIfFwdCtrInPkts                Counter,
                 nwRtrIfFwdCtrOutPkts               Counter,
                 nwRtrIfFwdCtrFwdPkts               Counter,
                 nwRtrIfFwdCtrFilteredPkts          Counter,
                 nwRtrIfFwdCtrDiscardPkts           Counter,
                         nwRtrIfFwdCtrAddrErrPkts                   Counter,
                         nwRtrIfFwdCtrLenErrPkts            Counter,
                         nwRtrIfFwdCtrHdrErrPkts            Counter,
                         nwRtrIfFwdCtrInBytes               Counter,
                 nwRtrIfFwdCtrOutBytes              Counter,
                 nwRtrIfFwdCtrFwdBytes              Counter,
                 nwRtrIfFwdCtrFilteredBytes         Counter,
                 nwRtrIfFwdCtrDiscardBytes          Counter,
                 nwRtrIfFwdCtrHostInPkts            Counter,
                 nwRtrIfFwdCtrHostOutPkts           Counter,
                 nwRtrIfFwdCtrHostDiscardPkts       Counter,
                 nwRtrIfFwdCtrHostInBytes           Counter,
                 nwRtrIfFwdCtrHostOutBytes          Counter,
                 nwRtrIfFwdCtrHostDiscardBytes      Counter
        }

 nwRtrIfFwdCtrIfIndex       OBJECT-TYPE
        SYNTAX          INTEGER
        ACCESS          read-only
        STATUS          mandatory
        DESCRIPTION
                "Indicates the value of MIB 2 ifindex, which identifies the router
                 port. When multiple routing services are running on the same router
                 port multiple entries  exist for the same nwRouterIfIndex."
        ::= {  nwRtrIfFwdCtrEntry 1 }

 nwRtrIfFwdCtrOperStatus     OBJECT-TYPE
        SYNTAX  INTEGER {
                        other(1),             --  none of the following
                        disabled(2),          --  not counting
                        enabled(3)            --  counting
                }
        ACCESS  read-only
        STATUS  mandatory
        DESCRIPTION
         "Indicates the current operating condition of the routing
                  services on the router port.  The value of  nwRtrIfFwdCtrOperStatus
                  indicates whether counting is active for the routing services
                  on the routing port."
        ::= {  nwRtrIfFwdCtrEntry 2 }


 nwRtrIfFwdCtrInPkts        OBJECT-TYPE
        SYNTAX          Counter
        ACCESS          read-only
        STATUS          mandatory
        DESCRIPTION
                "Indicates the total number of Routed Protocol packets that have been
                 received, during  System Operational Time, on the
                 router port for which this entry exists."
        ::= {  nwRtrIfFwdCtrEntry 3 }

 nwRtrIfFwdCtrOutPkts       OBJECT-TYPE
        SYNTAX          Counter
        ACCESS          read-only
        STATUS          mandatory
        DESCRIPTION
        "Indicates the total number of Routed Protocol packets that have been
                 transmitted, during  System Operational Time, on the
                 router port for which this entry exists"
        ::= {  nwRtrIfFwdCtrEntry 4 }

 nwRtrIfFwdCtrFwdPkts       OBJECT-TYPE
        SYNTAX          Counter
        ACCESS          read-only
        STATUS          mandatory
        DESCRIPTION
        "Indicates the total number of Routed Protocol packets that have been
                 forwarded, during  System Operational Time, on the
             router port for which this entry exists"
        ::= {  nwRtrIfFwdCtrEntry 5 }

 nwRtrIfFwdCtrFilteredPkts OBJECT-TYPE
        SYNTAX          Counter
        ACCESS          read-only
        STATUS          mandatory
        DESCRIPTION
           "Indicates the total number of Routed Protocol packets that have been
                administratively filtered, during
                System Operational Time, on the  router port for
                which this entry exists."
        ::= {  nwRtrIfFwdCtrEntry 6 }

 nwRtrIfFwdCtrDiscardPkts  OBJECT-TYPE
        SYNTAX          Counter
        ACCESS          read-only
        STATUS          mandatory
        DESCRIPTION
           "Indicates the total number of Routed Protocol packets that have been
                discarded (dropped), during  System Operational Time,
                on the  router port for which the entry exists."
        ::= {  nwRtrIfFwdCtrEntry 7 }

 nwRtrIfFwdCtrAddrErrPkts        OBJECT-TYPE
        SYNTAX  Counter
        ACCESS  read-only
        STATUS  mandatory
        DESCRIPTION
                "Indicates the total number of Routed Protocol packets that have been
                discarded, because of Routed Protocol addressing errors in the
            Routed Protocol header, during  System Operational Time, on the
                router port for which the entry exists."
        ::= {  nwRtrIfFwdCtrEntry 8 }

 nwRtrIfFwdCtrLenErrPkts        OBJECT-TYPE
        SYNTAX  Counter
        ACCESS  read-only
        STATUS  mandatory
        DESCRIPTION
                "Indicates the total number of Routed Protocol packets that have been
                discarded, because an invalid packet length was contained
                in the Routed Protocol header, during  System Operational Time, on
                the  router port for which the entry exists."
        ::= {  nwRtrIfFwdCtrEntry 9 }

 nwRtrIfFwdCtrHdrErrPkts        OBJECT-TYPE
        SYNTAX  Counter
        ACCESS  read-only
        STATUS  mandatory
        DESCRIPTION
                "Indicates the total number of Routed Protocol packets that have been
                discarded, because of an invalid Routed Protocol header, during
                 System Operational Time, on the  router port for
                which the entry exists."
        ::= {  nwRtrIfFwdCtrEntry 10 }

 nwRtrIfFwdCtrInBytes      OBJECT-TYPE
        SYNTAX          Counter
        ACCESS          read-only
        STATUS          mandatory
        DESCRIPTION
                "Indicates the total number of bytes in the Routed Protocol packets
                that have been received, during  System Operational Time, on the
            router port for which the entry exists."
        ::= {  nwRtrIfFwdCtrEntry 11 }

 nwRtrIfFwdCtrOutBytes     OBJECT-TYPE
        SYNTAX          Counter
        ACCESS          read-only
        STATUS          mandatory
        DESCRIPTION
        "Indicates the total number of bytes in the Routed Protocol packets
                 that have been transmitted, during  System Operational Time, on the
                 router port for which the entry exists."
        ::= {  nwRtrIfFwdCtrEntry 12 }

 nwRtrIfFwdCtrFwdBytes     OBJECT-TYPE
        SYNTAX          Counter
        ACCESS          read-only
        STATUS          mandatory
        DESCRIPTION
        "Indicates the total number of bytes in the Routed Protocol packets
                 that have been forwarded, during  System Operational Time, on the
         router port for which the entry exists."
        ::= {  nwRtrIfFwdCtrEntry 13 }

 nwRtrIfFwdCtrFilteredBytes        OBJECT-TYPE
        SYNTAX                  Counter
        ACCESS                  read-only
        STATUS                  mandatory
        DESCRIPTION
                "Indicates the total number of bytes in the Routed Protocol packets
                that have been administratively filtered, during
                 System Operational Time, on the  router port for
                which the entry exists."
        ::= {  nwRtrIfFwdCtrEntry 14 }

 nwRtrIfFwdCtrDiscardBytes OBJECT-TYPE
        SYNTAX          Counter
        ACCESS          read-only
        STATUS          mandatory
        DESCRIPTION
                "Indicates the total number of bytes in the Routed Protocol packets
                that have been discarded, during  System Operational Time, on the
            router port for     which the entry exists."
        ::= {  nwRtrIfFwdCtrEntry 15 }

 nwRtrIfFwdCtrHostInPkts   OBJECT-TYPE
        SYNTAX          Counter
        ACCESS          read-only
        STATUS          mandatory
        DESCRIPTION
                "Indicates the total number of Routed Protocol packets that have been
                delivered to the local host, during      System Operational Time,
            that were received on the router port for which the entry exists."
        ::= {  nwRtrIfFwdCtrEntry 16 }

 nwRtrIfFwdCtrHostOutPkts  OBJECT-TYPE
        SYNTAX          Counter
        ACCESS          read-only
        STATUS          mandatory
        DESCRIPTION
                "Indicates the total number of Routed Protocol packets that have been
                forwarded by the local host, during  System Operational Time, on the
            router port for     which the entry exists."
        ::= {  nwRtrIfFwdCtrEntry 17 }

 nwRtrIfFwdCtrHostDiscardPkts      OBJECT-TYPE
        SYNTAX          Counter
        ACCESS          read-only
        STATUS          mandatory
        DESCRIPTION
                "Indicates the total number of Routed Protocol packets that have been
                discarded by the local host, during  System Operational Time,
                that were received on the router port for which the entry exists."
        ::= {  nwRtrIfFwdCtrEntry 18 }

 nwRtrIfFwdCtrHostInBytes  OBJECT-TYPE
        SYNTAX          Counter
        ACCESS          read-only
        STATUS          mandatory
        DESCRIPTION
                "Indicates the total number of bytes in the Routed Protocol packets
                that have been received by the local host, during
                 System Operational Time, on the  router port for which the entry
            exists."
        ::= {  nwRtrIfFwdCtrEntry 19 }

 nwRtrIfFwdCtrHostOutBytes OBJECT-TYPE
        SYNTAX          Counter
        ACCESS          read-only
        STATUS          mandatory
        DESCRIPTION
                "Indicates the total number of bytes in the Routed Protocol packets
                that have been forwarded by the local host, during
                 System Operational Time, on the  router port for which the entry
            exists."
        ::= {  nwRtrIfFwdCtrEntry 20 }

 nwRtrIfFwdCtrHostDiscardBytes     OBJECT-TYPE
        SYNTAX                  Counter
        ACCESS                  read-only
        STATUS                  mandatory
        DESCRIPTION
                "Indicates the total number of bytes in the Routed Protocol packets
                that have been discarded by the local host, that were
                received, during  System Operational Time, on the
                router port for which the entry exists."
        ::= {  nwRtrIfFwdCtrEntry 21 }

END
