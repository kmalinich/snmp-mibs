ENTERASYS-IP-SLA-MIB DEFINITIONS ::= BEGIN

--  enterasys-ip-sla-mib.txt
--
--  Part Number:
--
--

--  This module provides authoritative definitions for Enterasys
--  Networks' IP SLA functionality.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2013 Enterasys Networks, Inc.

IMPORTS
    MODULE-IDENTITY, OBJECT-TYPE, Unsigned32, Gauge32
        FROM SNMPv2-SMI
    RowStatus
        FROM SNMPv2-TC
    MODULE-COMPLIANCE, OBJECT-GROUP
        FROM SNMPv2-CONF
    SnmpAdminString
        FROM SNMP-FRAMEWORK-MIB
    InetAddressType, InetAddress, InetPortNumber
        FROM INET-ADDRESS-MIB
    etsysModules
        FROM ENTERASYS-MIB-NAMES;

etsysIpSlaMIB MODULE-IDENTITY
    LAST-UPDATED "201302061826Z"  -- Wed Feb  6 18:26 UTC 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"
    DESCRIPTION
        "This MIB module defines a portion of the SNMP MIB under
         the Enterasys Networks enterprise OID pertaining to the
         IP Service Level Agreement (SLA) functionality.

         This MIB was designed to be used for configuring IP SLA
         entries, scheduling those entries to run tests, and retrieving
         the round-trip-time and packet delay variation (jitter) data.
         Management entities MAY use this data to verify the service
         provider is meeting its SLA obligation."

    REVISION    "201302061826Z"  -- Wed Feb  6 18:26 UTC 2013
    DESCRIPTION "The initial version of this MIB module"
    ::= { etsysModules 94 }

-- Textual Conventions


-- -------------------------------------------------------------
-- Branches
-- -------------------------------------------------------------
etsysIpSla OBJECT IDENTIFIER ::= { etsysIpSlaMIB 1 }

etsysIpSlaGlobals OBJECT IDENTIFIER ::= { etsysIpSla 1 }
etsysIpSlaTables OBJECT IDENTIFIER ::= { etsysIpSla 2 }

-- -------------------------------------------------------------
-- MIB Objects
-- -------------------------------------------------------------

etsysIpSlaMaxEntries OBJECT-TYPE
    SYNTAX       Unsigned32
    MAX-ACCESS   read-only
    STATUS       current
    DESCRIPTION
        "The maximum number of IP SLA entries that can be configured
         within the system."
    ::= { etsysIpSlaGlobals 1 }

etsysIpSlaEntriesInUse OBJECT-TYPE
    SYNTAX       Gauge32
    MAX-ACCESS   read-only
    STATUS       current
    DESCRIPTION
        "The number of IP SLA entries currently configured within the
         system."
    ::= { etsysIpSlaGlobals 2 }

etsysIpSlaMaxDataEntries OBJECT-TYPE
    SYNTAX       Unsigned32
    MAX-ACCESS   read-only
    STATUS       current
    DESCRIPTION
        "The maximum number of data constructs available within the
         system.  Row entries in the etsysIpSlaRttDataTable and the
         etsysIpSlaPdvDataTable consume this resource."
    ::= { etsysIpSlaGlobals 3 }

etsysIpSlaDataEntriesInUse OBJECT-TYPE
    SYNTAX       Gauge32
    MAX-ACCESS   read-only
    STATUS       current
    DESCRIPTION
        "The number of data constructs currently used within the system
         Row entries in the etsysIpSlaRttDataTable and the
         etsysIpSlaPdvDataTable consume this resource."
    ::= { etsysIpSlaGlobals 4 }


--
-- Enterasys IP SLA Configuration Table
--
etsysIpSlaConfigTable OBJECT-TYPE
    SYNTAX       SEQUENCE OF EtsysIpSlaConfigEntry
    MAX-ACCESS   not-accessible
    STATUS       current
    DESCRIPTION
        "This table defines the configuration parameters and attributes
         pertaining to an IP SLA entry.

         The agent limits the size of this table.  The object
         etsysIpSlaMaxEntries defines the maximum number of entries."
    ::= { etsysIpSlaTables 1 }

etsysIpSlaConfigEntry OBJECT-TYPE
    SYNTAX       EtsysIpSlaConfigEntry
    MAX-ACCESS   not-accessible
    STATUS       current
    DESCRIPTION
        "An entry (conceptual row) in the etsysIpSlaConfigTable."
    INDEX { etsysIpSlaConfigIndex }
    ::= { etsysIpSlaConfigTable 1 }

EtsysIpSlaConfigEntry ::= SEQUENCE {
    etsysIpSlaConfigIndex                         Unsigned32,
    etsysIpSlaConfigType                          INTEGER,
    etsysIpSlaConfigDestType                      InetAddressType,
    etsysIpSlaConfigDestAddr                      InetAddress,
    etsysIpSlaConfigDestPort                      InetPortNumber,
    etsysIpSlaConfigProbeName                     SnmpAdminString,
    etsysIpSlaConfigPathCount                     Unsigned32,
    etsysIpSlaConfigHopCount                      Unsigned32,
    etsysIpSlaConfigHistoryCollections            Unsigned32,
    etsysIpSlaConfigHistoryBuckets                Unsigned32,
    etsysIpSlaConfigHistoryBucketType             INTEGER,
    etsysIpSlaConfigHistorySamples                Unsigned32,
    etsysIpSlaConfigHistoryInterval               Unsigned32,
    etsysIpSlaConfigHistoryAgeout                 Unsigned32,
    etsysIpSlaConfigHistoryWrap                   INTEGER,
    etsysIpSlaConfigDistributionCount             Unsigned32,
    etsysIpSlaConfigDistributionInterval          Unsigned32,
    etsysIpSlaConfigStatisticsCollections         Unsigned32,
    etsysIpSlaConfigStatus                        RowStatus
}

etsysIpSlaConfigIndex OBJECT-TYPE
    SYNTAX       Unsigned32
    MAX-ACCESS   not-accessible
    STATUS       current
    DESCRIPTION
        "A value that uniquely identifies a row in the
         etsysIpSlaConfigTable.

         This is the primary index used for all tables that have an
         association with an IP SLA entry."
    ::= { etsysIpSlaConfigEntry 1 }

etsysIpSlaConfigType OBJECT-TYPE
    SYNTAX       INTEGER {
                     echo(1),
                     jitter(2)
                 }
    MAX-ACCESS   read-create
    STATUS       current
    DESCRIPTION
        "The type of the IP SLA entry.

         echo(1)   - Specifies that the IP SLA entry collect the
                     round-trip-time data for a destination host.  The IP
                     SLA entry MUST use a probe of type 'icmpTs'.

         jitter(2) - Specifies that the IP SLA entry collect the packet
                     delay variation (jitter) and round-trip-time data
                     for a destination host.  The IP SLA entry MUST use
                     a probe of type 'icmpTs'.  Both the source and
                     destination hosts MUST have clock synchorinzation
                     enabled for accurate packet delay variation data."
    REFERENCE
        "Tracked Objects MIB, Table etsysTrackedObjectsProbeTable,
         Objects etsysTrackedObjectsProbeType."
    DEFVAL { echo }
    ::= { etsysIpSlaConfigEntry 2 }

etsysIpSlaConfigDestType OBJECT-TYPE
    SYNTAX       InetAddressType
    MAX-ACCESS   read-create
    STATUS       current
    DESCRIPTION
        "The address family of the destination host specified in
         etsysIpSlaConfigDestAddr."
    DEFVAL { unknown }
    ::= { etsysIpSlaConfigEntry 3 }

etsysIpSlaConfigDestAddr OBJECT-TYPE
    SYNTAX       InetAddress
    MAX-ACCESS   read-create
    STATUS       current
    DESCRIPTION
        "The destination address of the host.  The IP SLA entry collects
         the data specified in etsysIpSlaConfigType for packets sent to
         this host."
    DEFVAL { "" }
    ::= { etsysIpSlaConfigEntry 4 }

etsysIpSlaConfigDestPort OBJECT-TYPE
    SYNTAX       InetPortNumber
    MAX-ACCESS   read-create
    STATUS       current
    DESCRIPTION
        "The port number of the service on the destination host.  The
         'icmpTs' entries MUST use the default value of zero."
    REFERENCE
        "Tracked Objects MIB, Table etsysTrackedObjectsProbeTable,
         Objects etsysTrackedObjectsProbeType."
    DEFVAL { 0 }
    ::= { etsysIpSlaConfigEntry 5 }

etsysIpSlaConfigProbeName OBJECT-TYPE
    SYNTAX       SnmpAdminString (SIZE(0..31))
    MAX-ACCESS   read-create
    STATUS       current
    DESCRIPTION
        "The name of the user configured probe this entry references.

         If this value is the empty string, the default probe assigned
         to the IP SLA application is used for running tests."
    REFERENCE
        "Tracked Objects MIB, Table etsysTrackedObjectsProbeTable,
         Objects etsysTrackedObjectsProbeName."
    DEFVAL { "" }
    ::= { etsysIpSlaConfigEntry 6 }

etsysIpSlaConfigPathCount OBJECT-TYPE
    SYNTAX       Unsigned32 (0..4)
    UNITS        "paths"
    MAX-ACCESS   read-create
    STATUS       current
    DESCRIPTION
        "A packet may traverse different routes to a destination host.
         This value specifies how many different paths to keep track of.
         Only the first etsysIpSlaConfigPathCount will be kept,
         additional detected paths are ignored.

         This object is only valid when the etsysIpSlaConfigType is
         'echo'.  An 'inconsistentValue' return code is returned for a
         set operation when the type is other than 'echo'."
    DEFVAL { 0 }
    ::= { etsysIpSlaConfigEntry 7 }

etsysIpSlaConfigHopCount OBJECT-TYPE
    SYNTAX       Unsigned32 (0..8)
    UNITS        "hops"
    MAX-ACCESS   read-create
    STATUS       current
    DESCRIPTION
        "The number of hops per path the entry keeps data for.  Only the
         first etsysIpSlaConfigHopCount will be kept, additional hops
         along the path are ignored.

         This object is only valid when the etsysIpSlaConfigType is
         'echo'.  An 'inconsistentValue' return code is returned for a
         set operation when the type is other than 'echo'."
    DEFVAL { 1 }
    ::= { etsysIpSlaConfigEntry 8 }

etsysIpSlaConfigHistoryCollections OBJECT-TYPE
    SYNTAX       Unsigned32 (0..10)
    MAX-ACCESS   read-create
    STATUS       current
    DESCRIPTION
        "The number of history collections to store in memory.  A new
         collection begins with the start of each test.  The
         etsysIpSlaScheduleTable dictates when tests start and stop.

         Modifying this value from a larger value to a smaller value
         causes the difference to be removed from memory.  The
         collection with higher index values are removed.  The history
         collections are found in the etsysIpSlaRttDataTable and the
         etsysIpSlaPdvDataTable using a etsysIpSlaCollectionType of
         'history'."
    DEFVAL { 0 }
    ::= { etsysIpSlaConfigEntry 9 }

etsysIpSlaConfigHistoryBuckets OBJECT-TYPE
    SYNTAX       Unsigned32 (1..50)
    MAX-ACCESS   read-create
    STATUS       current
    DESCRIPTION
        "The number of history buckets to maintain per history
         collection.  Each bucket contains statistical information from
         the test."
    DEFVAL { 15 }
    ::= { etsysIpSlaConfigEntry 10 }

etsysIpSlaConfigHistoryBucketType OBJECT-TYPE
    SYNTAX       INTEGER {
                     static(1),
                     timed(2)
                 }
    MAX-ACCESS   read-create
    STATUS       current
    DESCRIPTION
        "The history bucket type.  This determines the depth of each
         bucket.

         static(1) - A static bucket type indicates the depth of each
                     bucket is fixed.  The depth is specified in
                     etsysIpSlaConfigHistorySamples.

         timed(2)  - A timed bucket has a variable bucket depth.  The
                     etsysIpSlaConfigHistoryInterval specifies the
                     total time for the bucket.  To estimate the depth
                     of the bucket, multiply the history interval by the
                     expected number of received packets per second."
    REFERENCE
        "Tracked Objects MIB, Table etsysTrackedObjectsProbeStatsTable,
         Objects etsysTrackedObjectsProbeStatsInterval."
    DEFVAL { static }
    ::= { etsysIpSlaConfigEntry 11 }

etsysIpSlaConfigHistorySamples OBJECT-TYPE
    SYNTAX       Unsigned32 (16..512)
    MAX-ACCESS   read-create
    STATUS       current
    DESCRIPTION
        "Specifies the static depth of each bucket.  Modifying this
         value changes the depth for current and future buckets.
         Previous buckets MUST NOT be modified.

         This object is only valid when etsysIpSlaConfigHistoryBucketType
         is 'static'.  An 'inconsistentValue' return code is returned for
         a set operation when the type is other than 'static'."
    DEFVAL { 16 }
    ::= { etsysIpSlaConfigEntry 12 }

etsysIpSlaConfigHistoryInterval OBJECT-TYPE
    SYNTAX       Unsigned32 (30..3600)
    UNITS        "seconds"
    MAX-ACCESS   read-create
    STATUS       current
    DESCRIPTION
        "Specifies the length of time data should be continuously stored
         in the same bucket.  Modifying this value changes the time for
         the current and future buckets.  Previous buckets MUST NOT be
         modified.  Data in the current bucket MUST NOT be altered
         either.

         This object is only valid when etsysIpSlaConfigHistoryBucketType
         is 'timed'.  An 'inconsistentValue' return code is returned for
         a set operation when the type is other than 'timed'."
    DEFVAL { 30 }
    ::= { etsysIpSlaConfigEntry 13 }

etsysIpSlaConfigHistoryAgeout OBJECT-TYPE
    SYNTAX       Unsigned32 (0|15..7200)
    UNITS        "minutes"
    MAX-ACCESS   read-create
    STATUS       current
    DESCRIPTION
        "The length of time a history collection remains in memory.  The
         application reclaims the history collection's memory when it
         ages out.

         A value of zero means the history collection does not ageout."
    DEFVAL { 0 }
    ::= { etsysIpSlaConfigEntry 14 }

etsysIpSlaConfigHistoryWrap OBJECT-TYPE
    SYNTAX       INTEGER {
                     wrap(1),
                     noWrap(2)
                 }
    MAX-ACCESS   read-create
    STATUS       current
    DESCRIPTION
        "Specifies whether to replace the oldest history collection with
         a newer data set, or stop collecting history data when the
         collection limit is reached.

         wrap(1)   - When the history collection reaches its limit, the
                     oldest history collection data is replaced with the
                     newer data set.
         noWrap(2) - Once the history collection limit is reached, no new
                     history collections are stored unless they age out."
    DEFVAL { noWrap }
    ::= { etsysIpSlaConfigEntry 15 }

etsysIpSlaConfigDistributionCount OBJECT-TYPE
    SYNTAX       Unsigned32 (0|2..5)
    MAX-ACCESS   read-create
    STATUS       current
    DESCRIPTION
        "The number of statistical distributions to keep data for.  This
         object only accumulates round-trip-time data calculations.

         This objects works in conjunction with the
         etsysIpSlaConfigDistributionInterval object.  The last interval
         accumulates statistical distributions for all the entries from
         its interval start point to infinity (maximum value for a
         32-bit integer)."
    DEFVAL { 0 }
    ::= { etsysIpSlaConfigEntry 16 }

etsysIpSlaConfigDistributionInterval OBJECT-TYPE
    SYNTAX       Unsigned32 (5..1000)
    UNITS        "milliseconds"
    MAX-ACCESS   read-create
    STATUS       current
    DESCRIPTION
        "The statistical distribution interval.

         Example:
         etsysIpSlaConfigDistributionCount = 5
         etsysIpSlaConfigDistributionInterval = 20 milliseconds

          Distribution 1 : < 0 - 19 ms>
          Distribution 2 : <20 - 39 ms>
          Distribution 3 : <40 - 59 ms>
          Distribution 4 : <60 - 79 ms>
          Distribution 5 : <80 - 4294967295 ms>"
    DEFVAL { 25 }
    ::= { etsysIpSlaConfigEntry 17 }

etsysIpSlaConfigStatisticsCollections OBJECT-TYPE
    SYNTAX       Unsigned32 (1..10)
    MAX-ACCESS   read-create
    STATUS       current
    DESCRIPTION
        "The number of statistical collections to store in memory.  Each
         collection consists of the summary of results and the
         statistical distribution data.  The summary of results consists
         of the round-trip-time and, if applicable, the packet delay
         variation data.

         A new collection begins with the start of each test.  The
         etsysIpSlaScheduleTable dictates when tests start and stop.
         The collection automatically wraps back to one when the
         collection limit, configured by this object, is reached.  The
         statistics stored in the collection are cleared prior to
         starting a new test.

         Modifying this value from a larger to a smaller value causes
         the difference to be removed from memory.  The collections with
         the higher index values are removed.  The statistical
         collections are found in the etsysIpSlaRttDataTable and the
         etsysIpSlaPdvDataTable."
    DEFVAL { 1 }
    ::= { etsysIpSlaConfigEntry 18 }

etsysIpSlaConfigStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysIpSlaConfigEntry 19 }


--
-- Enterasys IP SLA Schedule Table
--
etsysIpSlaScheduleTable OBJECT-TYPE
    SYNTAX       SEQUENCE OF EtsysIpSlaScheduleEntry
    MAX-ACCESS   not-accessible
    STATUS       current
    DESCRIPTION
        "This table provides the scheduling parameters and attributes
         pertaining to an IP SLA entry.  The scheduler determines when
         a test should execute, the length of time that test should run,
         the number of iterations of the test, and when the next
         scheduled test should start.  An entry MUST exist in the
         etsysIpSlaConfigTable prior to setting the scheduling objects."
    ::= { etsysIpSlaTables 2 }

etsysIpSlaScheduleEntry OBJECT-TYPE
    SYNTAX       EtsysIpSlaScheduleEntry
    MAX-ACCESS   not-accessible
    STATUS       current
    DESCRIPTION
        "An entry (conceptual row) in the etsysIpSlaScheduleTable."
    INDEX { etsysIpSlaConfigIndex }
    ::= { etsysIpSlaScheduleTable 1 }

EtsysIpSlaScheduleEntry ::= SEQUENCE {
    etsysIpSlaScheduleStartTime                   Unsigned32,
    etsysIpSlaScheduleRecurrence                  Unsigned32,
    etsysIpSlaScheduleTestRepetitions             Unsigned32,
    etsysIpSlaScheduleTestDuration                Unsigned32,
    etsysIpSlaScheduleTestFrequency               Unsigned32,
    etsysIpSlaScheduleTestState                   INTEGER,
    etsysIpSlaScheduleTestStatus                  SnmpAdminString
}

etsysIpSlaScheduleStartTime OBJECT-TYPE
    SYNTAX       Unsigned32
    MAX-ACCESS   read-write
    STATUS       current
    DESCRIPTION
        "This is the initial start time for the entry's set of test
         cycles.  This value is expressed in seconds since the Epoch
         (Jan 1, 1970).

         The scheduled entry MUST be cancelled prior to modifying the
         start time.  An 'inconsistentValue' return code is returned for
         a set operation with a value other than zero if the
         etsysIpSlaScheduleTestState is NOT 'inactive'.

         Setting this value to zero cancels the scheduled tests and
         the etsysIpSlaScheduleTestState transitions to 'inactive'."
    REFERENCE
        "POSIX.1-2001."
    DEFVAL { 0 }
    ::= { etsysIpSlaScheduleEntry 1 }

etsysIpSlaScheduleRecurrence OBJECT-TYPE
    SYNTAX       Unsigned32 (0|120..7776000)
    UNITS        "seconds"
    MAX-ACCESS   read-write
    STATUS       current
    DESCRIPTION
        "This value represents the time between multiple test cycles.
         This value is the length of time between the end of one test
         cycle and the start of the next test cycle.

         A new test cycle SHALL NOT begin while a current cycle is
         running.  Thus, this value SHOULD be greater than the result of
         the number repetitions multiplied by the sum of the duration and
         the frequency.  If the value is less than the run time of a test
         cycle, the overlapping test cycles are skipped.

         For example, if there are two repetitions with a duration of 60
         seconds and a frequency of 30 seconds, the test cycle runs for
         180 seconds.

         Notes: Maximum value is 90 days; a value of 86400 is one day.

         A value of zero indicates this scheduled entry will not repeat
         its test cycle."
    DEFVAL { 0 }
    ::= { etsysIpSlaScheduleEntry 2 }

etsysIpSlaScheduleTestRepetitions OBJECT-TYPE
    SYNTAX       Unsigned32 (1..10)
    MAX-ACCESS   read-write
    STATUS       current
    DESCRIPTION
        "The number of test iterations per test cycle."
    DEFVAL { 1 }
    ::= { etsysIpSlaScheduleEntry 3 }

etsysIpSlaScheduleTestDuration OBJECT-TYPE
    SYNTAX       Unsigned32 (30..3600)
    UNITS        "seconds"
    MAX-ACCESS   read-write
    STATUS       current
    DESCRIPTION
        "The length of the time each test iteration should execute."
    DEFVAL { 30 }
    ::= { etsysIpSlaScheduleEntry 4 }

etsysIpSlaScheduleTestFrequency OBJECT-TYPE
    SYNTAX       Unsigned32 (30..3600)
    UNITS        "seconds"
    MAX-ACCESS   read-write
    STATUS       current
    DESCRIPTION
        "The length of time between each test iteration."
    DEFVAL { 30 }
    ::= { etsysIpSlaScheduleEntry 5 }

etsysIpSlaScheduleTestState OBJECT-TYPE
    SYNTAX       INTEGER {
                     inactive(1),
                     complete(2),
                     running(3),
                     queued(4)
                 }
    MAX-ACCESS   read-only
    STATUS       current
    DESCRIPTION
        "This is the state of the IP SLA entry test.

         inactive(1) - The entry is not currently scheduled.
         complete(2) - The entry has completed its test cycle and will
                       not be rescheduled.
         running(3)  - A test cycle is currently executing.
         queued(4)   - The entry is on scheduler's queue and will start
                       when the entry expires and is removed from the
                       queue.  At this point, it's state transitions to
                       'running'."
    ::= { etsysIpSlaScheduleEntry 6 }

etsysIpSlaScheduleTestStatus OBJECT-TYPE
    SYNTAX       SnmpAdminString (SIZE(0..63))
    MAX-ACCESS   read-only
    STATUS       current
    DESCRIPTION
        "Provides a brief description of the test.  The scheduler
         generates this string based on the test's state and where it
         is in it's tests cycle.

         For example, if the etsysIpSlaScheduleTestState is 'queued'
         and there is 193 seconds prior to the next test cycle starting,
         the string MAY read:

             Cycle begins in 193 seconds

         An implementation MAY choose to always return the empty string."
    ::= { etsysIpSlaScheduleEntry 7 }


--
-- Enterasys IP SLA Collection Table
--
etsysIpSlaCollectionTable OBJECT-TYPE
    SYNTAX       SEQUENCE OF EtsysIpSlaCollectionEntry
    MAX-ACCESS   not-accessible
    STATUS       current
    DESCRIPTION
        "This table provides generic information about the data
         collections stored in the IP SLA entry.  A new collection
         begins at the beginning of each test."
    ::= { etsysIpSlaTables 3 }

etsysIpSlaCollectionEntry OBJECT-TYPE
    SYNTAX       EtsysIpSlaCollectionEntry
    MAX-ACCESS   not-accessible
    STATUS       current
    DESCRIPTION
        "An entry (conceptual row) in the etsysIpSlaCollectionTable."
    INDEX {
        etsysIpSlaConfigIndex,
        etsysIpSlaCollectionType,
        etsysIpSlaCollectionIndex
    }
    ::= { etsysIpSlaCollectionTable 1 }

EtsysIpSlaCollectionEntry ::= SEQUENCE {
    etsysIpSlaCollectionType                      INTEGER,
    etsysIpSlaCollectionIndex                     Unsigned32,
    etsysIpSlaCollectionStartTime                 Unsigned32,
    etsysIpSlaCollectionNumPaths                  Gauge32,
    etsysIpslaCollectionNumHops                   Gauge32
}

etsysIpSlaCollectionType OBJECT-TYPE
    SYNTAX       INTEGER {
                     summary(1),
                     distribution(2),
                     history(3)
                 }
    MAX-ACCESS   not-accessible
    STATUS       current
    DESCRIPTION
        "This identifies the collection type for this row entry.  Each
         collection will have the 'summary' data.  If the
         etsysIpSlaConfigDistributionCount is not zero, the collection
         will have a 'distribution' set of data.  If the
         etsysIpSlaConfigHistoryCollections is not zero, the collection
         will have a 'history' set of data.

         summary(1)      - The row entry data corresponds to the
                           cumulative statistics gathered during a test.
         distribution(2) - The row entry data corresponds to the
                           statistical distribution of the round-trip-
                           time data.
         history(3)      - The row entry data corresponds to a storage
                           history collection of data."
    ::= { etsysIpSlaCollectionEntry 1 }

etsysIpSlaCollectionIndex OBJECT-TYPE
    SYNTAX       Unsigned32
    MAX-ACCESS   not-accessible
    STATUS       current
    DESCRIPTION
        "A value that uniquely identifies a collection of data for the
         IP SLA entry."
    ::= { etsysIpSlaCollectionEntry 2 }

etsysIpSlaCollectionStartTime OBJECT-TYPE
    SYNTAX       Unsigned32
    MAX-ACCESS   read-only
    STATUS       current
    DESCRIPTION
        "The start time of the test for this collection of data.  This
         value is expressed in seconds since the Epoch (Jan 1, 1970)."
    ::= { etsysIpSlaCollectionEntry 3 }

etsysIpSlaCollectionNumPaths OBJECT-TYPE
    SYNTAX       Gauge32
    MAX-ACCESS   read-only
    STATUS       current
    DESCRIPTION
        "This is the total number of paths available to this collection
         of data."
    ::= { etsysIpSlaCollectionEntry 4 }

etsysIpslaCollectionNumHops OBJECT-TYPE
    SYNTAX       Gauge32
    MAX-ACCESS   read-only
    STATUS       current
    DESCRIPTION
        "This is the total number of hops per path in this collection of
         data."
    ::= { etsysIpSlaCollectionEntry 5 }


--
-- Enterasys IP SLA Path and Hop Table
--
etsysIpSlaPathTable OBJECT-TYPE
    SYNTAX       SEQUENCE OF EtsysIpSlaPathEntry
    MAX-ACCESS   not-accessible
    STATUS       current
    DESCRIPTION
        "This table provides the information for the path and hop
         data of an IP SLA entry."
    ::= { etsysIpSlaTables 4 }

etsysIpSlaPathEntry OBJECT-TYPE
    SYNTAX       EtsysIpSlaPathEntry
    MAX-ACCESS   not-accessible
    STATUS       current
    DESCRIPTION
        "An entry (conceptual row) in the etsysIpSlaPathTable."
    INDEX {
        etsysIpSlaConfigIndex,
        etsysIpSlaCollectionType,
        etsysIpSlaCollectionIndex,
        etsysIpSlaPathIndex,
        etsysIpSlaHopIndex
    }
    ::= { etsysIpSlaPathTable 1 }

EtsysIpSlaPathEntry ::= SEQUENCE {
    etsysIpSlaPathIndex                     Unsigned32,
    etsysIpSlaHopIndex                      Unsigned32,
    etsysIpSlaHopDestType                   InetAddressType,
    etsysIpSlaHopDestAddr                   InetAddress
}

etsysIpSlaPathIndex OBJECT-TYPE
    SYNTAX       Unsigned32
    MAX-ACCESS   not-accessible
    STATUS       current
    DESCRIPTION
        "This value represents a unique path discovered to reach the
         destination host identified by etsysIpSlaConfigDestAddr.

         A value of zero for this object and etsysIpSlaHopIndex represent
         the destination host."
    ::= { etsysIpSlaPathEntry 1 }

etsysIpSlaHopIndex OBJECT-TYPE
    SYNTAX       Unsigned32
    MAX-ACCESS   not-accessible
    STATUS       current
    DESCRIPTION
        "This value represents the nth-hop in the path to the
         destination host identified by etsysIpSlaConfigDestAddr.

         A value of zero for this object and etsysIpSlaPathIndex
         represent the destination host."
    ::= { etsysIpSlaPathEntry 2 }

etsysIpSlaHopDestType OBJECT-TYPE
    SYNTAX       InetAddressType
    MAX-ACCESS   read-only
    STATUS       current
    DESCRIPTION
        "The address family of the hop in the path."
    ::= { etsysIpSlaPathEntry 3 }

etsysIpSlaHopDestAddr OBJECT-TYPE
    SYNTAX       InetAddress
    MAX-ACCESS   read-only
    STATUS       current
    DESCRIPTION
        "The address of the hop in the path."
    ::= { etsysIpSlaPathEntry 4 }


--
-- Enterasys IP SLA Round Trip Time Data Table
--
etsysIpSlaRttDataTable OBJECT-TYPE
    SYNTAX       SEQUENCE OF EtsysIpSlaRttDataEntry
    MAX-ACCESS   not-accessible
    STATUS       current
    DESCRIPTION
        "This table provides the round-trip-time statistics data for
         the IP SLA entry."
    ::= { etsysIpSlaTables 5 }

etsysIpSlaRttDataEntry OBJECT-TYPE
    SYNTAX       EtsysIpSlaRttDataEntry
    MAX-ACCESS   not-accessible
    STATUS       current
    DESCRIPTION
        "An entry (conceptual row) in the etsysIpSlaRttDataTable."
    INDEX {
        etsysIpSlaConfigIndex,
        etsysIpSlaCollectionType,
        etsysIpSlaCollectionIndex,
        etsysIpSlaPathIndex,
        etsysIpSlaHopIndex,
        etsysIpSlaBucketIndex
    }
    ::= { etsysIpSlaRttDataTable 1 }

EtsysIpSlaRttDataEntry ::= SEQUENCE {
    etsysIpSlaBucketIndex                         Unsigned32,
    etsysIpSlaBucketTime                          Unsigned32,
    etsysIpSlaRttDataSamples                      Gauge32,
    etsysIpSlaRttDataMinDelay                     Gauge32,
    etsysIpSlaRttDataAvgDelay                     Gauge32,
    etsysIpSlaRttDataMaxDelay                     Gauge32,
    etsysIpSlaRttDataSum                          Gauge32,
    etsysIpSlaRttDataSumSquareLow                 Gauge32,
    etsysIpSlaRttDataSumSquareHigh                Gauge32,
    etsysIpSlaRttDataPktOutOfOrder                Gauge32,
    etsysIpSlaRttDataPktLateArrival               Gauge32,
    etsysIpSlaRttDataPktMissing                   Gauge32,
    etsysIpSlaRttDataPktIpTosMismatch             Gauge32,
    etsysIpSlaRttDataPktVlanPcpMismatch           Gauge32,
    etsysIpSlaRttDataTxErrors                     Gauge32
}

etsysIpSlaBucketIndex OBJECT-TYPE
    SYNTAX       Unsigned32
    MAX-ACCESS   not-accessible
    STATUS       current
    DESCRIPTION
        "A value that identifies a set of RTT data.  The value of this
         object is influenced by the etsysIpSlaCollectionType.

         If the collection type is 'summary', the value of this object is
         one.  There is only one RTT summary per data collection.

         If the collection type is 'distribution' the value of this
         object represents the distribution index.  There is an
         associated entry in the etsysIpSlaDistDataTable.

         If the collection type is 'history', the value of this object
         is in the range of one to etsysIpSlaConfigHistoryBuckets."
    ::= { etsysIpSlaRttDataEntry 1 }

etsysIpSlaBucketTime OBJECT-TYPE
    SYNTAX       Unsigned32
    MAX-ACCESS   read-only
    STATUS       current
    DESCRIPTION
        "The time the first RTT data was stored in the bucket.  This
         value is expressed in seconds since the Epoch (Jan 1, 1970)."
    ::= { etsysIpSlaRttDataEntry 2 }

etsysIpSlaRttDataSamples OBJECT-TYPE
    SYNTAX       Gauge32
    UNITS        "packets"
    MAX-ACCESS   read-only
    STATUS       current
    DESCRIPTION
        "The RTT samples that were successfully measured."
    ::= { etsysIpSlaRttDataEntry 3 }

etsysIpSlaRttDataMinDelay OBJECT-TYPE
    SYNTAX       Gauge32
    UNITS        "microseconds"
    MAX-ACCESS   read-only
    STATUS       current
    DESCRIPTION
        "The minimum RTT measurement from the successful samples."
    ::= { etsysIpSlaRttDataEntry 4 }

etsysIpSlaRttDataAvgDelay OBJECT-TYPE
    SYNTAX       Gauge32
    UNITS        "microseconds"
    MAX-ACCESS   read-only
    STATUS       current
    DESCRIPTION
        "The average RTT calculated from the sum of the successful
         samples."
    ::= { etsysIpSlaRttDataEntry 5 }

etsysIpSlaRttDataMaxDelay OBJECT-TYPE
    SYNTAX       Gauge32
    UNITS        "microseconds"
    MAX-ACCESS   read-only
    STATUS       current
    DESCRIPTION
        "The maximum RTT measurement from the successful samples."
    ::= { etsysIpSlaRttDataEntry 6 }

etsysIpSlaRttDataSum OBJECT-TYPE
    SYNTAX       Gauge32
    UNITS        "microseconds"
    MAX-ACCESS   read-only
    STATUS       current
    DESCRIPTION
        "The summation of the successful RTT samples."
    ::= { etsysIpSlaRttDataEntry 7 }

etsysIpSlaRttDataSumSquareLow OBJECT-TYPE
    SYNTAX       Gauge32
    UNITS        "microseconds"
    MAX-ACCESS   read-only
    STATUS       current
    DESCRIPTION
        "The low 32 bits of the sum of squares of the successful RTT
         samples."
    ::= { etsysIpSlaRttDataEntry 8 }

etsysIpSlaRttDataSumSquareHigh OBJECT-TYPE
    SYNTAX       Gauge32
    UNITS        "microseconds"
    MAX-ACCESS   read-only
    STATUS       current
    DESCRIPTION
        "The high 32 bits of the sum of squares of the successful RTT
         samples."
    ::= { etsysIpSlaRttDataEntry 9 }

etsysIpSlaRttDataPktOutOfOrder OBJECT-TYPE
    SYNTAX       Gauge32
    UNITS        "packets"
    MAX-ACCESS   read-only
    STATUS       current
    DESCRIPTION
        "The number of packets that arrived out of order.  The RTT for
         these packets are not included in any calculations."
    ::= { etsysIpSlaRttDataEntry 10 }

etsysIpSlaRttDataPktLateArrival OBJECT-TYPE
    SYNTAX       Gauge32
    UNITS        "packets"
    MAX-ACCESS   read-only
    STATUS       current
    DESCRIPTION
        "The number of packets that arrived late.  The RTT for these
         packets are not included in any calculations."
    ::= { etsysIpSlaRttDataEntry 11 }

etsysIpSlaRttDataPktMissing OBJECT-TYPE
    SYNTAX       Gauge32
    UNITS        "packets"
    MAX-ACCESS   read-only
    STATUS       current
    DESCRIPTION
        "The number of packets lost."
    ::= { etsysIpSlaRttDataEntry 12 }

etsysIpSlaRttDataPktIpTosMismatch OBJECT-TYPE
    SYNTAX       Gauge32
    UNITS        "packets"
    MAX-ACCESS   read-only
    STATUS       current
    DESCRIPTION
        "The number of reply packets whose IP TOS field mismatched the
         value in the request."
    ::= { etsysIpSlaRttDataEntry 13 }

etsysIpSlaRttDataPktVlanPcpMismatch OBJECT-TYPE
    SYNTAX       Gauge32
    UNITS        "packets"
    MAX-ACCESS   read-only
    STATUS       current
    DESCRIPTION
        "The number of reply packets whose VLAN PCP field mismatched
         the value in the request."
    ::= { etsysIpSlaRttDataEntry 14 }

etsysIpSlaRttDataTxErrors OBJECT-TYPE
    SYNTAX       Gauge32
    MAX-ACCESS   read-only
    STATUS       current
    DESCRIPTION
        "The number transmissions errors."
    ::= { etsysIpSlaRttDataEntry 15 }


--
-- Enterasys IP SLA Packet Delay Variation Data Table
--
etsysIpSlaPdvDataTable OBJECT-TYPE
    SYNTAX       SEQUENCE OF EtsysIpSlaPdvDataEntry
    MAX-ACCESS   not-accessible
    STATUS       current
    DESCRIPTION
        "This table provides the packet delay variation (jitter)
         data for the IP SLA entry."
    ::= { etsysIpSlaTables 6 }

etsysIpSlaPdvDataEntry OBJECT-TYPE
    SYNTAX       EtsysIpSlaPdvDataEntry
    MAX-ACCESS   not-accessible
    STATUS       current
    DESCRIPTION
        "An entry (conceptual row) in the etsysIpSlaPdvDataTable."
    INDEX {
        etsysIpSlaConfigIndex,
        etsysIpSlaCollectionType,
        etsysIpSlaCollectionIndex,
        etsysIpSlaPathIndex,
        etsysIpSlaHopIndex,
        etsysIpSlaBucketIndex
    }
    ::= { etsysIpSlaPdvDataTable 1 }

EtsysIpSlaPdvDataEntry ::= SEQUENCE {
    etsysIpSlaPdvDataSamples                      Gauge32,
    etsysIpSlaPdvDataMinPositiveSD                Gauge32,
    etsysIpSlaPdvDataMaxPositiveSD                Gauge32,
    etsysIpSlaPdvDataNumPositiveSD                Gauge32,
    etsysIpSlaPdvDataSumPositiveSD                Gauge32,
    etsysIpSlaPdvDataSumSquarePositiveSD          Gauge32,
    etsysIpSlaPdvDataMinNegativeSD                Gauge32,
    etsysIpSlaPdvDataMaxNegativeSD                Gauge32,
    etsysIpSlaPdvDataNumNegativeSD                Gauge32,
    etsysIpSlaPdvDataSumNegativeSD                Gauge32,
    etsysIpSlaPdvDataSumSquareNegativeSD          Gauge32,
    etsysIpSlaPdvDataMinPositiveDS                Gauge32,
    etsysIpSlaPdvDataMaxPositiveDS                Gauge32,
    etsysIpSlaPdvDataNumPositiveDS                Gauge32,
    etsysIpSlaPdvDataSumPositiveDS                Gauge32,
    etsysIpSlaPdvDataSumSquarePositiveDS          Gauge32,
    etsysIpSlaPdvDataMinNegativeDS                Gauge32,
    etsysIpSlaPdvDataMaxNegativeDS                Gauge32,
    etsysIpSlaPdvDataNumNegativeDS                Gauge32,
    etsysIpSlaPdvDataSumNegativeDS                Gauge32,
    etsysIpSlaPdvDataSumSquareNegativeDS          Gauge32,
    etsysIpSlaPdvDataNumOneWaySD                  Gauge32,
    etsysIpSlaPdvDataMinOneWaySD                  Gauge32,
    etsysIpSlaPdvDataMaxOneWaySD                  Gauge32,
    etsysIpSlaPdvDataSumOneWaySD                  Gauge32,
    etsysIpSlaPdvDataSumSquareOneWaySD            Gauge32,
    etsysIpSlaPdvDataNumOneWayDS                  Gauge32,
    etsysIpSlaPdvDataMinOneWayDS                  Gauge32,
    etsysIpSlaPdvDataMaxOneWayDS                  Gauge32,
    etsysIpSlaPdvDataSumOneWayDS                  Gauge32,
    etsysIpSlaPdvDataSumSquareOneWayDS            Gauge32
}

etsysIpSlaPdvDataSamples OBJECT-TYPE
    SYNTAX       Gauge32
    MAX-ACCESS   read-only
    STATUS       current
    DESCRIPTION
        "The PDV samples that were successfully measured."
    ::= { etsysIpSlaPdvDataEntry 1 }

etsysIpSlaPdvDataMinPositiveSD OBJECT-TYPE
    SYNTAX       Gauge32
    MAX-ACCESS   read-only
    STATUS       current
    DESCRIPTION
        "The minimum PDV of all positive values for packets sent from
         the source to the destination."
    ::= { etsysIpSlaPdvDataEntry 2 }

etsysIpSlaPdvDataMaxPositiveSD OBJECT-TYPE
    SYNTAX       Gauge32
    MAX-ACCESS   read-only
    STATUS       current
    DESCRIPTION
        "The maximum PDV of all positive values for packets sent from
         the source to the destination."
    ::= { etsysIpSlaPdvDataEntry 3 }

etsysIpSlaPdvDataNumPositiveSD OBJECT-TYPE
    SYNTAX       Gauge32
    MAX-ACCESS   read-only
    STATUS       current
    DESCRIPTION
        "The total number of positive PDV values for packets sent from
         the source to the destination."
    ::= { etsysIpSlaPdvDataEntry 4 }

etsysIpSlaPdvDataSumPositiveSD OBJECT-TYPE
    SYNTAX       Gauge32
    MAX-ACCESS   read-only
    STATUS       current
    DESCRIPTION
        "The sum of the positive PDV values for packets sent from the
         source to the destination."
    ::= { etsysIpSlaPdvDataEntry 5 }

etsysIpSlaPdvDataSumSquarePositiveSD OBJECT-TYPE
    SYNTAX       Gauge32
    MAX-ACCESS   read-only
    STATUS       current
    DESCRIPTION
        "The sum of the squared positive PDV values for packets sent
         from the source to the destination."
    ::= { etsysIpSlaPdvDataEntry 6 }

etsysIpSlaPdvDataMinNegativeSD OBJECT-TYPE
    SYNTAX       Gauge32
    MAX-ACCESS   read-only
    STATUS       current
    DESCRIPTION
        "The negative PDV values are stored as absolute values.  The
         value of this object is the minimum value from the set of
         absolute values for packets sent from the source to the
         destination."
    ::= { etsysIpSlaPdvDataEntry 7 }

etsysIpSlaPdvDataMaxNegativeSD OBJECT-TYPE
    SYNTAX       Gauge32
    MAX-ACCESS   read-only
    STATUS       current
    DESCRIPTION
        "The negative PDV values are stored as absolute values.  The
         value of this object is the maximum value from the set of
         absolute values for packets sent from the source to the
         destination."
    ::= { etsysIpSlaPdvDataEntry 8 }

etsysIpSlaPdvDataNumNegativeSD OBJECT-TYPE
    SYNTAX       Gauge32
    MAX-ACCESS   read-only
    STATUS       current
    DESCRIPTION
        "The total number of negative PDV values for packets sent from
         the source to the destination."
    ::= { etsysIpSlaPdvDataEntry 9 }

etsysIpSlaPdvDataSumNegativeSD OBJECT-TYPE
    SYNTAX       Gauge32
    MAX-ACCESS   read-only
    STATUS       current
    DESCRIPTION
        "The sum of the negative PDV values for packets sent from the
         source to the destination.  The absolute value is returned."
    ::= { etsysIpSlaPdvDataEntry 10 }

etsysIpSlaPdvDataSumSquareNegativeSD OBJECT-TYPE
    SYNTAX       Gauge32
    MAX-ACCESS   read-only
    STATUS       current
    DESCRIPTION
        "The sum of the squared negative PDV values for packets sent
         from the source to the destination."
    ::= { etsysIpSlaPdvDataEntry 11 }

etsysIpSlaPdvDataMinPositiveDS OBJECT-TYPE
    SYNTAX       Gauge32
    MAX-ACCESS   read-only
    STATUS       current
    DESCRIPTION
        "The minimum PDV of all positive values for packets sent from
         the destination to the source."
    ::= { etsysIpSlaPdvDataEntry 12 }

etsysIpSlaPdvDataMaxPositiveDS OBJECT-TYPE
    SYNTAX       Gauge32
    MAX-ACCESS   read-only
    STATUS       current
    DESCRIPTION
        "The maximum PDV of all positive values for packets sent from
         the destination to the source."
    ::= { etsysIpSlaPdvDataEntry 13 }

etsysIpSlaPdvDataNumPositiveDS OBJECT-TYPE
    SYNTAX       Gauge32
    MAX-ACCESS   read-only
    STATUS       current
    DESCRIPTION
        "The total number of positive PDV values for packets sent from
         the destination to the source."
    ::= { etsysIpSlaPdvDataEntry 14 }

etsysIpSlaPdvDataSumPositiveDS OBJECT-TYPE
    SYNTAX       Gauge32
    MAX-ACCESS   read-only
    STATUS       current
    DESCRIPTION
        "The sum of the positive PDV values for packets sent from the
         destination to the source."
    ::= { etsysIpSlaPdvDataEntry 15 }

etsysIpSlaPdvDataSumSquarePositiveDS OBJECT-TYPE
    SYNTAX       Gauge32
    MAX-ACCESS   read-only
    STATUS       current
    DESCRIPTION
        "The sum of the squared positive PDV values for packets sent
         from the destination to the source."
    ::= { etsysIpSlaPdvDataEntry 16 }

etsysIpSlaPdvDataMinNegativeDS OBJECT-TYPE
    SYNTAX       Gauge32
    MAX-ACCESS   read-only
    STATUS       current
    DESCRIPTION
        "The negative PDV values are stored as absolute values.  The
         value of this object is the minimum value from the set of
         absolute values for packets sent from the destination to the
         source."
    ::= { etsysIpSlaPdvDataEntry 17 }

etsysIpSlaPdvDataMaxNegativeDS OBJECT-TYPE
    SYNTAX       Gauge32
    MAX-ACCESS   read-only
    STATUS       current
    DESCRIPTION
        "The negative PDV values are stored as absolute values.  The
         value of this object is the maximum value from the set of
         absolute values for packets sent from the destination to the
         source."
    ::= { etsysIpSlaPdvDataEntry 18 }

etsysIpSlaPdvDataNumNegativeDS OBJECT-TYPE
    SYNTAX       Gauge32
    MAX-ACCESS   read-only
    STATUS       current
    DESCRIPTION
        "The total number of negative PDV values for packets sent from
         the destination to the source."
    ::= { etsysIpSlaPdvDataEntry 19 }

etsysIpSlaPdvDataSumNegativeDS OBJECT-TYPE
    SYNTAX       Gauge32
    MAX-ACCESS   read-only
    STATUS       current
    DESCRIPTION
        "The sum of the negative PDV values for packets sent from the
         destination to the source.  The absolute value is returned."
    ::= { etsysIpSlaPdvDataEntry 20 }

etsysIpSlaPdvDataSumSquareNegativeDS OBJECT-TYPE
    SYNTAX       Gauge32
    MAX-ACCESS   read-only
    STATUS       current
    DESCRIPTION
        "The sum of the squared negative PDV values for packets sent
         from the destination to the source."
    ::= { etsysIpSlaPdvDataEntry 21 }

etsysIpSlaPdvDataNumOneWaySD OBJECT-TYPE
    SYNTAX       Gauge32
    MAX-ACCESS   read-only
    STATUS       current
    DESCRIPTION
        "The total number of one-way delay values for packets sent from
         the source to the destination."
    ::= { etsysIpSlaPdvDataEntry 22 }

etsysIpSlaPdvDataMinOneWaySD OBJECT-TYPE
    SYNTAX       Gauge32
    MAX-ACCESS   read-only
    STATUS       current
    DESCRIPTION
        "The minimum one-way delay value for packets sent from the
         source to the destination."
    ::= { etsysIpSlaPdvDataEntry 23 }

etsysIpSlaPdvDataMaxOneWaySD OBJECT-TYPE
    SYNTAX       Gauge32
    MAX-ACCESS   read-only
    STATUS       current
    DESCRIPTION
        "The maximum one-way delay value for packets sent from the
         source to the destination."
    ::= { etsysIpSlaPdvDataEntry 24 }

etsysIpSlaPdvDataSumOneWaySD OBJECT-TYPE
    SYNTAX       Gauge32
    MAX-ACCESS   read-only
    STATUS       current
    DESCRIPTION
        "The sum of the one-way delays for packets sent from the source
         to the destination."
    ::= { etsysIpSlaPdvDataEntry 25 }

etsysIpSlaPdvDataSumSquareOneWaySD OBJECT-TYPE
    SYNTAX       Gauge32
    MAX-ACCESS   read-only
    STATUS       current
    DESCRIPTION
        "The sum of squares of the one-way delays for packets sent from
         the source to the destination."
    ::= { etsysIpSlaPdvDataEntry 26 }

etsysIpSlaPdvDataNumOneWayDS OBJECT-TYPE
    SYNTAX       Gauge32
    MAX-ACCESS   read-only
    STATUS       current
    DESCRIPTION
        "The total number of one-way delay values for packets sent from
         the destination to the source."
    ::= { etsysIpSlaPdvDataEntry 27 }

etsysIpSlaPdvDataMinOneWayDS OBJECT-TYPE
    SYNTAX       Gauge32
    MAX-ACCESS   read-only
    STATUS       current
    DESCRIPTION
        "The minimum one-way delay value for packets sent from the
         destination to the source."
    ::= { etsysIpSlaPdvDataEntry 28 }

etsysIpSlaPdvDataMaxOneWayDS OBJECT-TYPE
    SYNTAX       Gauge32
    MAX-ACCESS   read-only
    STATUS       current
    DESCRIPTION
        "The maximum one-way delay value for packets sent from the
         destination to the source."
    ::= { etsysIpSlaPdvDataEntry 29 }

etsysIpSlaPdvDataSumOneWayDS OBJECT-TYPE
    SYNTAX       Gauge32
    MAX-ACCESS   read-only
    STATUS       current
    DESCRIPTION
        "The sum of the one-way delays for packets sent from the
         destination to the source."
    ::= { etsysIpSlaPdvDataEntry 30 }

etsysIpSlaPdvDataSumSquareOneWayDS OBJECT-TYPE
    SYNTAX       Gauge32
    MAX-ACCESS   read-only
    STATUS       current
    DESCRIPTION
        "The sum of squares of the one-way delays for packets sent from
         the destination to the source."
    ::= { etsysIpSlaPdvDataEntry 31 }


--
-- Enterasys IP SLA Distribution Data Table
--
etsysIpSlaDistDataTable OBJECT-TYPE
    SYNTAX       SEQUENCE OF EtsysIpSlaDistDataEntry
    MAX-ACCESS   not-accessible
    STATUS       current
    DESCRIPTION
        "This table provides the packet distribution data for the IP
         SLA entries."
    ::= { etsysIpSlaTables 7 }

etsysIpSlaDistDataEntry OBJECT-TYPE
    SYNTAX       EtsysIpSlaDistDataEntry
    MAX-ACCESS   not-accessible
    STATUS       current
    DESCRIPTION
        "An entry (conceptual row) in the etsysIpSlaDistDataTable."
    INDEX {
        etsysIpSlaConfigIndex,
        etsysIpSlaCollectionType,
        etsysIpSlaCollectionIndex,
        etsysIpSlaPathIndex,
        etsysIpSlaHopIndex,
        etsysIpSlaBucketIndex
    }
    ::= { etsysIpSlaDistDataTable 1 }

EtsysIpSlaDistDataEntry ::= SEQUENCE {
    etsysIpSlaDistMinRange                        Unsigned32,
    etsysIpSlaDistMaxRange                        Unsigned32
}

etsysIpSlaDistMinRange OBJECT-TYPE
    SYNTAX       Unsigned32
    UNITS        "milliseconds"
    MAX-ACCESS   read-only
    STATUS       current
    DESCRIPTION
        "This is the lower bound value for this statistical distribution
         segment.  The etsysIpSlaConfigDistributionInterval is used to
         determine this value."
    ::= { etsysIpSlaDistDataEntry 1 }

etsysIpSlaDistMaxRange OBJECT-TYPE
    SYNTAX       Unsigned32
    UNITS        "milliseconds"
    MAX-ACCESS   read-only
    STATUS       current
    DESCRIPTION
        "This is the upper bound value for this statistical distribution
         segment.  The etsysIpSlaConfigDistributionInterval is used to
         determine this value."
    ::= { etsysIpSlaDistDataEntry 2 }


-- -------------------------------------------------------------
-- Conformance Information
-- -------------------------------------------------------------

etsysIpSlaConformance OBJECT IDENTIFIER ::= { etsysIpSlaMIB 2 }

etsysIpSlaGroups OBJECT IDENTIFIER ::= { etsysIpSlaConformance 1 }
etsysIpSlaCompliances OBJECT IDENTIFIER ::= { etsysIpSlaConformance 2 }

-- -------------------------------------------------------------
-- Units of conformance
-- -------------------------------------------------------------

etsysIpSlaGlobalGroup OBJECT-GROUP
    OBJECTS {
        etsysIpSlaMaxEntries,
        etsysIpSlaEntriesInUse,
        etsysIpSlaMaxDataEntries,
        etsysIpSlaDataEntriesInUse
    }
    STATUS      current
    DESCRIPTION
        "This group defines information pertaining to the global
         resources used by the Enterasys IP SLA functionality."
    ::= { etsysIpSlaGroups 1 }

etsysIpSlaConfigGroup OBJECT-GROUP
    OBJECTS {
        etsysIpSlaConfigType,
        etsysIpSlaConfigDestType,
        etsysIpSlaConfigDestAddr,
        etsysIpSlaConfigDestPort,
        etsysIpSlaConfigProbeName,
        etsysIpSlaConfigPathCount,
        etsysIpSlaConfigHopCount,
        etsysIpSlaConfigHistoryCollections,
        etsysIpSlaConfigHistoryBuckets,
        etsysIpSlaConfigHistoryBucketType,
        etsysIpSlaConfigHistorySamples,
        etsysIpSlaConfigHistoryInterval,
        etsysIpSlaConfigHistoryAgeout,
        etsysIpSlaConfigHistoryWrap,
        etsysIpSlaConfigDistributionCount,
        etsysIpSlaConfigDistributionInterval,
        etsysIpSlaConfigStatisticsCollections,
        etsysIpSlaConfigStatus,
        etsysIpSlaScheduleStartTime,
        etsysIpSlaScheduleRecurrence,
        etsysIpSlaScheduleTestRepetitions,
        etsysIpSlaScheduleTestDuration,
        etsysIpSlaScheduleTestFrequency,
        etsysIpSlaScheduleTestState,
        etsysIpSlaScheduleTestStatus
    }
    STATUS      current
    DESCRIPTION
        "This group defines the objects used to configure and schedule
         the entries used by the Enterasys IP SLA functionality."
    ::= { etsysIpSlaGroups 2 }

etsysIpSlaCollectionGroup OBJECT-GROUP
    OBJECTS {
        etsysIpSlaCollectionStartTime,
        etsysIpSlaCollectionNumPaths,
        etsysIpslaCollectionNumHops
    }
    STATUS      current
    DESCRIPTION
        "This group defines the objects required to support the data
         collections for an IP SLA entry."
    ::= { etsysIpSlaGroups 3 }

etsysIpSlaPathGroup OBJECT-GROUP
    OBJECTS {
        etsysIpSlaHopDestType,
        etsysIpSlaHopDestAddr
    }
    STATUS      current
    DESCRIPTION
        "This group defines the path and hop objects used by the IP SLA
         entries."
    ::= { etsysIpSlaGroups 4 }

etsysIpSlaRttGroup OBJECT-GROUP
    OBJECTS {
        etsysIpSlaBucketTime,
        etsysIpSlaRttDataSamples,
        etsysIpSlaRttDataMinDelay,
        etsysIpSlaRttDataAvgDelay,
        etsysIpSlaRttDataMaxDelay,
        etsysIpSlaRttDataSum,
        etsysIpSlaRttDataSumSquareLow,
        etsysIpSlaRttDataSumSquareHigh,
        etsysIpSlaRttDataPktOutOfOrder,
        etsysIpSlaRttDataPktLateArrival,
        etsysIpSlaRttDataPktMissing,
        etsysIpSlaRttDataPktIpTosMismatch,
        etsysIpSlaRttDataPktVlanPcpMismatch,
        etsysIpSlaRttDataTxErrors
    }
    STATUS      current
    DESCRIPTION
        "This group defines the round-trip-time data objects defined
         for the IP SLA entries used by the Enterasys IP SLA
         functionality."
    ::= { etsysIpSlaGroups 5 }

etsysIpSlaPdvGroup OBJECT-GROUP
    OBJECTS {
        etsysIpSlaPdvDataSamples,
        etsysIpSlaPdvDataMinPositiveSD,
        etsysIpSlaPdvDataMaxPositiveSD,
        etsysIpSlaPdvDataNumPositiveSD,
        etsysIpSlaPdvDataSumPositiveSD,
        etsysIpSlaPdvDataSumSquarePositiveSD,
        etsysIpSlaPdvDataMinNegativeSD,
        etsysIpSlaPdvDataMaxNegativeSD,
        etsysIpSlaPdvDataNumNegativeSD,
        etsysIpSlaPdvDataSumNegativeSD,
        etsysIpSlaPdvDataSumSquareNegativeSD,
        etsysIpSlaPdvDataMinPositiveDS,
        etsysIpSlaPdvDataMaxPositiveDS,
        etsysIpSlaPdvDataNumPositiveDS,
        etsysIpSlaPdvDataSumPositiveDS,
        etsysIpSlaPdvDataSumSquarePositiveDS,
        etsysIpSlaPdvDataMinNegativeDS,
        etsysIpSlaPdvDataMaxNegativeDS,
        etsysIpSlaPdvDataNumNegativeDS,
        etsysIpSlaPdvDataSumNegativeDS,
        etsysIpSlaPdvDataSumSquareNegativeDS,
        etsysIpSlaPdvDataNumOneWaySD,
        etsysIpSlaPdvDataMinOneWaySD,
        etsysIpSlaPdvDataMaxOneWaySD,
        etsysIpSlaPdvDataSumOneWaySD,
        etsysIpSlaPdvDataSumSquareOneWaySD,
        etsysIpSlaPdvDataNumOneWayDS,
        etsysIpSlaPdvDataMinOneWayDS,
        etsysIpSlaPdvDataMaxOneWayDS,
        etsysIpSlaPdvDataSumOneWayDS,
        etsysIpSlaPdvDataSumSquareOneWayDS
    }
    STATUS      current
    DESCRIPTION
        "This group defines the packet delay variation (jitter) data
         objects defined for the IP SLA entries used by the Enterasys IP
         SLA functionality."
    ::= { etsysIpSlaGroups 6 }

etsysIpSlaDistribGroup OBJECT-GROUP
    OBJECTS {
        etsysIpSlaDistMinRange,
        etsysIpSlaDistMaxRange
    }
    STATUS      current
    DESCRIPTION
        "This group defines the statistical distribution range data."
    ::= { etsysIpSlaGroups 7 }


-- -------------------------------------------------------------
-- Compliance statements
-- -------------------------------------------------------------

etsysIpSlaCompliance MODULE-COMPLIANCE
    STATUS      current
    DESCRIPTION
        "The compliance statement for devices that support
         etsysIpSla."

    MODULE
        MANDATORY-GROUPS {
            etsysIpSlaConfigGroup,
            etsysIpSlaCollectionGroup,
            etsysIpSlaPathGroup,
            etsysIpSlaRttGroup
        }

        -- -----------------------------------------------------
        -- OBJECTS
        -- -----------------------------------------------------
        OBJECT       etsysIpSlaConfigType
        SYNTAX       INTEGER { echo(1) }
        WRITE-SYNTAX INTEGER { echo(1) }
        DESCRIPTION
            "Support for jitter is not required."

        OBJECT       etsysIpSlaConfigHistoryBucketType
        SYNTAX       INTEGER { static(1) }
        WRITE-SYNTAX INTEGER { static(1) }
        DESCRIPTION
            "Support for timed is not required."

        OBJECT       etsysIpSlaConfigStatus
        SYNTAX       RowStatus { active(1) }
        WRITE-SYNTAX RowStatus { createAndGo(4), destroy(6) }
        DESCRIPTION
            "Support for createAndWait and notInService is not required."

        -- -----------------------------------------------------
        -- GROUPS
        -- -----------------------------------------------------
        GROUP etsysIpSlaGlobalGroup
        DESCRIPTION
            "The etsysIpSlaGlobalGroup is not mandatory but is
             RECOMMENDED."

        GROUP etsysIpSlaPdvGroup
        DESCRIPTION
            "The etsysIpSlaPdvGroup is mandatory only for the entities
             implementing the packet delay variation feature with the IP
             SLA functionality."

        GROUP etsysIpSlaDistribGroup
        DESCRIPTION
            "The etsysIpSlaDistribGroup is mandatory only for entities
             that support statistical distribution of the round-trip-time
             data."

    ::= { etsysIpSlaCompliances 1 }

END
