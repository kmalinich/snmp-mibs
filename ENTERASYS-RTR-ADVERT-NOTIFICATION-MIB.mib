ENTERASYS-RTR-ADVERT-NOTIFICATION-MIB DEFINITIONS ::= BEGIN

--  enterasys-rtr-advert-notification-mib.txt

--  This module provides authoritative definitions for Enterasys
--  Networks' router advertisement notifications.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright May, 2011 Enterasys Networks, Inc.

IMPORTS
    MODULE-IDENTITY, OBJECT-TYPE, NOTIFICATION-TYPE
        FROM SNMPv2-SMI
    TEXTUAL-CONVENTION, DisplayString, TruthValue
        FROM SNMPv2-TC
    MODULE-COMPLIANCE, OBJECT-GROUP
        FROM SNMPv2-CONF
    SnmpAdminString
        FROM SNMP-FRAMEWORK-MIB
    ifName
        FROM IF-MIB
    InetAddressType, InetAddress
        FROM INET-ADDRESS-MIB
    etsysModules
        FROM ENTERASYS-MIB-NAMES;

etsysRtrAdvertNotificationMIB MODULE-IDENTITY
    LAST-UPDATED "201105131347Z"  -- Fri May 13 13:47 UTC 2011
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP MIB under
         the Enterasys Networks enterprise OID pertaining to
         router advertisement notifications.

         This MIB was designed to be used for monitoring router
         events that have occurred in the system related to router
         advertisements."

    REVISION    "201105131347Z"  -- Fri May 13 13:47 UTC 2011
    DESCRIPTION "The initial version of this MIB module"

    ::= { etsysModules 82 }

-- -------------------------------------------------------------
-- branches in the ENTERASYS-RTR-ADVERT-NOTIFICATION MIB
-- -------------------------------------------------------------

etsysRtrAdvertNotificationObjects   OBJECT IDENTIFIER
        ::= { etsysRtrAdvertNotificationMIB 1 }

etsysRtrAdvertConfigBranch          OBJECT IDENTIFIER
        ::= { etsysRtrAdvertNotificationObjects 0 }

etsysRtrAdvertInformationBranch     OBJECT IDENTIFIER
        ::= { etsysRtrAdvertNotificationObjects 1 }

etsysRtrAdvertNotificationBranch    OBJECT IDENTIFIER
        ::= { etsysRtrAdvertNotificationObjects 2 }

-- -------------------------------------------------------------
-- Objects in the etsysRtrAdvertConfigBranch
-- -------------------------------------------------------------

etsysRtrAdvertInconsistentEnabled OBJECT-TYPE
    SYNTAX      TruthValue
    MAX-ACCESS  read-write
    STATUS      current
    DESCRIPTION
        "If this object is set to true (1) a trap will be sent when
         an inconsistent router advertisement is processed."
    DEFVAL { false }
    ::= { etsysRtrAdvertConfigBranch 1 }

-- -------------------------------------------------------------
-- Objects in the etsysRtrAdvertInformationBranch
-- -------------------------------------------------------------

etsysRtrAdvertInetAddrType OBJECT-TYPE
    SYNTAX      InetAddressType
    MAX-ACCESS  accessible-for-notify
    STATUS      current
    DESCRIPTION
        "A value that represents a type of Internet address specified
         by etsysRtrAdvertInetAddress."
    ::= { etsysRtrAdvertInformationBranch 1 }

etsysRtrAdvertInetAddress  OBJECT-TYPE
    SYNTAX      InetAddress
    MAX-ACCESS  accessible-for-notify
    STATUS      current
    DESCRIPTION
        "The Internet Address of the router being advertised.
         The format of this object is defined by the
         etsysRtrAdvertInetAddrType object."
    ::= { etsysRtrAdvertInformationBranch 2 }

etsysRtrAdvertUserData     OBJECT-TYPE
    SYNTAX      SnmpAdminString
    MAX-ACCESS  accessible-for-notify
    STATUS      current
    DESCRIPTION
        "The data pertinent to the router advertisement notification
         being sent (i.e. mtu, hop-limit, etc.)."
    ::= { etsysRtrAdvertInformationBranch 3 }

-- -------------------------------------------------------------
-- Objects in the etsysRtrAdvertInformationBranch
-- -------------------------------------------------------------

etsysRtrAdvertInconsistent NOTIFICATION-TYPE
    OBJECTS     {
                  etsysRtrAdvertInetAddrType,
                  etsysRtrAdvertInetAddress,
                  ifName,
                  etsysRtrAdvertUserData
                }
    STATUS      current
    DESCRIPTION
        "Inconsistent router advertisement notification.  The device
         will send this notification when an inconsistent router
         advertisement is received from another router."
    ::= { etsysRtrAdvertNotificationBranch 1 }

-- -------------------------------------------------------------
-- Conformance Information
-- -------------------------------------------------------------

etsysRtrAdvertConformance
    OBJECT IDENTIFIER ::= { etsysRtrAdvertNotificationMIB 2 }

etsysRtrAdvertGroups
    OBJECT IDENTIFIER ::= { etsysRtrAdvertConformance 1 }

etsysRtrAdvertCompliances
    OBJECT IDENTIFIER ::= { etsysRtrAdvertConformance 2 }

-- -------------------------------------------------------------
-- Units of conformance
-- -------------------------------------------------------------

etsysRtrAdvertConfigGroup OBJECT-GROUP
    OBJECTS {
              etsysRtrAdvertInconsistentEnabled
            }
    STATUS current
    DESCRIPTION
        "A collection of objects providing basic instrumentation of
         router advertisement notifications."
    ::= { etsysRtrAdvertGroups 1 }

etsysRtrAdvertInformationGroup OBJECT-GROUP
    OBJECTS {
              etsysRtrAdvertInetAddrType,
              etsysRtrAdvertInetAddress,
              etsysRtrAdvertUserData
            }
    STATUS      current
    DESCRIPTION
        "A collection of objects providing router advertisement
         information."
    ::= { etsysRtrAdvertGroups 2 }

etsysRtrAdvertNotificationGroup NOTIFICATION-GROUP
    NOTIFICATIONS {
                    etsysRtrAdvertInconsistent
                  }
    STATUS      current
    DESCRIPTION
        "The router advertisement notifications."
    ::= { etsysRtrAdvertGroups 3 }

-- -------------------------------------------------------------
-- Compliance statements
-- -------------------------------------------------------------

etsysRtrAdvertCompliance MODULE-COMPLIANCE
    STATUS      current
    DESCRIPTION
        "The compliance statement for devices that support Enterasys
         router advertisement notifications."

    MODULE
        MANDATORY-GROUPS {
                           etsysRtrAdvertConfigGroup,
                           etsysRtrAdvertInformationGroup,
                           etsysRtrAdvertNotificationGroup
                         }

    ::= { etsysRtrAdvertCompliances 1 }

END
