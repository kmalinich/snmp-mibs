ENTERASYS-QUARANTINE-AGENT-MIB DEFINITIONS ::= BEGIN

--  enterasys-quarantine-agent-mib.txt
--
--  Part Number:
--
--

--  This module provides authoritative definitions for Enterasys
--  Networks' Quarantine Agent functionality.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February 2013 Enterasys Networks, Inc.

IMPORTS
    MODULE-IDENTITY, OBJECT-TYPE, Unsigned32
        FROM SNMPv2-SMI
    OBJECT-GROUP, MODULE-COMPLIANCE
        FROM SNMPv2-CONF
    EnabledStatus
        FROM P-BRIDGE-MIB
    etsysModules
        FROM ENTERASYS-MIB-NAMES
    ifIndex
        FROM IF-MIB;

etsysQuarantineAgentMIB MODULE-IDENTITY
    LAST-UPDATED "201302111857Z"  -- Mon Feb 11 15:57 UTC 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"

    DESCRIPTION
        "This MIB module defines a portion of the SNMP MIB under
         the Enterasys Networks enterprise OID pertaining to
         configuration of the Quarantine Agent on a device."

    REVISION    "201302111857Z"  -- Mon Feb 11 18:57 UTC 2013
    DESCRIPTION "Addition of Accounting enable and disable."

    REVISION    "201302111557Z"  -- Mon Feb 11 15:57 UTC 2013
    DESCRIPTION "OBJECT IDENTIFIER disambiguation."

    REVISION    "201301221532Z"  -- Tue Jan 22 15:32 UTC 2013
    DESCRIPTION "The initial version of this MIB module."

    ::= { etsysModules 93 }

-- -------------------------------------------------------------
-- MIB Objects
-- -------------------------------------------------------------

etsysQuarantineAgentBody
        OBJECT IDENTIFIER ::= { etsysQuarantineAgentMIB 2 }

etsysQuarantineAgentObjects
        OBJECT IDENTIFIER ::= { etsysQuarantineAgentBody 1 }

etsysQuarantineAgentSystem
        OBJECT IDENTIFIER ::= { etsysQuarantineAgentObjects 1 }

etsysQuarantineAgentPort
        OBJECT IDENTIFIER ::= { etsysQuarantineAgentObjects 2 }

-- -------------------------------------------------------------
-- etsysQuarantineAgentSystem Group
-- -------------------------------------------------------------

etsysQuarantineAgentSystemEnable OBJECT-TYPE
    SYNTAX      EnabledStatus
    MAX-ACCESS  read-write
    STATUS      current
    DESCRIPTION
        "When enabled(1), all objects in this MIB are fully active.
         When disabled(2), this object overrides all other object
         settings in this MIB without affecting their values."
    DEFVAL { disabled }
    ::= { etsysQuarantineAgentSystem 1 }

etsysQuarantineAgentSystemAccountEnable OBJECT-TYPE
    SYNTAX      EnabledStatus
    MAX-ACCESS  read-write
    STATUS      current
    DESCRIPTION
        "When enabled(1), RADIUS accounting start, interim and
         stop frames are sent to the configured RADIUS server(s).

         When disabled(2), accounting packets are not sent to
         the RADIUS server."
    DEFVAL { disabled }
    ::= { etsysQuarantineAgentSystem 2 }

-- -------------------------------------------------------------
-- etsysQuarantineAgentPort Group
-- -------------------------------------------------------------

etsysQuarantineAgentPortTable OBJECT-TYPE
    SYNTAX      SEQUENCE OF EtsysQuarantineAgentPortEntry
    MAX-ACCESS  not-accessible
    STATUS      current
    DESCRIPTION
        "A table containing configuration objects for each
         quarantine agent port. The configuration for
         each port in this table must be non-volatile."
    ::= { etsysQuarantineAgentPort 1 }

etsysQuarantineAgentPortEntry OBJECT-TYPE
    SYNTAX      EtsysQuarantineAgentPortEntry
    MAX-ACCESS  not-accessible
    STATUS      current
    DESCRIPTION
        "Each conceptual row provides control over all of the
         initial values used by each quarantine agent MAC on
         this port. Subsequent changes to rows in this table,
         except where noted, have no effect on existing quarantined
         sessions on this port."
    INDEX { ifIndex }
    ::= { etsysQuarantineAgentPortTable 1 }

EtsysQuarantineAgentPortEntry ::=
    SEQUENCE {
        etsysQuarantineAgentPortEnable                    EnabledStatus,
        etsysQuarantineAgentPortAuthenticationsAllowed    Unsigned32,
        etsysQuarantineAgentPortAuthenticationsAllocated  Unsigned32,
        etsysQuarantineAgentPortSessionTimeout            Unsigned32,
        etsysQuarantineAgentPortIdleTimeout               Unsigned32
    }

etsysQuarantineAgentPortEnable OBJECT-TYPE
    SYNTAX      EnabledStatus
    MAX-ACCESS  read-write
    STATUS      current
    DESCRIPTION
        "When set to enabled(1), a platform dependent triggering
         mechanism allows for quarantined sessions on this
         port.
         When disabled(2), quarantined sessions are disabled
         and all currently quarantined sessions or those in
         the process of being quarantined on this port are terminated."
    DEFVAL { disabled }
    ::= { etsysQuarantineAgentPortEntry 2 }

etsysQuarantineAgentPortAuthenticationsAllowed OBJECT-TYPE
    SYNTAX      Unsigned32
    MAX-ACCESS  read-only
    STATUS      current
    DESCRIPTION
        "The maximum number of concurrent quarantined sessions supported
         on this port on this module. The default value of this
         object is platform and resource dependent."
    ::= { etsysQuarantineAgentPortEntry 3 }

etsysQuarantineAgentPortAuthenticationsAllocated OBJECT-TYPE
    SYNTAX      Unsigned32
    MAX-ACCESS  read-write
    STATUS      current
    DESCRIPTION
        "The maximum number of quarantined sessions permitted on this
         port on this module. This value must be non-zero and be less
         than or equal to the value of
         etsysQuarantineAgentPortAuthenticationsAllowed.  Setting this
         object to a value less than the current number of quarantined
         sessions on this port prevents further quarantine agent
         provisioning, but has no affect on the current sessions."
    ::= { etsysQuarantineAgentPortEntry 4 }

etsysQuarantineAgentPortSessionTimeout OBJECT-TYPE
    SYNTAX       Unsigned32 (0|1..65535)
    UNITS        "seconds"
    MAX-ACCESS   read-write
    STATUS       current
    DESCRIPTION
        "The maximum number of seconds a quarantined session may last
         before termination of the session.  A value of zero indicates
         that the global etsysMultiAuthSessionTimeout value will be used."
    REFERENCE
        "RFC 2865, 'Remote Authentication Dial In User Service (RADIUS)',
         Section 5.27"
    DEFVAL { 0 }
    ::= { etsysQuarantineAgentPortEntry 5 }

etsysQuarantineAgentPortIdleTimeout OBJECT-TYPE
    SYNTAX       Unsigned32 (0|1..65535)
    UNITS        "seconds"
    MAX-ACCESS   read-write
    STATUS       current
    DESCRIPTION
        "The maximum number of consecutive seconds a quarantined
         session may be idle before termination of the session.  A
         value of zero indicates that the global
         etsysMultiAuthSessionTimeout value will be used."
    REFERENCE
        "RFC 2865, 'Remote Authentication Dial In User Service (RADIUS)',
         Section 5.28"
    DEFVAL { 0 }
    ::= { etsysQuarantineAgentPortEntry 6 }

-- -------------------------------------------------------------
-- Conformance Information
-- -------------------------------------------------------------

etsysQuarantineAgentConformance
        OBJECT IDENTIFIER ::= { etsysQuarantineAgentMIB 3 }

etsysQuarantineAgentGroups
        OBJECT IDENTIFIER ::= { etsysQuarantineAgentConformance 1 }

etsysQuarantineAgentCompliances
        OBJECT IDENTIFIER ::= { etsysQuarantineAgentConformance 2 }

-- -------------------------------------------------------------
-- Units of conformance
-- -------------------------------------------------------------

etsysQuarantineAgentSystemGroup OBJECT-GROUP
    OBJECTS {
        etsysQuarantineAgentSystemEnable
    }
    STATUS      deprecated
    DESCRIPTION
        "Global object controlling this feature.
         Global objects that affect how the credentials are
         presented to the authentication server."
    ::= { etsysQuarantineAgentGroups 1 }

etsysQuarantineAgentPortGroup OBJECT-GROUP
    OBJECTS {
        etsysQuarantineAgentPortEnable,
        etsysQuarantineAgentPortAuthenticationsAllowed,
        etsysQuarantineAgentPortAuthenticationsAllocated,
        etsysQuarantineAgentPortSessionTimeout,
        etsysQuarantineAgentPortIdleTimeout
    }
    STATUS      current
    DESCRIPTION
        "Objects describing the Quarantine Agent
         variables for each port."
    ::= { etsysQuarantineAgentGroups 2 }

etsysQuarantineAgentSystemGroup2 OBJECT-GROUP
    OBJECTS {
        etsysQuarantineAgentSystemEnable,
        etsysQuarantineAgentSystemAccountEnable
    }
    STATUS      current
    DESCRIPTION
        "Global object controlling this feature.
         Global objects that affect how the credentials are
         presented to the authentication server."
    ::= { etsysQuarantineAgentGroups 3 }

-- -------------------------------------------------------------
-- Compliance statements
-- -------------------------------------------------------------

etsysQuarantineAgentCompliance MODULE-COMPLIANCE
    STATUS      deprecated
    DESCRIPTION
        "The compliance statement for devices that support the
         Quarantine Agent."

    MODULE
       MANDATORY-GROUPS {
            etsysQuarantineAgentSystemGroup,
            etsysQuarantineAgentPortGroup
       }

       OBJECT      etsysQuarantineAgentSystemEnable
       SYNTAX      EnabledStatus
       MIN-ACCESS  read-only
       DESCRIPTION
           "Write access is not required. If read-only is selected,
            then the default value must be enabled(1)."

    ::= { etsysQuarantineAgentCompliances 1 }

etsysQuarantineAgentCompliance2 MODULE-COMPLIANCE
    STATUS      current
    DESCRIPTION
        "The compliance statement for devices that support the
         Quarantine Agent."

    MODULE
       MANDATORY-GROUPS {
            etsysQuarantineAgentSystemGroup2,
            etsysQuarantineAgentPortGroup
       }

       OBJECT      etsysQuarantineAgentSystemEnable
       SYNTAX      EnabledStatus
       MIN-ACCESS  read-only
       DESCRIPTION
           "Write access is not required. If read-only is selected,
            then the default value must be enabled(1)."

    ::= { etsysQuarantineAgentCompliances 2 }

END
