ENTERASYS-RIPv2-EXT-MIB DEFINITIONS ::= BEGIN

--  enterasys-ripv2-ext-mib.txt
--
--  Part Number:
--
--

--  This module provides authoritative definitions for Enterasys
--  Networks' RIPv2 protocol.  This module extends the RIPv2-MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2009 Enterasys Networks, Inc.

IMPORTS
    MODULE-IDENTITY, OBJECT-TYPE, Unsigned32, Counter32, Integer32
        FROM SNMPv2-SMI
    TEXTUAL-CONVENTION
        FROM SNMPv2-TC
    MODULE-COMPLIANCE, OBJECT-GROUP
        FROM SNMPv2-CONF
    etsysModules
        FROM ENTERASYS-MIB-NAMES;

etsysRip2ExtMIB MODULE-IDENTITY
    LAST-UPDATED "200902061711Z"  -- Fri Feb  6 17:11 UTC 2009
    ORGANIZATION "Enterasys Networks, Inc."
    CONTACT-INFO
        "Postal:  Enterasys Networks
                  50 Minuteman Rd.
                  Andover, MA 01810-1008
                  USA
         Phone:   +1 978 684 1000
         E-mail:  support@enterasys.com
         WWW:     http://www.enterasys.com"
    DESCRIPTION
        "This MIB module defines a portion of the SNMP MIB under
         the Enterasys Networks enterprise OID pertaining to
         the RIPv2 configuration

         This MIB was designed to be used for configuring the
         RIP-2 protocol parameters."

    REVISION     "200902061711Z"  -- Fri Feb  6 17:11 UTC 2009
    DESCRIPTION  "The initial version of this MIB module"
    ::= { etsysModules 66 }


-- -------------------------------------------------------------
-- Branches
-- -------------------------------------------------------------
etsysRip2ExtObjects  OBJECT IDENTIFIER ::= { etsysRip2ExtMIB 1 }
etsysRip2ExtGlobals  OBJECT IDENTIFIER ::= { etsysRip2ExtObjects 1 }

-- -------------------------------------------------------------
-- MIB Objects
-- -------------------------------------------------------------

etsysRip2ExtAdminStatus OBJECT-TYPE
    SYNTAX       INTEGER {
                     adminStatusUp(1),
                     adminStatusDown(2)
                 }
    MAX-ACCESS   read-write
    STATUS       current
    DESCRIPTION
       "The current administrative state of the RIP protocol.

       Setting this object to adminStatusUp turns on the RIP protocol,
       while setting it to adminStatusDown turns off the RIP protocol.
       When the object is set to adminStatusUp, it triggers the RIP
       process to begin normal operation by populating its routing
       table and sending/receiving routing updates.

       Setting this object to adminStatusDown turns off the RIP
       protocol.  This causes the etsysRip2ExtOperStatus object to
       change its state to operStatusGoingDown.  This has the effect of
       removing all of the RIP routes from the RIB."
    DEFVAL { adminStatusDown }
    ::= { etsysRip2ExtGlobals 1 }

etsysRip2ExtOperStatus OBJECT-TYPE
    SYNTAX       INTEGER {
                     operStatusUp(1),             -- active
                     operStatusDown(2),           -- inactive
                     operStatusGoingUp(3),        -- activating
                     operStatusGoingDown(4),      -- deactivating
                     operStatusActFailed(5)       -- activation failed
                 }
    MAX-ACCESS   read-only
    STATUS       current
    DESCRIPTION
        "The current operational state of the RIP Protocol.

        Changing the state of the etsysRip2ExtAdminStatus object may
        effect the state of this object.  If etsysRip2ExtAdminStatus is
        set to adminStatusDown, this object's status is changed to
        operStatusGoingDown.  Once the RIP process has finished
        cleaning up its routing table and freeing its resources, the
        status is changed to operStatusDown.

        If  etsysRip2ExtAdminStatus is set to adminStatusUp, this
        object's status is changed to operStatusGoingUp.  After RIP
        allocates its resources and begins operation, the status of
        this object changes to operStatusUp.

        If there are problems acquiring the resources needed to operate
        the RIP protocol, the status changes to operStatusActFailed."
    ::= { etsysRip2ExtGlobals 2 }

etsysRip2ExtMaxEcmpHops OBJECT-TYPE
    SYNTAX       Unsigned32 (1..2147483647)
    MAX-ACCESS   read-write
    STATUS       current
    DESCRIPTION
        "The maximum number of equal-cost next hops that RIP can program
        in the Routing Table Manager.

        Changing this value causes RIP to refresh all of its routes in
        the Routing Table Manager with the new maximum number of
        equal-cost next hops."
    DEFVAL { 4 }
    ::= { etsysRip2ExtGlobals 3 }

etsysRip2ExtRefreshInterval OBJECT-TYPE
    SYNTAX       Unsigned32 (1..2147483647)
    UNITS        "seconds"
    MAX-ACCESS   read-write
    STATUS       current
    DESCRIPTION
        "The frequency at which RIP sends periodic updates to all of its
        peers.

        A change to this value takes effect after the next periodic
        update is sent."
    DEFVAL { 30 }
    ::= { etsysRip2ExtGlobals 4 }

etsysRip2ExtTriggeredDelayMin OBJECT-TYPE
    SYNTAX       Unsigned32
    UNITS        "seconds"
    MAX-ACCESS   read-write
    STATUS       current
    DESCRIPTION
        "The lower bound of the random time period that RIP waits
        between sending Triggered Updates.

        A change to this value takes effect after the next Triggered
        Update is sent.

        This value MUST be less than etsysRip2ExtTriggeredDelayMax."
    DEFVAL { 1 }
    ::= { etsysRip2ExtGlobals 5 }

etsysRip2ExtTriggeredDelayMax OBJECT-TYPE
    SYNTAX       Unsigned32
    UNITS        "seconds"
    MAX-ACCESS   read-write
    STATUS       current
    DESCRIPTION
        "The upper bound of the random time period that RIP waits
        between sending Triggered Updates.

        A change to this value takes effect after the next Triggered
        Update is sent.

        This value MUST be greater than etsysRip2ExtTriggeredDelayMin."
    DEFVAL { 5 }
    ::= { etsysRip2ExtGlobals 6 }

etsysRip2ExtRouteCheckInterval OBJECT-TYPE
    SYNTAX       Unsigned32 (1..60)
    UNITS        "seconds"
    MAX-ACCESS   read-write
    STATUS       current
    DESCRIPTION
        "The frequency with which RIP checks the routing table for
        expired routes.

        A change to this value takes effect after the next scheduled
        route check."
    DEFVAL { 1 }
    ::= { etsysRip2ExtGlobals 7 }

etsysRip2ExtRouteExpiryInterval OBJECT-TYPE
    SYNTAX       Unsigned32 (1..255)
    MAX-ACCESS   read-write
    STATUS       current
    DESCRIPTION
        "The period from the point of the last refresh after which a
        route received from a peer times out and is marked as expired.

        This period is expressed as a multiple of the
        etsysRip2ExtRouteCheckInterval.

        A change to this value takes effect at the next scheduled
        route check."
    DEFVAL { 180 }
    ::= { etsysRip2ExtGlobals 8 }

etsysRip2ExtRouteFlushInterval OBJECT-TYPE
    SYNTAX       Unsigned32 (1..255)
    MAX-ACCESS   read-write
    STATUS       current
    DESCRIPTION
        "The period from the point of route expiry that a route is
        finally removed from the routing table, also known as the
        'garbage collection time'.

        This period is expressed as a multiple of the
        etsysRip2ExtRouteCheckInterval.

        A change to this value takes effect at the next scheduled
        route check."
    DEFVAL { 120 }
    ::= { etsysRip2ExtGlobals 9 }

-- -------------------------------------------------------------
-- Conformance Information
-- -------------------------------------------------------------

etsysRip2ExtConformance OBJECT IDENTIFIER ::= { etsysRip2ExtMIB 2 }

etsysRip2ExtGroups      OBJECT IDENTIFIER ::= { etsysRip2ExtConformance 1 }
etsysRip2ExtCompliances OBJECT IDENTIFIER ::= { etsysRip2ExtConformance 2 }

-- -------------------------------------------------------------
-- Units of conformance
-- -------------------------------------------------------------

etsysRip2ExtGlobalGroup OBJECT-GROUP
    OBJECTS {
            etsysRip2ExtAdminStatus,
            etsysRip2ExtOperStatus,
            etsysRip2ExtMaxEcmpHops,
            etsysRip2ExtRefreshInterval,
            etsysRip2ExtTriggeredDelayMin,
            etsysRip2ExtTriggeredDelayMax,
            etsysRip2ExtRouteCheckInterval,
            etsysRip2ExtRouteExpiryInterval,
            etsysRip2ExtRouteFlushInterval
    }
    STATUS  current
    DESCRIPTION
       "This group defines global controls for Enterasys RIPv2 systems."
    ::= { etsysRip2ExtGroups 1 }

-- -------------------------------------------------------------
-- Compliance statements
-- -------------------------------------------------------------

etsysRip2ExtCompliance MODULE-COMPLIANCE
    STATUS       current
    DESCRIPTION
        "The compliance statement for devices that support etsysRip2Ext."

    MODULE
        MANDATORY-GROUPS {
            etsysRip2ExtGlobalGroup
        }
    ::= { etsysRip2ExtCompliances 1 }

END
