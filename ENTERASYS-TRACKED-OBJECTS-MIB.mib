ENTERASYS-TRACKED-OBJECTS-MIB DEFINITIONS ::= BEGIN

--  enterasys-tracked-objects-mib.txt
--
--  Part Number:
--
--

--  This module provides authoritative definitions for Enterasys
--  Networks' Tracked Objects functionality.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, (2011-2013) Enterasys Networks, Inc.

IMPORTS
    MODULE-IDENTITY, OBJECT-TYPE, Counter32, Unsigned32, Gauge32,
    TimeTicks
        FROM SNMPv2-SMI
    RowStatus, TruthValue
        FROM SNMPv2-TC
    MODULE-COMPLIANCE, OBJECT-GROUP
        FROM SNMPv2-CONF
    SnmpAdminString
        FROM SNMP-FRAMEWORK-MIB
    InetAddressType, InetAddress, InetAddressPrefixLength,
    InetPortNumber
        FROM INET-ADDRESS-MIB
    InterfaceIndex
        FROM IF-MIB
    etsysModules
        FROM ENTERASYS-MIB-NAMES;

etsysTrackedObjectsMIB MODULE-IDENTITY
    LAST-UPDATED "201302071559Z"  -- Thu Feb  7 15:59 UTC 2013
    ORGANIZATION "Enterasys Networks, Inc."
    CONTACT-INFO
        "Postal:  Enterasys Networks
                  9 Northeastern Blvd.
                  Salem, NH 03079 USA

         Phone:   +1 603 952 5000
         E-mail:  support@enterasys.com
         WWW:     http://www.enterasys.com"
    DESCRIPTION
        "This MIB module defines a portion of the SNMP MIB under
         the Enterasys Networks enterprise OID pertaining to the
         Tracked Objects functionality.

         This MIB was designed to be used for configuring probes and
         tracked objects.  Each probe and tracked object has
         configuration parameters that may also be controlled via this
         MIB."

    REVISION    "201302071559Z"  -- Thu Feb  7 15:59 UTC 2013
    DESCRIPTION "Added the etsysTrackedObjectsProbeTsTable.  This table
                 supports the ICMP timestamp probes.  These probes
                 collect timestamp data for the client applications.
                 Additional changes include a new type 'icmpTs' for
                 etsysTrackedObjectsProbeType, and a new state 'collect'
                 for etsysTrackedObjectsSessionState.

                 Added the etsysTrackedObjectsPortIfSpeedTable.  This
                 tables supports 'portIfSpeed' tracked objects.  The
                 'portIfSpeed' tracked object determines the highest and
                 lowest port speeds for the interfaces associated with
                 the tracked object.

                 Additional changes include a new type 'portIfSpeed' for
                 etsysTrackedObjectsCommonType and a new object in the
                 etsysTrackedObjectsPortTable for associating the
                 interface with a tracked object
                 (etsysTrackedObjectsPortIfSpeedName).

                 Added two global objects that convey to the user the
                 resources available for associating interface indexes
                 with 'portGroup' and 'portIfSpeed' tracked objects.
                 The two objects are etsysTrackedObjectsMaxIntfAssoc and
                 etsysTrackedObjectsIntfAssocUsed.

                 Corrected the description text of several tables and
                 objects."

    REVISION    "201202081429Z"  -- Wed Feb  8 14:29 UTC 2012
    DESCRIPTION "Added threshold objects to the
                 etsysTrackedObjectsPortGroupTable."

    REVISION    "201105181506Z"  -- Wed May 18 15:06 UTC 2011
    DESCRIPTION "The initial version of this MIB module"
    ::= { etsysModules 79 }

-- Textual Conventions


-- -------------------------------------------------------------
-- Branches
-- -------------------------------------------------------------
etsysTrackedObjects OBJECT IDENTIFIER ::= { etsysTrackedObjectsMIB 1 }

etsysTrackedObjectsGlobals
    OBJECT IDENTIFIER ::= { etsysTrackedObjects 1 }
etsysTrackedObjectsTables
    OBJECT IDENTIFIER ::= { etsysTrackedObjects 2 }

-- -------------------------------------------------------------
-- MIB Objects
-- -------------------------------------------------------------

etsysTrackedObjectsMaxObjects OBJECT-TYPE
    SYNTAX       Unsigned32
    MAX-ACCESS   read-only
    STATUS       current
    DESCRIPTION
        "The maximum number of tracked objects that can be configured
         to monitor local entities."
    ::= { etsysTrackedObjectsGlobals 1 }

etsysTrackedObjectsObjectsUsed OBJECT-TYPE
    SYNTAX       Gauge32
    MAX-ACCESS   read-only
    STATUS       current
    DESCRIPTION
        "The current number of tracked objects that are configured."
    ::= { etsysTrackedObjectsGlobals 2 }

etsysTrackedObjectsMaxProbes OBJECT-TYPE
    SYNTAX       Unsigned32
    MAX-ACCESS   read-only
    STATUS       current
    DESCRIPTION
        "The maximum number of probes that can be configured to monitor
         remote entities."
    ::= { etsysTrackedObjectsGlobals 3 }

etsysTrackedObjectsProbesUsed OBJECT-TYPE
    SYNTAX       Gauge32
    MAX-ACCESS   read-only
    STATUS       current
    DESCRIPTION
        "The current number of probes that are configured."
    ::= { etsysTrackedObjectsGlobals 4 }

etsysTrackedObjectsMaxAcvProbes OBJECT-TYPE
    SYNTAX       Unsigned32
    MAX-ACCESS   read-only
    STATUS       current
    DESCRIPTION
        "The maximum number of Application Content Verification (ACV)
         probes that can be configured."
    ::= { etsysTrackedObjectsGlobals 5 }

etsysTrackedObjectsAcvProbesUsed OBJECT-TYPE
    SYNTAX       Gauge32
    MAX-ACCESS   read-only
    STATUS       current
    DESCRIPTION
        "The current number of ACV probes that are configured."
    ::= { etsysTrackedObjectsGlobals 6 }

etsysTrackedObjectsMaxSessions OBJECT-TYPE
    SYNTAX       Unsigned32
    MAX-ACCESS   read-only
    STATUS       current
    DESCRIPTION
        "The maximum number of probe sessions that can be configured
         by Enterasys client applications."
    ::= { etsysTrackedObjectsGlobals 7 }

etsysTrackedObjectsSessionsUsed OBJECT-TYPE
    SYNTAX       Gauge32
    MAX-ACCESS   read-only
    STATUS       current
    DESCRIPTION
        "The current number of probe sessions that are currently used
         by Enterasys client applications."
    ::= { etsysTrackedObjectsGlobals 8 }

etsysTrackedObjectsMaxIntfAssoc OBJECT-TYPE
    SYNTAX       Unsigned32
    MAX-ACCESS   read-only
    STATUS       current
    DESCRIPTION
        "The maximum number of system wide objects available to
         associate an InterfaceIndex with either a 'portGroup' or a
         'portIfSpeed' tracked object."
    ::= { etsysTrackedObjectsGlobals 9 }

etsysTrackedObjectsIntfAssocUsed OBJECT-TYPE
    SYNTAX       Gauge32
    MAX-ACCESS   read-only
    STATUS       current
    DESCRIPTION
        "The current number of system wide objects that are used to
         associate an InterfaceIndex with either a 'portGroup' or a
         'portIfSpeed' tracked object."
    ::= { etsysTrackedObjectsGlobals 10 }

--
-- Enterasys Tracked Objects Probe Table
--
etsysTrackedObjectsProbeTable OBJECT-TYPE
    SYNTAX       SEQUENCE OF EtsysTrackedObjectsProbeEntry
    MAX-ACCESS   not-accessible
    STATUS       current
    DESCRIPTION
        "This table provides the configuration parameters and attributes
         pertaining to probes.  Client applications use probes to
         determine the status of remote services, such as HTTP servers."
    ::= { etsysTrackedObjectsTables 1 }

etsysTrackedObjectsProbeEntry OBJECT-TYPE
    SYNTAX       EtsysTrackedObjectsProbeEntry
    MAX-ACCESS   not-accessible
    STATUS       current
    DESCRIPTION
        "An entry (conceptual row) in the etsysTrackedObjectsProbeTable."
    INDEX { IMPLIED etsysTrackedObjectsProbeName }
    ::= { etsysTrackedObjectsProbeTable 1 }

EtsysTrackedObjectsProbeEntry ::= SEQUENCE {
    etsysTrackedObjectsProbeName                  SnmpAdminString,
    etsysTrackedObjectsProbeIndex                 Unsigned32,
    etsysTrackedObjectsProbeDefault               TruthValue,
    etsysTrackedObjectsProbeType                  INTEGER,
    etsysTrackedObjectsProbeAcvClose              SnmpAdminString,
    etsysTrackedObjectsProbeAcvReply              SnmpAdminString,
    etsysTrackedObjectsProbeAcvRequest            SnmpAdminString,
    etsysTrackedObjectsProbeAcvDepth              Unsigned32,
    etsysTrackedObjectsProbeFdCount               Unsigned32,
    etsysTrackedObjectsProbeFdInterval            Unsigned32,
    etsysTrackedObjectsProbePdCount               Unsigned32,
    etsysTrackedObjectsProbePdInterval            Unsigned32,
    etsysTrackedObjectsProbeOpen                  Unsigned32,
    etsysTrackedObjectsProbeReceive               Unsigned32,
    etsysTrackedObjectsProbeInservice             TruthValue,
    etsysTrackedObjectsProbeDescription           SnmpAdminString,
    etsysTrackedObjectsProbeStatus                RowStatus
}

etsysTrackedObjectsProbeName OBJECT-TYPE
    SYNTAX       SnmpAdminString (SIZE(1..31))
    MAX-ACCESS   not-accessible
    STATUS       current
    DESCRIPTION
        "The name given to this probe."
    ::= { etsysTrackedObjectsProbeEntry 1 }

etsysTrackedObjectsProbeIndex OBJECT-TYPE
    SYNTAX       Unsigned32
    MAX-ACCESS   read-only
    STATUS       current
    DESCRIPTION
        "A unique value assigned by the system for referencing this
         entry within other tables that have memory restrictions."
    ::= { etsysTrackedObjectsProbeEntry 2 }

etsysTrackedObjectsProbeDefault OBJECT-TYPE
    SYNTAX       TruthValue
    MAX-ACCESS   read-only
    STATUS       current
    DESCRIPTION
        "Identifies whether this row entry is a default probe created
         by the system.  A 'true' value indicates the system created the
         row entry, otherwise the value is 'false'.

         If the value of this object is 'true', the entry is read-only.
         Any attempt to modify the objects within this table results in
         the operation failing with a badValue error."
    ::= { etsysTrackedObjectsProbeEntry 3 }

etsysTrackedObjectsProbeType OBJECT-TYPE
    SYNTAX       INTEGER {
                     icmp(1),
                     udp(2),
                     tcp(3),
                     icmpTs(4)
                 }
    MAX-ACCESS   read-create
    STATUS       current
    DESCRIPTION
        "The type of connection used when contacting the remote service.

         icmp(1) - Issues an ICMP echo request and expects an echo reply
                   from the remote service.  Probes of this type determine
                   the state of the remote service.

         udp(2)  - Sends a UDP request using either the
                   etsysTrackedObjectsProbeAcvRequest string or a generic
                   '\r\n'.  If its an ACV request, the system expects
                   an ACV reply.  If its a generic request, no reply is
                   expected.  Probes of this type determine the state of
                   the remote service.

         tcp(3)  - Sets up a 3-way handshake with the remote service.
                   If etsysTrackedObjectsProbeAcvRequest is configured,
                   that string is sent over the connected socket, and
                   an ACV reply is expected.  If that object is not
                   configured, then the connection is closed.  Probes of
                   this type determine the state of the remote service.

         icmpTs(4) - Issues an ICMP echo request and expects an echo
                   reply.  The echo request contains a timestamp of the
                   transmit time.  The echo reply includes the timestamp
                   of the received echo request and the transmit
                   timestamp of the echo reply.  Upon receiving the echo
                   reply, the application adds a final timestamp for the
                   receive time.

                   Hosts:
                     L - Local Host, D - Destination Host
                   Timestamps:
                     ETxTs - Echo Request Transmit Timestamp
                     ERxTs - Echo Request Receive Timestamp
                     RTxTs - Echo Reply Transmit Timestamp
                     RRxTs - Echo Reply Receive Timestamp

                   L ----- Echo Request (ETxTs) --------------> D
                   L <---- Echo Reply (ETxTs, ERxTs, RTxTs)---- D
                   L (Adds RRxTs)

                   Notes:
                   In order for the echo reply to contain the extra
                   timestamps, the destinaton host MUST be an Enterasys
                   device that supports the 'icmpTs' type.

                   However, it is not a requirement that the destination
                   host be an Enterasys device, nor does an Enterasys
                   device have to support the 'icmpTs' type for the probe
                   to operate correctly.  In this situation, the client
                   applications will have to handle the ERxTs and RTxTs
                   values being zero.

                   Probes of this type collect timestamp information for
                   the client applications.  These probes DO NOT determine
                   the state of the remote service.  Additional objects
                   are found in the etsysTrackedObjectsProbeTsTable.

         The value of this object MAY NOT be modified after creating the
         row."
    DEFVAL { icmp }
    ::= { etsysTrackedObjectsProbeEntry 4 }

etsysTrackedObjectsProbeAcvClose OBJECT-TYPE
    SYNTAX       SnmpAdminString (SIZE(0..127))
    MAX-ACCESS   read-create
    STATUS       current
    DESCRIPTION
        "The string that is sent prior to closing the connection to the
         remote service.  This string is used to help the remote service
         close/cleanup its side of connection.

         This object MAY NOT be set when etsysTrackedObjectsProbeType is
         either 'icmp' or 'icmpTs'."
    DEFVAL { "" }
    ::= { etsysTrackedObjectsProbeEntry 5 }

etsysTrackedObjectsProbeAcvReply OBJECT-TYPE
    SYNTAX       SnmpAdminString (SIZE(0..127))
    MAX-ACCESS   read-create
    STATUS       current
    DESCRIPTION
        "The string that must be found within the response to an ACV
         request in order for the transaction to be successful.  The
         entire string must be found prior to exceeding the ACV search
         depth (etsysTrackedObjectsProbeAcvDepth).

         This object MAY NOT be set when etsysTrackedObjectsProbeType is
         either 'icmp' or 'icmpTs'."
    DEFVAL { "" }
    ::= { etsysTrackedObjectsProbeEntry 6 }

etsysTrackedObjectsProbeAcvRequest OBJECT-TYPE
    SYNTAX       SnmpAdminString (SIZE(0..127))
    MAX-ACCESS   read-create
    STATUS       current
    DESCRIPTION
        "The string that is sent to the remote host after a
         connection is established with the specified service.

         An ACV transaction will fail if an ACV request is sent and the
         ACV reply string (etsysTrackedObjectsProbeAcvReply) is not set.

         This object MAY NOT be set when etsysTrackedObjectsProbeType is
         either 'icmp' or 'icmpTs'."
    DEFVAL { "" }
    ::= { etsysTrackedObjectsProbeEntry 7 }

etsysTrackedObjectsProbeAcvDepth OBJECT-TYPE
    SYNTAX       Unsigned32 (1..255)
    UNITS        "characters"
    MAX-ACCESS   read-create
    STATUS       current
    DESCRIPTION
        "The search depth at which to stop looking for the
         etsysTrackedObjectsProbeAcvReply within an ACV response.  A
         successful match may stop prior to this search depth, but an
         unsuccessful match will not (unless the response from the server
         contains fewer characters than the specified search depth).

         This object MAY NOT be set when etsysTrackedObjectsProbeType is
         either 'icmp' or 'icmpTs'."
    DEFVAL { 255 }
    ::= { etsysTrackedObjectsProbeEntry 8 }

etsysTrackedObjectsProbeFdCount OBJECT-TYPE
    SYNTAX       Unsigned32 (1..65535)
    MAX-ACCESS   read-create
    STATUS       current
    DESCRIPTION
        "The fail-detect count.  This is the number of consecutive
         attempts that MUST fail prior to marking a session's state
         object, etsysTrackedObjectsSessionState, as 'down'."
    DEFVAL { 3 }
    ::= { etsysTrackedObjectsProbeEntry 9 }

etsysTrackedObjectsProbeFdInterval OBJECT-TYPE
    SYNTAX       Unsigned32 (2..300)
    UNITS        "seconds"
    MAX-ACCESS   read-create
    STATUS       current
    DESCRIPTION
        "The fail-detect interval.  The number of seconds between
         attempts while any associated session's state object,
         etsysTrackedObjectsSessionState, is 'up'."
    DEFVAL { 10 }
    ::= { etsysTrackedObjectsProbeEntry 10 }

etsysTrackedObjectsProbePdCount OBJECT-TYPE
    SYNTAX       Unsigned32 (1..65535)
    MAX-ACCESS   read-create
    STATUS       current
    DESCRIPTION
        "The pass-detect count.  This is the number of consecutive
         attempts that MUST pass prior to marking a session's state
         object, etsysTrackedObjectsSessionState, as 'up'."
    DEFVAL { 3 }
    ::= { etsysTrackedObjectsProbeEntry 11 }

etsysTrackedObjectsProbePdInterval OBJECT-TYPE
    SYNTAX       Unsigned32 (2..300)
    UNITS        "seconds"
    MAX-ACCESS   read-create
    STATUS       current
    DESCRIPTION
        "The pass-detect interval.  The number of seconds between
         attempts while any associated session's state object,
         etsysTrackedObjectsSessionState, is 'down'."
    DEFVAL { 300 }
    ::= { etsysTrackedObjectsProbeEntry 12 }

etsysTrackedObjectsProbeOpen OBJECT-TYPE
    SYNTAX       Unsigned32 (1..30)
    UNITS        "seconds"
    MAX-ACCESS   read-create
    STATUS       current
    DESCRIPTION
        "The amount of time to wait for the TCP 3-way handshake to
         complete.

         This object is only relevant when etsysTrackedObjectsProbeType is
         'tcp'."
    DEFVAL { 5 }
    ::= { etsysTrackedObjectsProbeEntry 13 }

etsysTrackedObjectsProbeReceive OBJECT-TYPE
    SYNTAX       Unsigned32 (1..65535)
    UNITS        "seconds"
    MAX-ACCESS   read-create
    STATUS       current
    DESCRIPTION
        "The amount of time to wait for a response to come back from the
         remote service."
    DEFVAL { 10 }
    ::= { etsysTrackedObjectsProbeEntry 14 }

etsysTrackedObjectsProbeInservice OBJECT-TYPE
    SYNTAX       TruthValue
    MAX-ACCESS   read-create
    STATUS       current
    DESCRIPTION
        "A toggle mechanism that allows probe sessions to be put into
         service and taken out of service.  Only the session entries in
         the etsysTrackedObjectsSessionTable that reference this probe
         are affected.

         Probe sessions are inservice when the value of this object is
         set to 'true'.  In this case, those sessions MUST be scheduled
         to determine the status of the remote service.

         Probe sessions are not-inservice when the value of this object
         is set to 'false'.  In this case, the sessions MUST NOT be
         scheduled."
    DEFVAL { false }
    ::= { etsysTrackedObjectsProbeEntry 15 }

etsysTrackedObjectsProbeDescription OBJECT-TYPE
    SYNTAX       SnmpAdminString (SIZE(0..127))
    MAX-ACCESS   read-create
    STATUS       current
    DESCRIPTION
        "A user provided description of this entry."
    DEFVAL { "" }
    ::= { etsysTrackedObjectsProbeEntry 16 }

etsysTrackedObjectsProbeStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysTrackedObjectsProbeEntry 17 }


--
-- Enterasys Tracked Objects Session Table
--
etsysTrackedObjectsSessionTable OBJECT-TYPE
    SYNTAX       SEQUENCE OF EtsysTrackedObjectsSessionEntry
    MAX-ACCESS   not-accessible
    STATUS       current
    DESCRIPTION
        "This table provides the information pertaining to individual
         probe sessions.  Sessions are derived from probes and require a
         destination IP address and port number.  Sessions determine
         whether a remote service is up or down.

         Session are created by client applications that wish to
         monitor the state of a remote service.

         The number and size of objects in this table SHOULD be
         minimized in order to provide the scalability needed to support
         a lot of entries."
    ::= { etsysTrackedObjectsTables 2 }

etsysTrackedObjectsSessionEntry OBJECT-TYPE
    SYNTAX       EtsysTrackedObjectsSessionEntry
    MAX-ACCESS   not-accessible
    STATUS       current
    DESCRIPTION
        "An entry (conceptual row) in the etsysTrackedObjectsSessionTable."
    INDEX {
        etsysTrackedObjectsProbeIndex,
        etsysTrackedObjectsSessionType,
        etsysTrackedObjectsSessionAddr,
        etsysTrackedObjectsSessionPort
    }
    ::= { etsysTrackedObjectsSessionTable 1 }

EtsysTrackedObjectsSessionEntry ::= SEQUENCE {
    etsysTrackedObjectsSessionType                InetAddressType,
    etsysTrackedObjectsSessionAddr                InetAddress,
    etsysTrackedObjectsSessionPort                InetPortNumber,
    etsysTrackedObjectsSessionState               INTEGER,
    etsysTrackedObjectsSessionStateChanges        Counter32,
    etsysTrackedObjectsSessionLastChange          TimeTicks
}

etsysTrackedObjectsSessionType OBJECT-TYPE
    SYNTAX       InetAddressType
    MAX-ACCESS   not-accessible
    STATUS       current
    DESCRIPTION
        "The address family of the data contained in
         etsysTrackedObjectsSessionAddr."
    ::= { etsysTrackedObjectsSessionEntry 1 }

etsysTrackedObjectsSessionAddr OBJECT-TYPE
    SYNTAX       InetAddress
    MAX-ACCESS   not-accessible
    STATUS       current
    DESCRIPTION
        "The destination address of the object to monitor."
    ::= { etsysTrackedObjectsSessionEntry 2 }

etsysTrackedObjectsSessionPort OBJECT-TYPE
    SYNTAX       InetPortNumber
    MAX-ACCESS   not-accessible
    STATUS       current
    DESCRIPTION
        "The port number of the service being monitored."
    ::= { etsysTrackedObjectsSessionEntry 3 }

etsysTrackedObjectsSessionState OBJECT-TYPE
    SYNTAX       INTEGER {
                     up(1),
                     down(2),
                     pending(3),
                     disabled(4),
                     collect(5)
                 }
    MAX-ACCESS   read-only
    STATUS       current
    DESCRIPTION
        "The current state of the session.

         up(1)       - The service on the remote session is up.  The
                       session has passed the criteria specified in the
                       corresponding probe.
         down(2)     - The service on the remote session is down.  The
                       session has not passed the criteria specified in
                       the corresponding probe.
         pending(3)  - The system is in the process of determining the
                       initial state of the session.
         disabled(4) - The corresponding probe has been taken out of
                       service (etsysTrackedObjectsProbeInservice has
                       been set to 'false').
         collect(5)  - The system is actively collecting timestamp data
                       to pass along to the client applications.  Only
                       the sessions whose corresponding probe type is
                       'icmpTs' (etsysTrackedObjectsProbeType) may be in
                       this state."
    ::= { etsysTrackedObjectsSessionEntry 4 }

etsysTrackedObjectsSessionStateChanges OBJECT-TYPE
    SYNTAX       Counter32
    MAX-ACCESS   read-only
    STATUS       current
    DESCRIPTION
        "The number of times the etsysTrackedObjectsSessionState object
         has changed state."
    ::= { etsysTrackedObjectsSessionEntry 5 }

etsysTrackedObjectsSessionLastChange OBJECT-TYPE
    SYNTAX       TimeTicks
    MAX-ACCESS   read-only
    STATUS       current
    DESCRIPTION
        "The sysUpTime at which the etsysTrackedObjectsSessionState was
         last modified."
    ::= { etsysTrackedObjectsSessionEntry 6 }


--
-- Enterasys Tracked Objects Common Table
--
etsysTrackedObjectsCommonTable OBJECT-TYPE
    SYNTAX       SEQUENCE OF EtsysTrackedObjectsCommonEntry
    MAX-ACCESS   not-accessible
    STATUS       current
    DESCRIPTION
        "This table contains the objects pertaining to the common
         attributes shared by the tracked objects."
    ::= { etsysTrackedObjectsTables 3 }

etsysTrackedObjectsCommonEntry OBJECT-TYPE
    SYNTAX       EtsysTrackedObjectsCommonEntry
    MAX-ACCESS   not-accessible
    STATUS       current
    DESCRIPTION
        "An entry (conceptual row) in the etsysTrackedObjectsCommonTable."
    INDEX { IMPLIED etsysTrackedObjectsCommonName }
    ::= { etsysTrackedObjectsCommonTable 1 }

EtsysTrackedObjectsCommonEntry ::= SEQUENCE {
    etsysTrackedObjectsCommonName                 SnmpAdminString,
    etsysTrackedObjectsCommonType                 INTEGER,
    etsysTrackedObjectsCommonState                INTEGER,
    etsysTrackedObjectsCommonDelayUp              Unsigned32,
    etsysTrackedObjectsCommonDelayDown            Unsigned32,
    etsysTrackedObjectsCommonDescription          SnmpAdminString,
    etsysTrackedObjectsCommonInservice            TruthValue,
    etsysTrackedObjectsCommonActionUp             SnmpAdminString,
    etsysTrackedObjectsCommonActionDown           SnmpAdminString
}

etsysTrackedObjectsCommonName OBJECT-TYPE
    SYNTAX       SnmpAdminString (SIZE(1..31))
    MAX-ACCESS   not-accessible
    STATUS       current
    DESCRIPTION
        "The name given to this tracked object."
    ::= { etsysTrackedObjectsCommonEntry 1 }

etsysTrackedObjectsCommonType OBJECT-TYPE
    SYNTAX       INTEGER {
                     interface(1),
                     ipRoute(2),
                     portGroup(3),
                     portIfspeed(4)
                 }
    MAX-ACCESS   read-only
    STATUS       current
    DESCRIPTION
        "The object type that is tracked by this entry.  The objects
         non-common attributes are in one of the following tables based
         on the type:

         interface(1)   - etsysTrackedObjectsIntfTable
         ipRoute(2)     - etsysTrackedObjectsRouteTable
         portGroup(3)   - etsysTrackedObjectsPortGroupTable
         portIfSpeed(4) - etsysTrackedObjectsPortIfSpeedTable"
    ::= { etsysTrackedObjectsCommonEntry 2 }

etsysTrackedObjectsCommonState OBJECT-TYPE
    SYNTAX       INTEGER {
                     up(1),
                     down(2),
                     testing(3),
                     disabled(4)
                 }
    MAX-ACCESS   read-only
    STATUS       current
    DESCRIPTION
        "The current state of the tracked object.

         up(1)       - The tracked object has been detected as being up.
         down(2)     - The tracked object has been detected as being
                       down.
         testing(3)  - The system is in the process of determining the
                       initial state of the tracked object.
         disabled(4) - The tracked object has been taken out of service
                       (etsysTrackedObjectsCommonInservice has been set to
                       'false')."
    ::= { etsysTrackedObjectsCommonEntry 3 }

etsysTrackedObjectsCommonDelayUp OBJECT-TYPE
    SYNTAX       Unsigned32 (0..180)
    UNITS        "seconds"
    MAX-ACCESS   read-write
    STATUS       current
    DESCRIPTION
        "The amount of time the system waits prior to informing the
         client applications of an 'up' status for the
         etsysTrackedObjectsState object.

         If the etsysTrackedObjectsState object transitions back to
         the 'down' state prior to the delay period expiring, the client
         applications are not informed."
    ::= { etsysTrackedObjectsCommonEntry 4 }

etsysTrackedObjectsCommonDelayDown OBJECT-TYPE
    SYNTAX       Unsigned32 (0..180)
    UNITS        "seconds"
    MAX-ACCESS   read-write
    STATUS       current
    DESCRIPTION
        "The amount of time the system waits prior to informing the
         client applications of a 'down' status for the
         etsysTrackedObjectsState object.

         If the etsysTrackedObjectsState object transitions back to
         the 'up' state prior to the delay period expiring, the client
         applications are not informed."
    ::= { etsysTrackedObjectsCommonEntry 5 }

etsysTrackedObjectsCommonDescription OBJECT-TYPE
    SYNTAX       SnmpAdminString (SIZE(0..127))
    MAX-ACCESS   read-write
    STATUS       current
    DESCRIPTION
        "A user provided description of this entry."
    DEFVAL { "" }
    ::= { etsysTrackedObjectsCommonEntry 6 }

etsysTrackedObjectsCommonInservice OBJECT-TYPE
    SYNTAX       TruthValue
    MAX-ACCESS   read-write
    STATUS       current
    DESCRIPTION
        "A toggle mechanism that allows the tracked object to be put
         into service and taken out of service.

         A tracked object is inservice when the value of this object
         is set to 'true'.  In this case, the system is actively tracking
         the status of the object.

         A tracked object is not-inservice when the value of this object
         is set to 'false'.  In this case, the system does not monitor
         the status of the tracked object."
    ::= { etsysTrackedObjectsCommonEntry 7 }

etsysTrackedObjectsCommonActionUp OBJECT-TYPE
    SYNTAX       SnmpAdminString
    MAX-ACCESS   read-write
    STATUS       current
    DESCRIPTION
        "The name of a script file local to the system that is provided
         to the client applications when informing them this tracked
         object transitioned to the 'up' state.

         It is the client applications responsibility to verify the
         contents of the file."
    ::= { etsysTrackedObjectsCommonEntry 8 }

etsysTrackedObjectsCommonActionDown OBJECT-TYPE
    SYNTAX       SnmpAdminString
    MAX-ACCESS   read-write
    STATUS       current
    DESCRIPTION
        "The name of a script file local to the system that is provided
         to the client applications when informing them this tracked
         object transitioned to the 'down' state.

         It is the client applications responsibility to verify the
         contents of the file."
    ::= { etsysTrackedObjectsCommonEntry 9 }


--
-- Enterasys Tracked Objects Interface Table
--
etsysTrackedObjectsIntfTable OBJECT-TYPE
    SYNTAX       SEQUENCE OF EtsysTrackedObjectsIntfEntry
    MAX-ACCESS   not-accessible
    STATUS       current
    DESCRIPTION
        "This table provides the configuration parameters pertaining to
         local interface tracked objects.  VLANs and tunnels are the
         supported interface types.  The objects in this table cannot be
         modified after row creation with the exception of the RowStatus
         object.

         An entry created via this table will have a corresponding entry
         in the etsysTrackedObjectsCommonTable, which contains objects
         that are modifiable after row creation."
    ::= { etsysTrackedObjectsTables 4 }

etsysTrackedObjectsIntfEntry OBJECT-TYPE
    SYNTAX       EtsysTrackedObjectsIntfEntry
    MAX-ACCESS   not-accessible
    STATUS       current
    DESCRIPTION
        "An entry (conceptual row) in the etsysTrackedObjectsIntfTable."
    INDEX { IMPLIED etsysTrackedObjectsCommonName }
    ::= { etsysTrackedObjectsIntfTable 1 }

EtsysTrackedObjectsIntfEntry ::= SEQUENCE {
    etsysTrackedObjectsIntfIndex                  InterfaceIndex,
    etsysTrackedObjectsIntfOption                 INTEGER,
    etsysTrackedObjectsIntfStatus                 RowStatus
}

etsysTrackedObjectsIntfIndex OBJECT-TYPE
    SYNTAX       InterfaceIndex
    MAX-ACCESS   read-create
    STATUS       current
    DESCRIPTION
        "The MIB-II ifIndex of the interface being tracked.

         The value of this object MAY NOT be modified after creating
         the row."
    ::= { etsysTrackedObjectsIntfEntry 1 }

etsysTrackedObjectsIntfOption OBJECT-TYPE
    SYNTAX       INTEGER {
                     lineProtocol(1)
                 }
    MAX-ACCESS   read-create
    STATUS       current
    DESCRIPTION
        "The following are the tracked object options available for
         interfaces.

         line-protocol(1) - Track the operational status of the
                            interface.

         The value of this object MAY NOT be modified after creating
         the row."
    DEFVAL { lineProtocol }
    ::= { etsysTrackedObjectsIntfEntry 2 }

etsysTrackedObjectsIntfStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysTrackedObjectsIntfEntry 3 }


--
-- Enterasys Tracked Objects Route Table
--
etsysTrackedObjectsRouteTable OBJECT-TYPE
    SYNTAX       SEQUENCE OF EtsysTrackedObjectsRouteEntry
    MAX-ACCESS   not-accessible
    STATUS       current
    DESCRIPTION
        "This table provides the configuration parameters pertaining to
         local route tracked objects, such as routes in the FIB.  The
         objects in this table cannot be modified after row creation with
         the exception of the RowStatus and metric thresholds object.

         An entry created via this table will have a corresponding entry
         in the etsysTrackedObjectsCommonTable, which contains objects
         that are modifiable after row creation."
    ::= { etsysTrackedObjectsTables 5 }

etsysTrackedObjectsRouteEntry OBJECT-TYPE
    SYNTAX       EtsysTrackedObjectsRouteEntry
    MAX-ACCESS   not-accessible
    STATUS       current
    DESCRIPTION
        "An entry (conceptual row) in the etsysTrackedObjectsRouteTable."
    INDEX { IMPLIED etsysTrackedObjectsCommonName }
    ::= { etsysTrackedObjectsRouteTable 1 }

EtsysTrackedObjectsRouteEntry ::= SEQUENCE {
    etsysTrackedObjectsRouteType                  InetAddressType,
    etsysTrackedObjectsRoutePrefix                InetAddressPrefixLength,
    etsysTrackedObjectsRoute                      InetAddress,
    etsysTrackedObjectsRouteOption                INTEGER,
    etsysTrackedObjectsRouteMetricUpThresh        Unsigned32,
    etsysTrackedObjectsRouteMetricDownThresh      Unsigned32,
    etsysTrackedObjectsRouteStatus                RowStatus
}

etsysTrackedObjectsRouteType OBJECT-TYPE
    SYNTAX       InetAddressType
    MAX-ACCESS   read-create
    STATUS       current
    DESCRIPTION
        "The address family of this tracked object entry.  This object
         dictates the valid input for the etsysTrackedObjectsRoutePrefix
         and etsysTrackedObjectsRoute objects.

         The value of this object MAY NOT be modified after creating
         the row."
    DEFVAL { ipv4 }
    ::= { etsysTrackedObjectsRouteEntry 1 }

etsysTrackedObjectsRoutePrefix OBJECT-TYPE
    SYNTAX       InetAddressPrefixLength
    MAX-ACCESS   read-create
    STATUS       current
    DESCRIPTION
        "The address mask of etsysTrackedObjectsRoute.

         The value of this object MUST be set while creating the row
         and it MAY NOT be modified afterwards."
    ::= { etsysTrackedObjectsRouteEntry 2 }

etsysTrackedObjectsRoute OBJECT-TYPE
    SYNTAX       InetAddress
    MAX-ACCESS   read-create
    STATUS       current
    DESCRIPTION
        "The address of the route that is monitored by this tracked
         object.

         The value of this object MUST be set while creating the row
         and it MAY NOT be modified afterwards."
    ::= { etsysTrackedObjectsRouteEntry 3 }

etsysTrackedObjectsRouteOption OBJECT-TYPE
    SYNTAX       INTEGER {
                     reachability(1),
                     metric(2)
                 }
    MAX-ACCESS   read-create
    STATUS       current
    DESCRIPTION
        "Dictates what to monitor in relation to the address.

         reachability(1) - Tracks the status of the route within the
                           FIB.
         metric(2)       - Uses metric thresholds to determine the
                           status of the route.

         The value of this object MAY NOT be modified after creating the
         row."
    DEFVAL { reachability }
    ::= { etsysTrackedObjectsRouteEntry 4 }

etsysTrackedObjectsRouteMetricUpThresh OBJECT-TYPE
    SYNTAX       Unsigned32 (0..254)
    MAX-ACCESS   read-create
    STATUS       current
    DESCRIPTION
        "The threshold value the route metric MUST reach in order for
         the tracked object to transition to the 'up' state from the
         'down' state.

         This value MUST be less than the value specified in
         etsysTrackedObjectsRouteMetricDownThresh.  An inconsistentValue
         error is returned if the value of a set operation is greater
         than or equal to etsysTrackedObjectsRouteMetricDownThresh.

         This value only has meaning when etsysTrackedObjectsRouteOption
         is 'metric'."
    DEFVAL { 254 }
    ::= { etsysTrackedObjectsRouteEntry 5 }

etsysTrackedObjectsRouteMetricDownThresh OBJECT-TYPE
    SYNTAX       Unsigned32 (1..255)
    MAX-ACCESS   read-create
    STATUS       current
    DESCRIPTION
        "The threshold value the route metric MUST reach in order for
         the tracked object to transition to the 'down' state from the
         'up' state.

         This value MUST be greater than the value specified in
         etsysTrackedObjectsRouteMetricUpThresh.  An inconsistentValue
         error is returned if the value of a set operation is less than
         or equal to etsysTrackedObjectsRouteMetricUpThresh.

         This value only has meaning when etsysTrackedObjectsRouteOption
         is 'metric'."
    DEFVAL { 255 }
    ::= { etsysTrackedObjectsRouteEntry 6 }

etsysTrackedObjectsRouteStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysTrackedObjectsRouteEntry 7 }


--
-- Enterasys Tracked Objects Port Group Table
--
etsysTrackedObjectsPortGroupTable OBJECT-TYPE
    SYNTAX       SEQUENCE OF EtsysTrackedObjectsPortGroupEntry
    MAX-ACCESS   not-accessible
    STATUS       current
    DESCRIPTION
        "This table provides the configuration parameters pertaining to
         a 'portGroup' tracked object.

         An entry created via this table will have a corresponding entry
         in the etsysTrackedObjectsCommonTable, which contains objects
         that are modifiable after row creation."
    ::= { etsysTrackedObjectsTables 6 }

etsysTrackedObjectsPortGroupEntry OBJECT-TYPE
    SYNTAX       EtsysTrackedObjectsPortGroupEntry
    MAX-ACCESS   not-accessible
    STATUS       current
    DESCRIPTION
        "An entry (conceptual row) in the
        etsysTrackedObjectsPortGroupTable."
    INDEX { IMPLIED etsysTrackedObjectsCommonName }
    ::= { etsysTrackedObjectsPortGroupTable 1 }

EtsysTrackedObjectsPortGroupEntry ::= SEQUENCE {
    etsysTrackedObjectsPortGroupMemberMax         Unsigned32,
    etsysTrackedObjectsPortGroupMemberCount       Gauge32,
    etsysTrackedObjectsPortGroupStatus            RowStatus,
    etsysTrackedObjectsPortGroupUpCount           Gauge32,
    etsysTrackedObjectsPortGroupDownCount         Gauge32,
    etsysTrackedObjectsPortGroupUpThresh          Unsigned32,
    etsysTrackedObjectsPortGroupDownThresh        Unsigned32
}

etsysTrackedObjectsPortGroupMemberMax OBJECT-TYPE
    SYNTAX       Unsigned32
    MAX-ACCESS   read-only
    STATUS       current
    DESCRIPTION
        "The maximum number of ports that may be members of this
         'portGroup'."
    ::= { etsysTrackedObjectsPortGroupEntry 1 }

etsysTrackedObjectsPortGroupMemberCount OBJECT-TYPE
    SYNTAX       Gauge32
    MAX-ACCESS   read-only
    STATUS       current
    DESCRIPTION
        "The number of ports that are members of this 'portGroup'."
    ::= { etsysTrackedObjectsPortGroupEntry 2 }

etsysTrackedObjectsPortGroupStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysTrackedObjectsPortGroupEntry 3 }

etsysTrackedObjectsPortGroupUpCount OBJECT-TYPE
    SYNTAX       Gauge32
    MAX-ACCESS   read-only
    STATUS       current
    DESCRIPTION
        "The number of ports in the 'portGroup' that are up."
    ::= { etsysTrackedObjectsPortGroupEntry 4 }

etsysTrackedObjectsPortGroupDownCount OBJECT-TYPE
    SYNTAX       Gauge32
    MAX-ACCESS   read-only
    STATUS       current
    DESCRIPTION
        "The number of ports in the 'portGroup' that are down."
    ::= { etsysTrackedObjectsPortGroupEntry 5 }

etsysTrackedObjectsPortGroupUpThresh OBJECT-TYPE
    SYNTAX       Unsigned32 (1..255)
    MAX-ACCESS   read-create
    STATUS       current
    DESCRIPTION
        "The threshold used to determine when to set the tracked
         object's etsysTrackedObjectsCommonState to 'up'.

         If the value of etsysTrackedObjectsPortGroupUpCount is
         greater than or equal to this value, the
         etsysTrackedObjectsCommonState for this tracked object is set
         to 'up'.

         This value MUST be greater than the value specified in
         etsysTrackedObjectsPortGroupDownThresh.  An inconsistentValue
         error is returned if the value of a set operation is less than
         or equal to etsysTrackedObjectsPortGroupDownThresh."
    DEFVAL { 1 }
    ::= { etsysTrackedObjectsPortGroupEntry 6 }

etsysTrackedObjectsPortGroupDownThresh OBJECT-TYPE
    SYNTAX       Unsigned32 (0..254)
    MAX-ACCESS   read-create
    STATUS       current
    DESCRIPTION
        "The threshold used to determine when to set the tracked
         object's etsysTrackedObjectsCommonState to 'down'.

         If the value of etsysTrackedObjectsPortGroupUpCount is
         less than or equal to this value, the
         etsysTrackedObjectsCommonState for this tracked object is set
         to 'down'.

         This value MUST be less than the value specified in
         etsysTrackedObjectsPortGroupUpThresh.  An inconsistentValue
         error is returned if the value of a set operation is greater
         than or equal to etsysTrackedObjectsPortGroupUpThresh."
    DEFVAL { 0 }
    ::= { etsysTrackedObjectsPortGroupEntry 7 }

--
-- Enterasys Tracked Objects Port Table
--
etsysTrackedObjectsPortTable OBJECT-TYPE
    SYNTAX       SEQUENCE OF EtsysTrackedObjectsPortEntry
    MAX-ACCESS   not-accessible
    STATUS       current
    DESCRIPTION
        "This table provides the ability to associate a port that has
         a MIB-II ifIndex to a 'portGroup' and 'portIfSpeed' tracked
         object.  The tracked objects MUST exist prior to assigning the
         association."
    ::= { etsysTrackedObjectsTables 7 }

etsysTrackedObjectsPortEntry OBJECT-TYPE
    SYNTAX       EtsysTrackedObjectsPortEntry
    MAX-ACCESS   not-accessible
    STATUS       current
    DESCRIPTION
        "An entry (conceptual row) in the etsysTrackedObjectsPortTable."
    INDEX { etsysTrackedObjectsPortIfIndex }
    ::= { etsysTrackedObjectsPortTable 1 }

EtsysTrackedObjectsPortEntry ::= SEQUENCE {
    etsysTrackedObjectsPortIfIndex                InterfaceIndex,
    etsysTrackedObjectsPortGroupName              SnmpAdminString,
    etsysTrackedObjectsPortState                  INTEGER,
    etsysTrackedObjectsPortIfSpeedName            SnmpAdminString
}

etsysTrackedObjectsPortIfIndex OBJECT-TYPE
    SYNTAX       InterfaceIndex
    MAX-ACCESS   not-accessible
    STATUS       current
    DESCRIPTION
        "The MIB-II ifIndex of the port."
    ::= { etsysTrackedObjectsPortEntry 1 }

etsysTrackedObjectsPortGroupName OBJECT-TYPE
    SYNTAX       SnmpAdminString (SIZE(0..31))
    MAX-ACCESS   read-write
    STATUS       current
    DESCRIPTION
        "The name of the 'portGroup' tracked object this port is
         associated with.

         The tracked object MUST exist in the
         etsysTrackedObjectsPortGroupTable.  An inconsistentValue error
         is returned if the tracked object does not exist.

         The empty string indicates this port is not associated with a
         'portGroup' tracked object."
    DEFVAL { "" }
    ::= { etsysTrackedObjectsPortEntry 2 }

etsysTrackedObjectsPortState OBJECT-TYPE
    SYNTAX       INTEGER {
                     up(1),
                     down(2),
                     testing(3),
                     notTracked(4)
                 }
    MAX-ACCESS   read-only
    STATUS       current
    DESCRIPTION
        "The systems interpretation of the operational status of the
         port.

         up(1)         - The state when the port is operationally up.
         down(2)       - The state when the port has any other
                         operational status other than 'up'.
         testing(3)    - The state when the system is retrieving the
                         status of the port.
         notTracked(4) - The state when etsysTrackedObjectsPortGroupName
                         has its default value."
    ::= { etsysTrackedObjectsPortEntry 3 }

etsysTrackedObjectsPortIfSpeedName OBJECT-TYPE
    SYNTAX       SnmpAdminString (SIZE(0..31))
    MAX-ACCESS   read-write
    STATUS       current
    DESCRIPTION
        "The name of the 'portIfSpeed' tracked object this port is
         associated with.

         The tracked object MUST exist in the
         etsysTrackedObjectsPortIfSpeedTable.  An inconsistentValue error
         is returned if the tracked object does not exist.

         The empty string indicates this port is not associated with a
         'portIfSpeed' tracked object."
    DEFVAL { "" }
    ::= { etsysTrackedObjectsPortEntry 4 }

--
-- Enterasys Tracked Objects ICMP Timestamp Probe Table
--
etsysTrackedObjectsProbeTsTable OBJECT-TYPE
    SYNTAX       SEQUENCE OF EtsysTrackedObjectsProbeTsEntry
    MAX-ACCESS   not-accessible
    STATUS       current
    DESCRIPTION
        "This table provides the configuration parameters for probes
         of type 'icmpTs'.  Probes of this type collect timestamp
         information for the client applications."
    ::= { etsysTrackedObjectsTables 8 }

etsysTrackedObjectsProbeTsEntry OBJECT-TYPE
    SYNTAX       EtsysTrackedObjectsProbeTsEntry
    MAX-ACCESS   not-accessible
    STATUS       current
    DESCRIPTION
        "An entry (conceptual row) in the
         etsysTrackedObjectsProbeTsEntry."
    INDEX { IMPLIED etsysTrackedObjectsProbeName }
    ::= { etsysTrackedObjectsProbeTsTable 1 }

EtsysTrackedObjectsProbeTsEntry ::= SEQUENCE {
    etsysTrackedObjectsProbeTsInterval            Unsigned32,
    etsysTrackedObjectsProbeTsRecvWait            Unsigned32,
    etsysTrackedObjectsProbeTsTOS                 Unsigned32,
    etsysTrackedObjectsProbeTsPCP                 Unsigned32
}

etsysTrackedObjectsProbeTsInterval OBJECT-TYPE
    SYNTAX       Unsigned32 (100..30000)
    UNITS        "milliseconds"
    MAX-ACCESS   read-write
    STATUS       current
    DESCRIPTION
        "The interval used for entries retrieving the timestamp data.
         This is the number of milliseconds between attempts.  The value
         MUST be expressed in increments of 100.  This value MUST be
         greater than etsysTrackedObjectsProbeTsRecvWait.

         A badValue error is returned if the value of a set operation
         is not an increment of 100.

         An inconsistentValue error is returned if the value of a set
         operation would make this value less than or equal to
         etsysTrackedObjectsProbeTsRecvWait."
    DEFVAL { 2000 }
    ::= { etsysTrackedObjectsProbeTsEntry 1 }

etsysTrackedObjectsProbeTsRecvWait OBJECT-TYPE
    SYNTAX       Unsigned32 (50..29900)
    UNITS        "milliseconds"
    MAX-ACCESS   read-write
    STATUS       current
    DESCRIPTION
        "The amount of time to wait for a response.  This value MUST be
         less than etsysTrackedObjectsProbeTsInterval.

         An inconsistentValue error is returned if the value of a set
         operation would make this value greater than or equal to
         etsysTrackedObjectsProbeTsInterval."
    DEFVAL { 1000 }
    ::= { etsysTrackedObjectsProbeTsEntry 2 }

etsysTrackedObjectsProbeTsTOS OBJECT-TYPE
    SYNTAX       Unsigned32 (0..254)
    MAX-ACCESS   read-write
    STATUS       current
    DESCRIPTION
        "The type-of-service value to use in the IP header when
         transmitting packets for timestamp data.

         The value of the TOS is not checked for accuracy."
    REFERENCE
        "RFC 791"
    ::= { etsysTrackedObjectsProbeTsEntry 3 }

etsysTrackedObjectsProbeTsPCP OBJECT-TYPE
    SYNTAX       Unsigned32 (0..7)
    MAX-ACCESS   read-write
    STATUS       current
    DESCRIPTION
        "The priority code point value to use in the VLAN header when
         transmitting packets for timestamp data.

         The value of the PCP is not checked for accuracy."
    REFERENCE
        "IEEE 802.1Q"
    ::= { etsysTrackedObjectsProbeTsEntry 4 }

--
-- Enterasys Tracked Objects Port If Speed Table
--
etsysTrackedObjectsPortIfSpeedTable OBJECT-TYPE
    SYNTAX       SEQUENCE OF EtsysTrackedObjectsPortIfSpeedEntry
    MAX-ACCESS   not-accessible
    STATUS       current
    DESCRIPTION
        "This table provides the configuration parameters pertaining to
         a 'portIfSpeed' tracked object.

         An entry created via this table will have a corresponding entry
         in the etsysTrackedObjectsCommonTable, which contains objects
         that are modifiable after row creation."
    ::= { etsysTrackedObjectsTables 9 }

etsysTrackedObjectsPortIfSpeedEntry OBJECT-TYPE
    SYNTAX       EtsysTrackedObjectsPortIfSpeedEntry
    MAX-ACCESS   not-accessible
    STATUS       current
    DESCRIPTION
        "An entry (conceptual row) in the
         etsysTrackedObjectsPortIfSpeedTable."
    INDEX { IMPLIED etsysTrackedObjectsCommonName }
    ::= { etsysTrackedObjectsPortIfSpeedTable 1 }

EtsysTrackedObjectsPortIfSpeedEntry ::= SEQUENCE {
    etsysTrackedObjectsPortIfSpeedMemberMax            Unsigned32,
    etsysTrackedObjectsPortIfSpeedMemberCount          Gauge32,
    etsysTrackedObjectsPortIfSpeedLow                  Gauge32,
    etsysTrackedObjectsPortIfSpeedHigh                 Gauge32,
    etsysTrackedObjectsPortIfSpeedStatus               RowStatus
}

etsysTrackedObjectsPortIfSpeedMemberMax OBJECT-TYPE
    SYNTAX       Unsigned32
    MAX-ACCESS   read-only
    STATUS       current
    DESCRIPTION
        "The maximum number of ports that may be members of this
         'portIfSpeed' group."
    ::= { etsysTrackedObjectsPortIfSpeedEntry 1 }

etsysTrackedObjectsPortIfSpeedMemberCount OBJECT-TYPE
    SYNTAX       Gauge32
    MAX-ACCESS   read-only
    STATUS       current
    DESCRIPTION
        "The number of ports that are members of this 'portIfSpeed'
         group."
    ::= { etsysTrackedObjectsPortIfSpeedEntry 2 }

etsysTrackedObjectsPortIfSpeedLow OBJECT-TYPE
    SYNTAX       Gauge32
    UNITS        "Megabits per second"
    MAX-ACCESS   read-only
    STATUS       current
    DESCRIPTION
        "The lowest interface speed among the ports associated with this
         tracked object."
    ::= { etsysTrackedObjectsPortIfSpeedEntry 3 }

etsysTrackedObjectsPortIfSpeedHigh OBJECT-TYPE
    SYNTAX       Gauge32
    UNITS        "Megabits per second"
    MAX-ACCESS   read-only
    STATUS       current
    DESCRIPTION
        "The highest interface speed among the ports associated with this
         tracked object."
    ::= { etsysTrackedObjectsPortIfSpeedEntry 4 }

etsysTrackedObjectsPortIfSpeedStatus OBJECT-TYPE
    SYNTAX       RowStatus
    MAX-ACCESS   read-create
    STATUS       current
    DESCRIPTION
        "This object permits management of the table by facilitating
         actions such as row creation and deletion.

         Creation and activation of a conceptual row in this table MUST
         be performed as a single operation by setting this object to
         createAndGo(4).  Suspension of an active conceptual row is
         not supported.  Consequently, setting this object to
         createAndWait(5) or notInService(2) SHALL fail."
    ::= { etsysTrackedObjectsPortIfSpeedEntry 5 }

-- -------------------------------------------------------------
-- Conformance Information
-- -------------------------------------------------------------

etsysTrackedObjectsConformance
    OBJECT IDENTIFIER ::= { etsysTrackedObjectsMIB 2 }

etsysTrackedObjectsGroups
    OBJECT IDENTIFIER ::= { etsysTrackedObjectsConformance 1 }
etsysTrackedObjectsCompliances
    OBJECT IDENTIFIER ::= { etsysTrackedObjectsConformance 2 }

-- -------------------------------------------------------------
-- Units of conformance
-- -------------------------------------------------------------

etsysTrackedObjectsGlobalGroup OBJECT-GROUP
    OBJECTS {
        etsysTrackedObjectsMaxObjects,
        etsysTrackedObjectsObjectsUsed,
        etsysTrackedObjectsMaxProbes,
        etsysTrackedObjectsProbesUsed,
        etsysTrackedObjectsMaxAcvProbes,
        etsysTrackedObjectsAcvProbesUsed,
        etsysTrackedObjectsMaxSessions,
        etsysTrackedObjectsSessionsUsed
    }
    STATUS      deprecated
    DESCRIPTION
        "This group defines information pertaining to the global
         resources used by Enterasys Tracked Objects."
    ::= { etsysTrackedObjectsGroups 1 }

etsysTrackedObjectsProbeGroup OBJECT-GROUP
    OBJECTS {
        etsysTrackedObjectsProbeIndex,
        etsysTrackedObjectsProbeDefault,
        etsysTrackedObjectsProbeType,
        etsysTrackedObjectsProbeAcvClose,
        etsysTrackedObjectsProbeAcvReply,
        etsysTrackedObjectsProbeAcvRequest,
        etsysTrackedObjectsProbeAcvDepth,
        etsysTrackedObjectsProbeFdCount,
        etsysTrackedObjectsProbeFdInterval,
        etsysTrackedObjectsProbePdCount,
        etsysTrackedObjectsProbePdInterval,
        etsysTrackedObjectsProbeOpen,
        etsysTrackedObjectsProbeReceive,
        etsysTrackedObjectsProbeInservice,
        etsysTrackedObjectsProbeDescription,
        etsysTrackedObjectsProbeStatus
    }
    STATUS      current
    DESCRIPTION
        "This group defines the attributes and configuration parameters
         for probe objects."
    ::= { etsysTrackedObjectsGroups 2 }

etsysTrackedObjectsSessionGroup OBJECT-GROUP
    OBJECTS {
        etsysTrackedObjectsSessionState,
        etsysTrackedObjectsSessionStateChanges,
        etsysTrackedObjectsSessionLastChange
    }
    STATUS      current
    DESCRIPTION
        "This group defines the session information, created by client
         applications."
    ::= { etsysTrackedObjectsGroups 3 }

etsysTrackedObjectsCommonGroup OBJECT-GROUP
    OBJECTS {
        etsysTrackedObjectsCommonType,
        etsysTrackedObjectsCommonState,
        etsysTrackedObjectsCommonDelayUp,
        etsysTrackedObjectsCommonDelayDown,
        etsysTrackedObjectsCommonDescription,
        etsysTrackedObjectsCommonInservice,
        etsysTrackedObjectsCommonActionUp,
        etsysTrackedObjectsCommonActionDown
    }
    STATUS      current
    DESCRIPTION
        "This group defines the common attributes shared by tracked
         objects."
    ::= { etsysTrackedObjectsGroups 4 }

etsysTrackedObjectsIfGroup OBJECT-GROUP
    OBJECTS {
        etsysTrackedObjectsIntfIndex,
        etsysTrackedObjectsIntfOption,
        etsysTrackedObjectsIntfStatus
    }
    STATUS      current
    DESCRIPTION
        "This group defines the configuration parameters for tracking
         local interfaces."
    ::= { etsysTrackedObjectsGroups 5 }

etsysTrackedObjectsRouteGroup OBJECT-GROUP
    OBJECTS {
        etsysTrackedObjectsRouteType,
        etsysTrackedObjectsRoutePrefix,
        etsysTrackedObjectsRoute,
        etsysTrackedObjectsRouteOption,
        etsysTrackedObjectsRouteMetricUpThresh,
        etsysTrackedObjectsRouteMetricDownThresh,
        etsysTrackedObjectsRouteStatus
    }
    STATUS      current
    DESCRIPTION
        "This group defines the configuration parameters for tracking
         IP routes."
    ::= { etsysTrackedObjectsGroups 6 }

etsysTrackedObjectsPortGroup OBJECT-GROUP
    OBJECTS {
        etsysTrackedObjectsPortGroupMemberMax,
        etsysTrackedObjectsPortGroupMemberCount,
        etsysTrackedObjectsPortGroupStatus,
        etsysTrackedObjectsPortGroupName,
        etsysTrackedObjectsPortState
    }
    STATUS      current
    DESCRIPTION
        "This group defines the configuration parameters for tracking
         port groups."
    ::= { etsysTrackedObjectsGroups 7 }

etsysTrackedObjectsPortGroupThresh OBJECT-GROUP
    OBJECTS {
        etsysTrackedObjectsPortGroupUpCount,
        etsysTrackedObjectsPortGroupDownCount,
        etsysTrackedObjectsPortGroupUpThresh,
        etsysTrackedObjectsPortGroupDownThresh
    }
    STATUS      current
    DESCRIPTION
        "This group defines the threshold parameters for tracking port
         groups."
    ::= { etsysTrackedObjectsGroups 8 }

etsysTrackedObjectsProbeTsGroup OBJECT-GROUP
    OBJECTS {
        etsysTrackedObjectsProbeTsInterval,
        etsysTrackedObjectsProbeTsRecvWait,
        etsysTrackedObjectsProbeTsTOS,
        etsysTrackedObjectsProbeTsPCP
    }
    STATUS      current
    DESCRIPTION
        "This group defines the probe timestamp configuration
         parameters."
    ::= { etsysTrackedObjectsGroups 9 }

etsysTrackedObjectsPortIfSpeedGroup OBJECT-GROUP
    OBJECTS {
        etsysTrackedObjectsPortIfSpeedMemberMax,
        etsysTrackedObjectsPortIfSpeedMemberCount,
        etsysTrackedObjectsPortIfSpeedLow,
        etsysTrackedObjectsPortIfSpeedHigh,
        etsysTrackedObjectsPortIfSpeedStatus,
        etsysTrackedObjectsPortIfSpeedName
    }
    STATUS      current
    DESCRIPTION
        "This group defines the threshold parameters for tracking port
         if speed."
    ::= { etsysTrackedObjectsGroups 10 }

etsysTrackedObjectsGlobalGroup2 OBJECT-GROUP
    OBJECTS {
        etsysTrackedObjectsMaxObjects,
        etsysTrackedObjectsObjectsUsed,
        etsysTrackedObjectsMaxProbes,
        etsysTrackedObjectsProbesUsed,
        etsysTrackedObjectsMaxAcvProbes,
        etsysTrackedObjectsAcvProbesUsed,
        etsysTrackedObjectsMaxSessions,
        etsysTrackedObjectsSessionsUsed,
        etsysTrackedObjectsMaxIntfAssoc,
        etsysTrackedObjectsIntfAssocUsed
    }
    STATUS      current
    DESCRIPTION
        "This group defines information pertaining to the global
         resources used by Enterasys Tracked Objects."
    ::= { etsysTrackedObjectsGroups 11 }

-- -------------------------------------------------------------
-- Compliance statements
-- -------------------------------------------------------------

etsysTrackedObjectsCompliance MODULE-COMPLIANCE
    STATUS      deprecated
    DESCRIPTION
        "The compliance statement for devices that support
         etsysTrackedObjects."

    MODULE
        MANDATORY-GROUPS {
            etsysTrackedObjectsGlobalGroup,
            etsysTrackedObjectsProbeGroup,
            etsysTrackedObjectsSessionGroup
        }

        GROUP etsysTrackedObjectsCommonGroup
        DESCRIPTION
            "The etsysTrackedObjectsCommonGroup is mandatory only for
             the entities implementing at least one of the tracked
             objects features."

        GROUP etsysTrackedObjectsIfGroup
        DESCRIPTION
            "The etsysTrackedObjectsIfGroup is mandatory only for
             the entities implementing the Interface tracked objects
             feature."

        GROUP etsysTrackedObjectsRouteGroup
        DESCRIPTION
            "The etsysTrackedObjectsRouteGroup is mandatory only for
             the entities implementing the L3 route tracked objects
             feature."

        GROUP etsysTrackedObjectsPortGroup
        DESCRIPTION
            "The etsysTrackedObjectsPortGroup is mandatory only for
             the entities implementing the port-group tracked objects
             feature."

        GROUP etsysTrackedObjectsPortGroupThresh
        DESCRIPTION
            "The etsysTrackedObjectsPortGroupThresh group is mandatory
             only for the entities implementing the port-group tracked
             objects feature."
    ::= { etsysTrackedObjectsCompliances 1 }

etsysTrackedObjectsCompliance2 MODULE-COMPLIANCE
    STATUS      current
    DESCRIPTION
        "The compliance statement for devices that support
         etsysTrackedObjects."

    MODULE
        MANDATORY-GROUPS {
            etsysTrackedObjectsGlobalGroup2,
            etsysTrackedObjectsProbeGroup,
            etsysTrackedObjectsSessionGroup
        }

        -- -----------------------------------------------------
        -- OBJECTS
        -- -----------------------------------------------------
        OBJECT       etsysTrackedObjectsProbeType
        SYNTAX       INTEGER { icmp(1), udp(2), tcp(3) }
        WRITE-SYNTAX INTEGER { icmp(1), udp(2), tcp(3) }
        DESCRIPTION
            "Support for icmpTs is not required."

        OBJECT       etsysTrackedObjectsProbeStatus
        SYNTAX       RowStatus { active(1) }
        WRITE-SYNTAX RowStatus { createAndGo(4), destroy(6) }
        DESCRIPTION
            "Support for createAndWait and notInService is not required."

        OBJECT       etsysTrackedObjectsSessionState
        SYNTAX       INTEGER { up(1), down(2), pending(3), disabled(4) }
        DESCRIPTION
            "Support for collect is not required."

        OBJECT       etsysTrackedObjectsIntfStatus
        SYNTAX       RowStatus { active(1) }
        WRITE-SYNTAX RowStatus { createAndGo(4), destroy(6) }
        DESCRIPTION
            "Support for createAndWait and notInService is not required."

        OBJECT       etsysTrackedObjectsRouteStatus
        SYNTAX       RowStatus { active(1) }
        WRITE-SYNTAX RowStatus { createAndGo(4), destroy(6) }
        DESCRIPTION
            "Support for createAndWait and notInService is not required."

        OBJECT       etsysTrackedObjectsPortGroupStatus
        SYNTAX       RowStatus { active(1) }
        WRITE-SYNTAX RowStatus { createAndGo(4), destroy(6) }
        DESCRIPTION
            "Support for createAndWait and notInService is not required."

        OBJECT       etsysTrackedObjectsPortIfSpeedStatus
        SYNTAX       RowStatus { active(1) }
        WRITE-SYNTAX RowStatus { createAndGo(4), destroy(6) }
        DESCRIPTION
            "Support for createAndWait and notInService is not required."

        -- -----------------------------------------------------
        -- GROUPS
        -- -----------------------------------------------------
        GROUP etsysTrackedObjectsCommonGroup
        DESCRIPTION
            "The etsysTrackedObjectsCommonGroup is mandatory only for
             the entities implementing at least one of the tracked
             objects features."

        GROUP etsysTrackedObjectsIfGroup
        DESCRIPTION
            "The etsysTrackedObjectsIfGroup is mandatory only for
             the entities implementing the Interface tracked objects
             feature."

        GROUP etsysTrackedObjectsRouteGroup
        DESCRIPTION
            "The etsysTrackedObjectsRouteGroup is mandatory only for
             the entities implementing the L3 route tracked objects
             feature."

        GROUP etsysTrackedObjectsPortGroup
        DESCRIPTION
            "The etsysTrackedObjectsPortGroup is mandatory only for
             the entities implementing the port-group tracked objects
             feature."

        GROUP etsysTrackedObjectsPortGroupThresh
        DESCRIPTION
            "The etsysTrackedObjectsPortGroupThresh group is mandatory
             only for the entities implementing the port-group tracked
             objects feature."

        GROUP etsysTrackedObjectsProbeTsGroup
        DESCRIPTION
            "The etsysTrackedObjectsProbeTsGroup group is mandatory only
             for the entities implementing the probe timestamp feature."

        GROUP etsysTrackedObjectsPortIfSpeedGroup
        DESCRIPTION
            "The etsysTrackedObjectsPortIfSpeed group is mandatory
             only for the entities implementing the port-ifspeed tracked
             objects feature."
    ::= { etsysTrackedObjectsCompliances 2 }

END
