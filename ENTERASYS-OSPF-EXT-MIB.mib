ENTERASYS-OSPF-EXT-MIB DEFINITIONS ::= BEGIN

--  enterasys-ospf-ext-mib.txt
--
--  Part Number:
--
--

--  This module provides authoritative definitions for Enterasys
--  Networks' OSPF protocol.  This module extends the OSPF-MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2009 Enterasys Networks, Inc.

IMPORTS
    MODULE-IDENTITY, OBJECT-TYPE, Integer32, Counter32, Gauge32,
    Unsigned32, IpAddress, BITS
        FROM SNMPv2-SMI
    TEXTUAL-CONVENTION, TruthValue
        FROM SNMPv2-TC
    MODULE-COMPLIANCE, OBJECT-GROUP
        FROM SNMPv2-CONF
    SnmpAdminString
        FROM SNMP-FRAMEWORK-MIB
    InterfaceIndexOrZero
        FROM IF-MIB
    Status, AreaID, ospfAreaEntry, ospfIfEntry, ospfVirtIfEntry,
    ospfNbrEntry, ospfVirtNbrEntry, ospfLocalLsdbEntry
        FROM OSPF-MIB
    etsysModules
        FROM ENTERASYS-MIB-NAMES;

etsysOspfExtMIB MODULE-IDENTITY
    LAST-UPDATED "200902271934Z"  -- Fri Feb 27 19:34 UTC 2009
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"
    DESCRIPTION
        "This MIB module defines a portion of the SNMP MIB under
         the Enterasys Networks enterprise OID pertaining to
         the OSPF configuration.

         This MIB was designed to be used in conjunction with
         the OSPF-MIB (RFC 4750) for configuring the OSPF
         protocol parameters."

    REVISION     "200902271934Z"  -- Fri Feb 27 19:34 UTC 2009
    DESCRIPTION  "The initial version of this MIB module"
    ::= { etsysModules 65 }


-- Textual Conventions

EtsysOspfOperStatus ::= TEXTUAL-CONVENTION
    STATUS       current
    DESCRIPTION
        "The current operational state of the OSPF Protocol.

        operStatusUp       : Active state for the protocol.
        operStatusDown     : Inactive state for the protocol.
        operStatusGoingUp  : In this state, OSPF is in the process of
                             acquiring resources it needs to operate.
        operStatusGoingDown: In this state, OSPF is in the process of
                             releasing resources and cleaning up.
        operStatusActFailed: This state indicates that activiation
                             failed."
    SYNTAX       INTEGER {
                   operStatusUp(1),       -- active
                   operStatusDown(2),     -- inactive
                   operStatusGoingUp(3),  -- activating
                   operStatusGoingDown(4),-- deactivating
                   operStatusActFailed(5) -- activation failed
                 }

-- -------------------------------------------------------------
-- Branches
-- -------------------------------------------------------------
etsysOspfExtObjects  OBJECT IDENTIFIER ::= { etsysOspfExtMIB 1 }

etsysOspfExtGlobals  OBJECT IDENTIFIER ::= { etsysOspfExtObjects 1 }
etsysOspfExtTables   OBJECT IDENTIFIER ::= { etsysOspfExtObjects 2 }

-- -------------------------------------------------------------
-- MIB Objects
-- -------------------------------------------------------------

etsysOspfExtOperStatus OBJECT-TYPE
    SYNTAX      EtsysOspfOperStatus
    MAX-ACCESS  read-only
    STATUS      current
    DESCRIPTION
        "The current operational state of the OSPF Protocol.

        Changing the state of the ospfAdminStat object effects the state
        of this object.  If ospfAdminStat is set to 'disabled', this
        object's status is changed to 'operStatusGoingDown'.  Once all
        of the resources have been reclaimed, the status is changed to
        'operStatusDown'.

        If ospfAdminStat is set to 'enabled', this object's status is
        changed to 'operStatusGoingUp'.  When the OSPF protocol has
        finished the activation process, the state of this object changes
        to 'operStatusUp'.

        If there are problems activating the OSPF protocol, the status
        becomes 'operStatusActFailed'."
    ::= { etsysOspfExtGlobals 1 }

etsysOspfExtCalcMaxDelay OBJECT-TYPE
    SYNTAX       Unsigned32
    UNITS        "milliseconds"
    MAX-ACCESS   read-write
    STATUS       current
    DESCRIPTION
        "The maximum delay before the Routing Table is recalculated
        following a change to the Link State Database.  (Recalculation
        is delayed to reduce the frequency of recalculations of the
        Routing Table).

        This parameter has units of milliseconds.  A value of 0
        indicates that a routing calculation will immediately follow an
        update to the database."
    DEFVAL { 5000 }
    ::= { etsysOspfExtGlobals 2 }

etsysOspfExtCalcThrshUpdStart OBJECT-TYPE
    SYNTAX       Integer32 (-1|0|1..2147483647)
    MAX-ACCESS   read-write
    STATUS       current
    DESCRIPTION
        "This parameter can be used to override the
        etsysOspfExtCalcMaxDelay when the number of updates to the
        Link State Database reaches a threshold value.

        -1  Indicates that this threshold is infinite, and hence
            the timing of a routing calculation is determined solely by
            etsysOspfExtCalcMaxDelay.

        0   Indicates that a routing calculation will immediately
            follow an update to the database.

        1..2147483647
            Specifies the threshold number of updates that can be made
            to the Link State Database such that any subsequent update
            to the database causes a full routing calculation to start
            immediately."
    DEFVAL { -1 }
    ::= { etsysOspfExtGlobals 3 }

etsysOspfExtCalcThrshUpdRestart OBJECT-TYPE
    SYNTAX       Integer32 (-1|0|1..2147483647)
    MAX-ACCESS   read-write
    STATUS       current
    DESCRIPTION
        "This parameter can be used to interrupt a full routing
        calculation when the number of pending updates to the Link
        State Database has reached a threshold value.

        -1  Indicates that this threshold is infinite, and hence no
            number of pending updates to the database will cause a
            routing calculation to be interrupted.

        0   Indicates that an update to the Link State Database will
            cause any current routing calculation to be interrupted and
            a new one to start.

        1..2147483647
            Specifies the threshold number of updates that can be made
            to the Link State Database such that any subsequent update
            to the database causes the current routing calculation to be
            interrupted, and a new calculation to start using an up to
            date Link State Database."
    DEFVAL { -1 }
    ::= { etsysOspfExtGlobals 4 }

etsysOspfExtCalcThrshIncUpdates OBJECT-TYPE
    SYNTAX       Integer32 (-1|0|1..2147483647)
    MAX-ACCESS   read-write
    STATUS       current
    DESCRIPTION
        "This parameter can be used to optimize the performance of the
        Routing Calculator in the situation where updates that are
        pending to the Link State Database solely concern inter-area or
        AS-external routes.  In this case, the Routing Table can be
        updated either by one full recalculation, or by multiple
        incremental recalculations.

        This parameter is used to configure the threshold value for
        which recalculation by multiple incremental updates is no longer
        quicker than a single full recalculation.

        -1 Indicates that this threshold is infinite, and incremental
           recalculations are always done in preference to a full
           recalculation.

        0  Indicates that incremental updates will never be used.

        1..2147483647 (n)
          Indicates that a full recalculation will be performed whenever
          there are more than 'n' updates to make to inter-area
          or AS-external routes."
    DEFVAL { 50 }
    ::= { etsysOspfExtGlobals 5 }

etsysOspfExtCalcThrshIncSpfUpd OBJECT-TYPE
    SYNTAX       Integer32 (-1|0|1..2147483647)
    MAX-ACCESS   read-write
    STATUS       current
    DESCRIPTION
        "This parameter can be used to optimize the performance of the
        Routing Calculator in the situation where updates that are
        pending to the Link State Database concern intra-area routes.
        In this case, the Routing Table can be updated either by one
        full recalculation, or by multiple incremental SPF
        recalculations.

        This parameter is used to configure the threshold value for
        which recalculation by multiple incremental SPF updates is no
        longer quicker than a single full recalculation.

        -1 Indicates that this threshold is infinite, and incremental
           SPF recalculations are always done in preference to a full
           recalculation.

        0  Indicates that incremental SPF updates will never be used.

        1..2147483647 (n)
           Indicates that a full recalculation will be performed
           whenever there are more than 'n' updates to make to
           intra-area routes."
    DEFVAL { 0 }
    ::= { etsysOspfExtGlobals 6 }

etsysOspfExtCalcPauseFreq OBJECT-TYPE
    SYNTAX       Integer32 (-1|0|1..2147483647)
    MAX-ACCESS   read-write
    STATUS       current
    DESCRIPTION
        "This value determines how regularly a Routing Calculation is
        paused.  It is measured in points.  The points scale roughly
        maps to a time scale, so that the larger this value is, the
        longer the Routing Calculation runs before pausing.

        -1 Indicates that the Routing Calculation is never paused.

        0  Indicates that the routing calculation is paused after
           every calculation step."
    DEFVAL { 10000 }
    ::= { etsysOspfExtGlobals 7 }

etsysOspfExtRteMaxEqCostPaths OBJECT-TYPE
    SYNTAX       Unsigned32 (1..65535)
    MAX-ACCESS   read-write
    STATUS       current
    DESCRIPTION
        "The maximum number of equal cost paths that are stored for
        each destination in the Routing Table."
    DEFVAL { 5 }
    ::= { etsysOspfExtGlobals 8 }

etsysOspfExtCheckAge OBJECT-TYPE
    SYNTAX       Unsigned32
    UNITS        "seconds"
    MAX-ACCESS   read-write
    STATUS       current
    DESCRIPTION
        "This value determines how often the checksums of LSAs in the
        Link State Database are checked.  If 0, no checksums in the
        database are checked."
    DEFVAL { 300 }
    ::= { etsysOspfExtGlobals 9 }

etsysOspfExtExtLsaRfshIntvl OBJECT-TYPE
    SYNTAX       Unsigned32 (1..3599)
    UNITS        "seconds"
    MAX-ACCESS   read-write
    STATUS       current
    DESCRIPTION
        "Self-originated LSAs are periodically reflooded into the
        routing domain to add to the robustness of the OSPF protocol.
        This value determines the interval between refreshes of type-5
        and type-11 AS-external LSAs, and is defaulted to the OSPF
        standard default of 1800 seconds (30 minutes)."
    DEFVAL { 1800 }
    ::= { etsysOspfExtGlobals 10 }

etsysOspfExtExternOpLsaCount OBJECT-TYPE
    SYNTAX       Gauge32
    MAX-ACCESS   read-only
    STATUS       current
    DESCRIPTION
        "The number of type-11 LSAs in the external database."
    ::= { etsysOspfExtGlobals 11 }

etsysOspfExtExternOpLsaCksumSum OBJECT-TYPE
    SYNTAX       Unsigned32
    MAX-ACCESS   read-only
    STATUS       current
    DESCRIPTION
        "The 32 bit sum of LS checksums of all type-11 LSAs in the
        external Link State Database."
    ::= { etsysOspfExtGlobals 12 }

etsysOspfExtNumUpdPending OBJECT-TYPE
    SYNTAX       Gauge32
    MAX-ACCESS   read-only
    STATUS       current
    DESCRIPTION
        "The number of updates that are pending addition to the Link
        State Database."
    ::= { etsysOspfExtGlobals 13 }

etsysOspfExtNumUpdMerged OBJECT-TYPE
    SYNTAX       Gauge32
    MAX-ACCESS   read-only
    STATUS       current
    DESCRIPTION
        "The number of updates that have been merged into the Link
        State Database since the last routing calculation."
    ::= { etsysOspfExtGlobals 14 }

etsysOspfExtNumCksumsPending OBJECT-TYPE
    SYNTAX       Gauge32
    MAX-ACCESS   read-only
    STATUS       current
    DESCRIPTION
        "The number of LSAs in the Link State Database which are now
        due to have their checksum checked."
    ::= { etsysOspfExtGlobals 15 }

etsysOspfExtDoGraceHitless OBJECT-TYPE
    SYNTAX       TruthValue
    MAX-ACCESS   read-write
    STATUS       current
    DESCRIPTION
        "Indicates whether OSPF should perform hitless restart using
        grace LSAs.  If OSPF is being deactivated, grace LSAs are sent
        out to inform neighboring routers that we wish to undergo a
        hitless restart.

        If OSPF is being activated, we will attempt to restart
        hitlessly, then set this field to 'false'.  Therefore this field
        needs to be explicitly set to 'true' each time planned hitless
        restart is required.

        This object is persistent and when written the entity SHOULD
        save the change to non-volatile storage."
    DEFVAL { false }
    ::= { etsysOspfExtGlobals 16 }

etsysOspfExtDoGraceUnplannedHitless OBJECT-TYPE
    SYNTAX       TruthValue
    MAX-ACCESS   read-write
    STATUS       current
    DESCRIPTION
        "Indicates whether OSPF should perform an unplanned hitless
        restart using grace LSAs.  Note that etsysOspfExtDoGraceHitless
        has a higher priority than this object.  Therefore if both
        etsysOspfExtDoGraceHitless and this object are both set to
        'true' on activation, OSPF will assume it is undergoing a
        planned hitless restart.  If only this object is 'true', then
        OSPF will attempt an unplanned hitless restart, and send out
        grace LSAs on activation."
    DEFVAL { false }
    ::= { etsysOspfExtGlobals 17 }

etsysOspfExtHitlessGracePeriod OBJECT-TYPE
    SYNTAX       Unsigned32 (1..1800)
    UNITS        "seconds"
    MAX-ACCESS   read-write
    STATUS       current
    DESCRIPTION
        "If OSPF is attempting to undergo a hitless restart, this field
        specifies the length of grace period that should be requested
        from adjacent routers in grace LSAs.  After this timer period
        has passed, an RTM will delete routes from this RPM from its
        routing table, and so hitless restart will have failed.  Hitless
        grace period must be greater than zero."
    DEFVAL { 120 }
    ::= { etsysOspfExtGlobals 18 }


--
-- Enterasys OSPF Area Table (augments ospfAreaTable)
--
etsysOspfExtAreaTable OBJECT-TYPE
    SYNTAX       SEQUENCE OF EtsysOspfExtAreaEntry
    MAX-ACCESS   not-accessible
    STATUS       current
    DESCRIPTION
        "This table provides additional information pertaining to
        OSPF Areas for Enterasys OSPF systems."
    ::= { etsysOspfExtTables 1 }

etsysOspfExtAreaEntry OBJECT-TYPE
    SYNTAX       EtsysOspfExtAreaEntry
    MAX-ACCESS   not-accessible
    STATUS       current
    DESCRIPTION
        "An entry (conceptual row) in the etsysOspfExtAreaTable."
    AUGMENTS     { ospfAreaEntry }
    ::= { etsysOspfExtAreaTable 1 }

EtsysOspfExtAreaEntry ::= SEQUENCE {
    etsysOspfExtAreaAdminStatus              Status,
    etsysOspfExtAreaOperStatus               EtsysOspfOperStatus,
    etsysOspfExtAreaTransitCapability        TruthValue,
    etsysOspfExtAreaLsaRfshIntvl             Unsigned32,
    etsysOspfExtAreaRtrLsaCount              Gauge32,
    etsysOspfExtAreaRtrLsaCksumSum           Unsigned32,
    etsysOspfExtAreaNetLsaCount              Gauge32,
    etsysOspfExtAreaNetLsaCksumSum           Unsigned32,
    etsysOspfExtAreaSummLsaCount             Gauge32,
    etsysOspfExtAreaSummLsaCksumSum          Unsigned32,
    etsysOspfExtAreaSummAsLsaCount           Gauge32,
    etsysOspfExtAreaSummAsLsaCksumSum        Unsigned32,
    etsysOspfExtAreaNssaLsaCount             Gauge32,
    etsysOspfExtAreaNssaLsaCksumSum          Unsigned32,
    etsysOspfExtAreaOpLsaCount               Gauge32,
    etsysOspfExtAreaOpLsaCksumSum            Unsigned32
}

etsysOspfExtAreaAdminStatus OBJECT-TYPE
    SYNTAX       Status
    MAX-ACCESS   read-create
    STATUS       current
    DESCRIPTION
        "The desired administrative state of this OSPF area.

        When the status of this object is set to 'disabled', no
        flooding will occur for routes in this area and all routes
        for this area are removed from the RIB.

        When the status of this object is set to 'enabled', flooding
        occurs for this area, and routes are added to the RIB.

        This object needs to be 'disabled' in order to modify the
        ospfImportAsExtern object."
    DEFVAL { enabled }
    ::= { etsysOspfExtAreaEntry 1 }

etsysOspfExtAreaOperStatus OBJECT-TYPE
    SYNTAX       EtsysOspfOperStatus
    MAX-ACCESS   read-only
    STATUS       current
    DESCRIPTION
        "The current operational state of this OSPF area."
    ::= { etsysOspfExtAreaEntry 2 }

etsysOspfExtAreaTransitCapability OBJECT-TYPE
    SYNTAX       TruthValue
    MAX-ACCESS   read-only
    STATUS       current
    DESCRIPTION
        "This parameter indicates whether the area can carry data
        traffic that neither originates nor terminates in the area
        itself.  This parameter is calculated when the area's
        shortest-path tree is built."
    DEFVAL { false }
    ::= { etsysOspfExtAreaEntry 3 }

etsysOspfExtAreaLsaRfshIntvl OBJECT-TYPE
    SYNTAX       Unsigned32 (1..3599)
    UNITS        "seconds"
    MAX-ACCESS   read-create
    STATUS       current
    DESCRIPTION
        "Self-originated LSAs are periodically reflooded into the
        routing domain, to add to the robustness of the OSPF protocol.
        This value determines the interval between refreshes of LSAs
        in this area, and is defaulted to the OSPF standard default of
        1800 seconds (30 minutes)."
    DEFVAL { 1800 }
    ::= { etsysOspfExtAreaEntry 4 }

etsysOspfExtAreaRtrLsaCount OBJECT-TYPE
    SYNTAX       Gauge32
    MAX-ACCESS   read-only
    STATUS       current
    DESCRIPTION
        "The number of LSAs with LS type-1 in this area's Link State
        Database."
    ::= { etsysOspfExtAreaEntry 5 }

etsysOspfExtAreaRtrLsaCksumSum OBJECT-TYPE
    SYNTAX       Unsigned32
    MAX-ACCESS   read-only
    STATUS       current
    DESCRIPTION
        "The 32 bit sum of LS checksums of all LSAs with LS type-1 in
        this area's Link State Database."
    ::= { etsysOspfExtAreaEntry 6 }

etsysOspfExtAreaNetLsaCount OBJECT-TYPE
    SYNTAX       Gauge32
    MAX-ACCESS   read-only
    STATUS       current
    DESCRIPTION
        "The number of LSAs with LS type-2 in this area's Link State
        Database."
    ::= { etsysOspfExtAreaEntry 7 }

etsysOspfExtAreaNetLsaCksumSum OBJECT-TYPE
    SYNTAX       Unsigned32
    MAX-ACCESS   read-only
    STATUS       current
    DESCRIPTION
        "The 32 bit sum of LS checksums of all LSAs with LS type-2 in
        this area's Link State Database."
    ::= { etsysOspfExtAreaEntry 8 }

etsysOspfExtAreaSummLsaCount OBJECT-TYPE
    SYNTAX       Gauge32
    MAX-ACCESS   read-only
    STATUS       current
    DESCRIPTION
        "The number of LSAs with LS type-3 in this area's Link State
        Database."
    ::= { etsysOspfExtAreaEntry 9 }

etsysOspfExtAreaSummLsaCksumSum OBJECT-TYPE
    SYNTAX       Unsigned32
    MAX-ACCESS   read-only
    STATUS       current
    DESCRIPTION
        "The 32 bit sum of LS checksums of all LSAs with LS type-3 in
        this area's Link State Database."
    ::= { etsysOspfExtAreaEntry 10 }

etsysOspfExtAreaSummAsLsaCount OBJECT-TYPE
    SYNTAX       Gauge32
    MAX-ACCESS   read-only
    STATUS       current
    DESCRIPTION
        "The number of LSAs with LS type-4 in this area's Link State
        Database."
    ::= { etsysOspfExtAreaEntry 11 }

etsysOspfExtAreaSummAsLsaCksumSum OBJECT-TYPE
    SYNTAX       Unsigned32
    MAX-ACCESS   read-only
    STATUS       current
    DESCRIPTION
        "The 32 bit sum of LS checksums of all LSAs with LS type-4 in
        this area's Link State Database."
    ::= { etsysOspfExtAreaEntry 12 }

etsysOspfExtAreaNssaLsaCount OBJECT-TYPE
    SYNTAX       Gauge32
    MAX-ACCESS   read-only
    STATUS       current
    DESCRIPTION
        "The number of LSAs with LS type-7 in this area's Link State
        Database."
    ::= { etsysOspfExtAreaEntry 13 }

etsysOspfExtAreaNssaLsaCksumSum OBJECT-TYPE
    SYNTAX       Unsigned32
    MAX-ACCESS   read-only
    STATUS       current
    DESCRIPTION
        "The 32 bit sum of LS checksums of all LSAs with LS type-7 in
        this area's Link State Database."
    ::= { etsysOspfExtAreaEntry 14 }

etsysOspfExtAreaOpLsaCount OBJECT-TYPE
    SYNTAX       Gauge32
    MAX-ACCESS   read-only
    STATUS       current
    DESCRIPTION
        "The number of LSAs with LS type-10 in this area's Link State
        Database."
    ::= { etsysOspfExtAreaEntry 15 }

etsysOspfExtAreaOpLsaCksumSum OBJECT-TYPE
    SYNTAX       Unsigned32
    MAX-ACCESS   read-only
    STATUS       current
    DESCRIPTION
        "The 32 bit sum of LS checksums of all LSAs with LS type-10 in
        this area's Link State Database."
    ::= { etsysOspfExtAreaEntry 16 }

--
-- Enterasys OSPF if Table (augments ospfIfTable)
--
etsysOspfExtIfTable OBJECT-TYPE
    SYNTAX       SEQUENCE OF EtsysOspfExtIfEntry
    MAX-ACCESS   not-accessible
    STATUS       current
    DESCRIPTION
        "This table provides additional information pertaining to
        OSPF Interfaces for Enterasys OSPF systems."
    ::= { etsysOspfExtTables 2 }

etsysOspfExtIfEntry OBJECT-TYPE
    SYNTAX       EtsysOspfExtIfEntry
    MAX-ACCESS   not-accessible
    STATUS       current
    DESCRIPTION
        "An entry (conceptual row) in the etsysOspfExtIfTable."
    AUGMENTS     { ospfIfEntry }
    ::= { etsysOspfExtIfTable 1 }

EtsysOspfExtIfEntry ::= SEQUENCE {
    etsysOspfExtIfOperStatus                 EtsysOspfOperStatus,
    etsysOspfExtIfNetMask                    IpAddress,
    etsysOspfExtIfTransmitTimerDelay         Unsigned32,
    etsysOspfExtIfIPMaxPacketSize            Unsigned32,
    etsysOspfExtIfPassive                    TruthValue,
    etsysOspfExtIfLsaRefreshIntvl            Unsigned32,
    etsysOspfExtIfHelperModePolicy           BITS,
    etsysOspfExtIfMaxHitlessGracePeriod      Unsigned32,
    etsysOspfExtIfAuthUserData               OCTET STRING,
    etsysOspfExtIfFastHelloMultiplier        Unsigned32,
    etsysOspfExtIfAutoDeleteNbr              TruthValue,
    etsysOspfExtIfMtuIgnore                  TruthValue
}

etsysOspfExtIfOperStatus OBJECT-TYPE
    SYNTAX       EtsysOspfOperStatus
    MAX-ACCESS   read-only
    STATUS       current
    DESCRIPTION
        "The current operational state of OSPF on this interface."
    ::= { etsysOspfExtIfEntry 1 }

etsysOspfExtIfNetMask OBJECT-TYPE
    SYNTAX       IpAddress
    MAX-ACCESS   read-create
    STATUS       current
    DESCRIPTION
        "The subnet mask associated with the IP address of this entry.
        The value of the mask is an IP address with all the network bits
        set to 1 and all the hosts bits set to 0."
    ::= { etsysOspfExtIfEntry 2 }

etsysOspfExtIfTransmitTimerDelay OBJECT-TYPE
    SYNTAX       Unsigned32
    UNITS        "milliseconds"
    MAX-ACCESS   read-create
    STATUS       current
    DESCRIPTION
        "The time this interface will delay a LSU packet, in order to
        add more LSAs to the packet before sending.  Setting this
        correctly can reduce the network traffic.  This is configurable
        on a per-interface basis."
    DEFVAL { 100 }
    ::= { etsysOspfExtIfEntry 3 }

etsysOspfExtIfIPMaxPacketSize OBJECT-TYPE
    SYNTAX       Unsigned32
    MAX-ACCESS   read-create
    STATUS       current
    DESCRIPTION
        "Maximum transfer unit (MTU) for the network interface.

        This is the maximum packet size in bytes for packets sent over
        the network interface.  This size excludes link layer headers
        but includes IP headers and higher-level headers.

        Normally, OSPF limits sent PDUs (protocol data units) to less
        than or equal to this size.  However, if OSPF cannot construct
        a valid PDU smaller than or equal to this size, then it will
        send the smallest valid PDU and assume that the IP stack will
        fragment the packet."
    DEFVAL { 576 }
    ::= { etsysOspfExtIfEntry 4 }

etsysOspfExtIfPassive OBJECT-TYPE
    SYNTAX       TruthValue
    MAX-ACCESS   read-create
    STATUS       current
    DESCRIPTION
        "Indicates whether this interface is a passive interface.  If
        set to 'true', we suppress HELLO packets sent on and received
        from this interface.  We will therefore advertise this interface
        in our LSAs but not run the OSPF protocol over it."
    DEFVAL { false }
    ::= { etsysOspfExtIfEntry 5 }

etsysOspfExtIfLsaRefreshIntvl OBJECT-TYPE
    SYNTAX       Unsigned32 (1..3599)
    UNITS        "seconds"
    MAX-ACCESS   read-create
    STATUS       current
    DESCRIPTION
        "Self-originated LSAs are periodically reflooded into the
        routing domain, to add to the robustness of the OSPF protocol.
        This value determines the interval between refreshes of LSAs that
        are only flooded over this interface (type-9 opaque LSAs) and is
        defaulted to the OSPF standard default of 1800 seconds
        (30 minutes)."
    DEFVAL { 1800 }
    ::= { etsysOspfExtIfEntry 6 }

etsysOspfExtIfHelperModePolicy OBJECT-TYPE
    SYNTAX       BITS {
                     reasonUnknown(0),
                     reasonSoftwareRestart(1),
                     reasonSoftwareReload(2),
                     reasonSwitchToBackup(3)
                 }
    MAX-ACCESS   read-create
    STATUS       current
    DESCRIPTION
        "Indicates whether OSPF will help a neighbor undergoing
        hitless restart on this interface for the specified reason. This
        field contains a bit flag for each of OspfHitlessRestartReasons.
        If a bit flag for a specific restart reason is set, then OSPF
        will help a router restarting for this reason. Otherwise grace
        LSAs received containing this restart reason will be ignored."
    DEFVAL { { reasonUnknown, reasonSoftwareRestart,
               reasonSoftwareReload, reasonSwitchToBackup } }
    ::= { etsysOspfExtIfEntry 7 }

etsysOspfExtIfMaxHitlessGracePeriod OBJECT-TYPE
    SYNTAX       Unsigned32
    UNITS        "seconds"
    MAX-ACCESS   read-create
    STATUS       current
    DESCRIPTION
        "If configured to help neighbors undergoing hitless restart on
        this interface, this field indicates the maximum grace period
        that will be allowed for a neighboring router undergoing hitless
        restart.  If a type-9 grace LSA is received with a greater
        requested grace period, then the grace LSA will be ignored."
    DEFVAL { 120 }
    ::= { etsysOspfExtIfEntry 8 }

etsysOspfExtIfAuthUserData  OBJECT-TYPE
    SYNTAX      OCTET STRING (SIZE (0..4))
    MAX-ACCESS  read-create
    STATUS      current
    DESCRIPTION
        "Authentication user data for interface level authentication.

        This data is passed opaquely to the authentication process,
        where it can be used to assist with authentication decisions.

        When read, etsysOspfExtIfAuthUserData always returns an Octet
        String of length zero."
    DEFVAL { '00'H }
    ::= { etsysOspfExtIfEntry 9 }

etsysOspfExtIfFastHelloMultiplier OBJECT-TYPE
    SYNTAX       Unsigned32 (3..20)
    MAX-ACCESS   read-create
    STATUS       current
    DESCRIPTION
        "The number of Hellos that should be sent within 1 second when
        using Fast Hellos on this interface.  This value does not have
        to be same for all routers attached to a common network, but it
        is advisable.  Fast Hellos are configured using
        ospfIfRtrDeadInterval."
    DEFVAL { 5 }
    ::= { etsysOspfExtIfEntry 10 }

etsysOspfExtIfAutoDeleteNbr OBJECT-TYPE
    SYNTAX       TruthValue
    MAX-ACCESS   read-create
    STATUS       current
    DESCRIPTION
        "Whether dynamically created entries in the ospfNbrTable
        should be kept when the adjacency goes down.

        If this object is set to 'false', then a dynamically created
        entry in the ospfNbrTable will remain with state 'down' when
        the adjacency is lost.  Such entries can be deleted manually
        by setting ospfNbrStatus to 'destroy'.

        If this object is set to 'true', then dynamically created
        entries in the ospfNbrTable will be deleted automatically
        when the adjacency goes down."
    DEFVAL { true }
    ::= { etsysOspfExtIfEntry 11 }

etsysOspfExtIfMtuIgnore OBJECT-TYPE
    SYNTAX       TruthValue
    MAX-ACCESS   read-create
    STATUS       current
    DESCRIPTION
        "This object controls whether OSPF checks the MTU size on
        incoming Database Description packets.  By default, if the
        received MTU size in a DB Description packet is higher than
        the MTU size configured on the incoming interface, the OSPF
        adjacency will not be established.  If the interface is
        tunneled over, say, an MPLS network, then the administrator
        may not know the maximum MTU size and so can tell OSPF to
        ignore the MTU size on incoming DB description packets."
    DEFVAL { false }
    ::= { etsysOspfExtIfEntry 12 }

--
-- Enterasys OSPF Virtual if Table (augments ospfVirtIfTable)
--
etsysOspfExtVirtIfTable OBJECT-TYPE
    SYNTAX       SEQUENCE OF EtsysOspfExtVirtIfEntry
    MAX-ACCESS   not-accessible
    STATUS       current
    DESCRIPTION
        "This table provides additional information pertaining to
        OSPF Virtual Interfaces for Enterasys OSPF systems."
    ::= { etsysOspfExtTables 3 }

etsysOspfExtVirtIfEntry OBJECT-TYPE
    SYNTAX       EtsysOspfExtVirtIfEntry
    MAX-ACCESS   not-accessible
    STATUS       current
    DESCRIPTION
        "An entry (conceptual row) in the etsysOspfExtVirtIfTable."
    AUGMENTS     { ospfVirtIfEntry }
    ::= { etsysOspfExtVirtIfTable 1 }

EtsysOspfExtVirtIfEntry ::= SEQUENCE {
    etsysOspfExtVirtIfAdminStatus            Status,
    etsysOspfExtVirtIfOperStatus             EtsysOspfOperStatus,
    etsysOspfExtVirtIfTransmitTimerDelay     Unsigned32,
    etsysOspfExtVirtIfIPMaxPacketSize        Unsigned32,
    etsysOspfExtVirtIfPassive                TruthValue,
    etsysOspfExtVirtIfLsaRefreshIntvl        Unsigned32,
    etsysOspfExtVirtIfHelperModePolicy       BITS,
    etsysOspfExtVirtIfMaxHtlssGracePeriod    Unsigned32,
    etsysOspfExtVirtIfFastHelloMultiplier    Unsigned32,
    etsysOspfExtVirtIfMtuIgnore              TruthValue
}

etsysOspfExtVirtIfAdminStatus OBJECT-TYPE
    SYNTAX       Status
    MAX-ACCESS   read-create
    STATUS       current
    DESCRIPTION
        "The desired administrative state of this virtual interface.

        When the status of this object is set to 'disabled', the
        virtual link is torn down and no routing information is
        exchanged with its peer.

        When the status of this object is set to 'enabled', the
        virtual link is established (if possible) and routing
        information is shared with its peer.  The
        etsysOspfExtVirtIfOperStatus object provides the status of
        this connection."
    DEFVAL { enabled }
    ::= { etsysOspfExtVirtIfEntry 1 }

etsysOspfExtVirtIfOperStatus OBJECT-TYPE
    SYNTAX       EtsysOspfOperStatus
    MAX-ACCESS   read-only
    STATUS       current
    DESCRIPTION
        "The current operational state of OSPF on this virtual
        interface."
    ::= { etsysOspfExtVirtIfEntry 2 }

etsysOspfExtVirtIfTransmitTimerDelay OBJECT-TYPE
    SYNTAX       Unsigned32
    UNITS        "milliseconds"
    MAX-ACCESS   read-create
    STATUS       current
    DESCRIPTION
        "The time this interface will delay a LSU packet, in order to
        add more LSAs to the packet before sending.  Setting this
        correctly can reduce the network traffic.  This is configurable
        on a per-interface basis."
    DEFVAL { 100 }
    ::= { etsysOspfExtVirtIfEntry 3 }

etsysOspfExtVirtIfIPMaxPacketSize OBJECT-TYPE
    SYNTAX       Unsigned32
    MAX-ACCESS   read-create
    STATUS       current
    DESCRIPTION
        "Maximum transfer unit (MTU) for the network interface.

        This is the maximum packet size in bytes for packets sent over
        the network interface.  This size excludes link layer headers
        but includes IP headers and higher-level headers.

        Normally, OSPF limits sent PDUs (protocol data units) to less
        than or equal to this size.  However, if OSPF cannot construct
        a valid PDU smaller than or equal to this size, then it will
        send the smallest valid PDU and assume that the IP stack will
        fragment the packet."
    DEFVAL { 576 }
    ::= { etsysOspfExtVirtIfEntry 4 }

etsysOspfExtVirtIfPassive OBJECT-TYPE
    SYNTAX       TruthValue
    MAX-ACCESS   read-create
    STATUS       current
    DESCRIPTION
        "Indicates whether this interface is a passive interface.  If
        set to 'true', we suppress HELLO packets sent on and received
        from this interface.  We will therefore advertise this interface
        in our LSAs but not run the OSPF protocol over it."
    DEFVAL { false }
    ::= { etsysOspfExtVirtIfEntry 5 }

etsysOspfExtVirtIfLsaRefreshIntvl OBJECT-TYPE
    SYNTAX       Unsigned32 (1..3599)
    UNITS        "seconds"
    MAX-ACCESS   read-create
    STATUS       current
    DESCRIPTION
        "Self-originated LSAs are periodically reflooded into the
        routing domain, to add to the robustness of the OSPF protocol.
        This value determines the interval between refreshes of LSAs
        that are only flooded over this interface (type-9 opaque LSAs)
        and is defaulted to the OSPF standard default of 1800 seconds
        (30 minutes)."
    DEFVAL { 1800 }
    ::= { etsysOspfExtVirtIfEntry 6 }

etsysOspfExtVirtIfHelperModePolicy OBJECT-TYPE
    SYNTAX       BITS {
                     reasonUnknown(0),
                     reasonSoftwareRestart(1),
                     reasonSoftwareReload(2),
                     reasonSwitchToBackup(3)
                 }
    MAX-ACCESS   read-create
    STATUS       current
    DESCRIPTION
        "Indicates whether OSPF will help a neighbor undergoing
        hitless restart on this interface for the specified reason. This
        field contains a bit flag for each of OspfHitlessRestartReasons.
        If a bit flag for a specific restart reason is set, then OSPF
        will help a router restarting for this reason. Otherwise grace
        LSAs received containing this restart reason will be ignored."
    DEFVAL { { } }
    ::= { etsysOspfExtVirtIfEntry 7 }

etsysOspfExtVirtIfMaxHtlssGracePeriod OBJECT-TYPE
    SYNTAX       Unsigned32
    UNITS        "seconds"
    MAX-ACCESS   read-create
    STATUS       current
    DESCRIPTION
        "If configured to help neighbors undergoing hitless restart on
        this interface, this field indicates the maximum grace period
        that will be allowed for a neighboring router undergoing hitless
        restart.  If a  type-9 grace LSA is received with a greater
        requested grace period, then the grace LSA will be ignored."
    DEFVAL { 120 }
    ::= { etsysOspfExtVirtIfEntry 8 }

etsysOspfExtVirtIfFastHelloMultiplier OBJECT-TYPE
    SYNTAX       Unsigned32 (3..20)
    MAX-ACCESS   read-create
    STATUS       current
    DESCRIPTION
        "The number of Hellos that should be sent within 1 second when
        using Fast Hellos on this interface.  This value does not have
        to be same for all routers attached to a common network, but it
        is advisable.  Fast Hellos are configured using
        ospfVirtIfRtrDeadInterval."
    DEFVAL { 5 }
    ::= { etsysOspfExtVirtIfEntry 9 }

etsysOspfExtVirtIfMtuIgnore OBJECT-TYPE
    SYNTAX       TruthValue
    MAX-ACCESS   read-create
    STATUS       current
    DESCRIPTION
        "This object controls whether OSPF checks the MTU size on
        incoming Database Description packets.  By default, if the
        received MTU size in a DB Description packet is higher than
        the MTU size configured on the incoming interface, the OSPF
        adjacency will not be established.  If the interface is
        tunneled over, say, an MPLS network, then the administrator
        may not know the maximum MTU size and so can tell OSPF to
        ignore the MTU size on incoming DB description packets."
    DEFVAL { false }
    ::= { etsysOspfExtVirtIfEntry 10 }

--
-- Enterasys OSPF Neighbor Table (augments ospfNbrTable)
--
etsysOspfExtNbrTable OBJECT-TYPE
    SYNTAX       SEQUENCE OF EtsysOspfExtNbrEntry
    MAX-ACCESS   not-accessible
    STATUS       current
    DESCRIPTION
        "This table provides additional information pertaining to
        OSPF Neighbors for Enterasys OSPF systems."
    ::= { etsysOspfExtTables 4 }

etsysOspfExtNbrEntry OBJECT-TYPE
    SYNTAX       EtsysOspfExtNbrEntry
    MAX-ACCESS   not-accessible
    STATUS       current
    DESCRIPTION
        "An entry (conceptual row) in the etsysOspfExtNbrTable."
    AUGMENTS     { ospfNbrEntry }
    ::= { etsysOspfExtNbrTable 1 }

EtsysOspfExtNbrEntry ::= SEQUENCE {
    etsysOspfExtNbrAdminStatus               Status,
    etsysOspfExtNbrOperStatus                EtsysOspfOperStatus,
    etsysOspfExtNbrNumRequests               Gauge32,
    etsysOspfExtNbrIfIpAddr                  IpAddress,
    etsysOspfExtNbrDeadTime                  Unsigned32,
    etsysOspfExtNbrAreaId                    AreaID
}

etsysOspfExtNbrAdminStatus OBJECT-TYPE
    SYNTAX       Status
    MAX-ACCESS   read-create
    STATUS       current
    DESCRIPTION
        "The desired administrative state of this neighbor.

        When the status of this object is set to 'disabled', the
        connection to the neighbor is torn down and the routes
        learned from this neighbor are removed from the RIB.

        When the status of this object is set to 'enabled', the
        connection to the neighbor is established (if possible) and
        routes learned from the neighbor are added to the RIB."
    DEFVAL { enabled }
    ::= { etsysOspfExtNbrEntry 1 }

etsysOspfExtNbrOperStatus OBJECT-TYPE
    SYNTAX       EtsysOspfOperStatus
    MAX-ACCESS   read-only
    STATUS       current
    DESCRIPTION
        "The current operational state of this neighbor."
    ::= { etsysOspfExtNbrEntry 2 }

etsysOspfExtNbrNumRequests OBJECT-TYPE
    SYNTAX       Gauge32
    MAX-ACCESS   read-only
    STATUS       current
    DESCRIPTION
        "The number of LSAs requested from this neighbor for which we
        are awaiting for a response.  This field is incremented when an
        LSA is requested by sending a LS request packet and is
        decremented when the LSA arrives in a LS update packet."
    ::= { etsysOspfExtNbrEntry 3 }

etsysOspfExtNbrIfIpAddr OBJECT-TYPE
    SYNTAX       IpAddress
    MAX-ACCESS   read-create
    STATUS       current
    DESCRIPTION
        "The IP address of the interface used for this neighbor.  If
        this value is set to zero OSPF will choose a suitable interface
        to use.  If this value is non-zero this neighbor will only be
        associated with an exactly matching interface.

        Note this field is only used for NBMA and P2MP links.  Also,
        the etsysOspfExtNbrAdminStatus object must be 'disabled' prior
        to modifiying this object."
    DEFVAL { '00000000'H } -- 0.0.0.0
    ::= { etsysOspfExtNbrEntry 4 }

etsysOspfExtNbrDeadTime OBJECT-TYPE
    SYNTAX          Unsigned32 (1..2147483647)
    UNITS           "seconds"
    MAX-ACCESS      read-only
    STATUS          current
    DESCRIPTION
        "The time remaining in seconds within which we need to receive
        a hello packet from the neighbor or we declare the adjacency
        down.  If fast hellos area in use, this value is always set to
        1.  If the etsysOspfExtNbrOperStatus is down or ospfNbrState is
        DOWN, then the value is set to zero and the field is not valid."
    ::= { etsysOspfExtNbrEntry 5 }

etsysOspfExtNbrAreaId OBJECT-TYPE
    SYNTAX          AreaID
    MAX-ACCESS      read-only
    STATUS          current
    DESCRIPTION
        "The area to which the neighbor belongs. If the
        etsysOspfExtNbrOperStatus is down, then this value is set to
        zero and the field is not valid."
    ::= { etsysOspfExtNbrEntry 6 }

--
-- Enterasys OSPF Virtual Neighbor Table (augments ospfVirtNbrTable)
--
etsysOspfExtVirtNbrTable OBJECT-TYPE
    SYNTAX       SEQUENCE OF EtsysOspfExtVirtNbrEntry
    MAX-ACCESS   not-accessible
    STATUS       current
    DESCRIPTION
        "This table provides additional information pertaining to
        OSPF Virtual Neighbors for Enterasys OSPF systems."
    ::= { etsysOspfExtTables 5 }

etsysOspfExtVirtNbrEntry OBJECT-TYPE
    SYNTAX       EtsysOspfExtVirtNbrEntry
    MAX-ACCESS   not-accessible
    STATUS       current
    DESCRIPTION
        "An entry (conceptual row) in the etsysOspfExtVirtNbrTable."
    AUGMENTS     { ospfVirtNbrEntry }
    ::= { etsysOspfExtVirtNbrTable 1 }

EtsysOspfExtVirtNbrEntry ::= SEQUENCE {
    etsysOspfExtVirtNbrNumRequests           Gauge32,
    etsysOspfExtVirtNbrDeadTime              Unsigned32
}

etsysOspfExtVirtNbrNumRequests OBJECT-TYPE
    SYNTAX       Gauge32
    MAX-ACCESS   read-only
    STATUS       current
    DESCRIPTION
        "The number of LSAs requested from this neighbor for which we
        are awaiting for a response.  This field is incremented when an
        LSA is requested by sending a LS request packet and is
        decremented when the LSA arrives in an LS update packet."
    ::= { etsysOspfExtVirtNbrEntry 1 }

etsysOspfExtVirtNbrDeadTime OBJECT-TYPE
    SYNTAX          Unsigned32 (1..2147483647)
    MAX-ACCESS      read-only
    STATUS          current
    DESCRIPTION
        "The time remaining in seconds within which we need to receive
        a hello packet from the neighbor or we declare the adjacency
        down.  If fast hellos area in use, this value is always set
        to 1."
    ::= { etsysOspfExtVirtNbrEntry 2 }

--
-- Enterasys OSPF Local LSDB Area Table (augments ospfLocalLsdbTable)
--
etsysOspfExtLocalLsdbTable OBJECT-TYPE
    SYNTAX       SEQUENCE OF EtsysOspfExtLocalLsdbEntry
    MAX-ACCESS   not-accessible
    STATUS       current
    DESCRIPTION
        "This table provides additional information pertaining to
        OSPF Local LS Database for Enterasys OSPF systems."
    ::= { etsysOspfExtTables 6 }

etsysOspfExtLocalLsdbEntry OBJECT-TYPE
    SYNTAX       EtsysOspfExtLocalLsdbEntry
    MAX-ACCESS   not-accessible
    STATUS       current
    DESCRIPTION
        "An entry (conceptual row) in the etsysOspfExtLocalLsdbTable."
    AUGMENTS     { ospfLocalLsdbEntry }
    ::= { etsysOspfExtLocalLsdbTable 1 }

EtsysOspfExtLocalLsdbEntry ::= SEQUENCE {
    etsysOspfExtLocalLsdbAreaId              AreaID
}

etsysOspfExtLocalLsdbAreaId OBJECT-TYPE
    SYNTAX          AreaID
    MAX-ACCESS      read-only
    STATUS          current
    DESCRIPTION
        "The OSPF area in which the link belongs."
    ::= { etsysOspfExtLocalLsdbEntry 1 }


-- -------------------------------------------------------------
-- Conformance Information
-- -------------------------------------------------------------

etsysOspfExtConformance OBJECT IDENTIFIER ::= { etsysOspfExtMIB 2 }

etsysOspfExtGroups
    OBJECT IDENTIFIER ::= { etsysOspfExtConformance 1 }
etsysOspfExtCompliances
    OBJECT IDENTIFIER ::= { etsysOspfExtConformance 2 }

-- -------------------------------------------------------------
-- Units of conformance
-- -------------------------------------------------------------

etsysOspfExtGlobalGroup OBJECT-GROUP
    OBJECTS {
        etsysOspfExtOperStatus,
        etsysOspfExtCalcMaxDelay,
        etsysOspfExtCalcThrshUpdStart,
        etsysOspfExtCalcThrshUpdRestart,
        etsysOspfExtCalcThrshIncUpdates,
        etsysOspfExtCalcThrshIncSpfUpd,
        etsysOspfExtCalcPauseFreq,
        etsysOspfExtRteMaxEqCostPaths,
        etsysOspfExtCheckAge,
        etsysOspfExtExtLsaRfshIntvl,
        etsysOspfExtExternOpLsaCount,
        etsysOspfExtExternOpLsaCksumSum,
        etsysOspfExtNumUpdPending,
        etsysOspfExtNumUpdMerged,
        etsysOspfExtNumCksumsPending,
        etsysOspfExtDoGraceHitless,
        etsysOspfExtDoGraceUnplannedHitless,
        etsysOspfExtHitlessGracePeriod
    }
    STATUS      current
    DESCRIPTION
        "This group defines global controls for Enterasys OSPF systems."
    ::= { etsysOspfExtGroups 1 }

etsysOspfExtAreaGroup OBJECT-GROUP
    OBJECTS {
        etsysOspfExtAreaAdminStatus,
        etsysOspfExtAreaOperStatus,
        etsysOspfExtAreaTransitCapability,
        etsysOspfExtAreaLsaRfshIntvl,
        etsysOspfExtAreaRtrLsaCount,
        etsysOspfExtAreaRtrLsaCksumSum,
        etsysOspfExtAreaNetLsaCount,
        etsysOspfExtAreaNetLsaCksumSum,
        etsysOspfExtAreaSummLsaCount,
        etsysOspfExtAreaSummLsaCksumSum,
        etsysOspfExtAreaSummAsLsaCount,
        etsysOspfExtAreaSummAsLsaCksumSum,
        etsysOspfExtAreaNssaLsaCount,
        etsysOspfExtAreaNssaLsaCksumSum,
        etsysOspfExtAreaOpLsaCount,
        etsysOspfExtAreaOpLsaCksumSum
    }
    STATUS      current
    DESCRIPTION
        "This group defines the additional OSPF Area objects supported
        in the Enterasys OSPF systems."
    ::= { etsysOspfExtGroups 2 }

etsysOspfExtIfGroup OBJECT-GROUP
    OBJECTS {
        etsysOspfExtIfOperStatus,
        etsysOspfExtIfNetMask,
        etsysOspfExtIfTransmitTimerDelay,
        etsysOspfExtIfIPMaxPacketSize,
        etsysOspfExtIfPassive,
        etsysOspfExtIfLsaRefreshIntvl,
        etsysOspfExtIfHelperModePolicy,
        etsysOspfExtIfMaxHitlessGracePeriod,
        etsysOspfExtIfAuthUserData,
        etsysOspfExtIfFastHelloMultiplier,
        etsysOspfExtIfAutoDeleteNbr,
        etsysOspfExtIfMtuIgnore
    }
    STATUS      current
    DESCRIPTION
        "This group defines the additional OSPF Interface objects
        supported in the Enterasys OSPF systems."
    ::= { etsysOspfExtGroups 3 }

etsysOspfExtVirtIfGroup OBJECT-GROUP
    OBJECTS {
        etsysOspfExtVirtIfAdminStatus,
        etsysOspfExtVirtIfOperStatus,
        etsysOspfExtVirtIfTransmitTimerDelay,
        etsysOspfExtVirtIfIPMaxPacketSize,
        etsysOspfExtVirtIfPassive,
        etsysOspfExtVirtIfLsaRefreshIntvl,
        etsysOspfExtVirtIfHelperModePolicy,
        etsysOspfExtVirtIfMaxHtlssGracePeriod,
        etsysOspfExtVirtIfFastHelloMultiplier,
        etsysOspfExtVirtIfMtuIgnore
    }
    STATUS      current
    DESCRIPTION
        "This group defines the additional OSPF Virtual Interface objects
        supported in the Enterasys OSPF systems."
    ::= { etsysOspfExtGroups 4 }

etsysOspfExtNbrGroup OBJECT-GROUP
    OBJECTS {
        etsysOspfExtNbrAdminStatus,
        etsysOspfExtNbrOperStatus,
        etsysOspfExtNbrNumRequests,
        etsysOspfExtNbrIfIpAddr,
        etsysOspfExtNbrDeadTime,
        etsysOspfExtNbrAreaId
    }
    STATUS      current
    DESCRIPTION
        "This group defines the additional OSPF Neighbor objects supported
        in the Enterasys OSPF systems."
    ::= { etsysOspfExtGroups 5 }

etsysOspfExtVirtNbrGroup OBJECT-GROUP
    OBJECTS {
        etsysOspfExtVirtNbrNumRequests,
        etsysOspfExtVirtNbrDeadTime
    }
    STATUS      current
    DESCRIPTION
        "This group defines the additional OSPF Virtual Neighbor objects
        supported in the Enterasys OSPF systems."
    ::= { etsysOspfExtGroups 6 }

etsysOspfExtLocalLsdbGroup OBJECT-GROUP
    OBJECTS {
        etsysOspfExtLocalLsdbAreaId
    }
    STATUS      current
    DESCRIPTION
        "This group defines the additional OSPF Virtual Neighbor objects
        supported in the Enterasys OSPF systems."
    ::= { etsysOspfExtGroups 7 }

-- -------------------------------------------------------------
-- Compliance statements
-- -------------------------------------------------------------

etsysOspfExtCompliance MODULE-COMPLIANCE
    STATUS      current
    DESCRIPTION
        "The compliance statement for devices that support etsysOspfExt."

    MODULE
        MANDATORY-GROUPS {
            etsysOspfExtGlobalGroup,
            etsysOspfExtAreaGroup,
            etsysOspfExtIfGroup,
            etsysOspfExtVirtIfGroup,
            etsysOspfExtNbrGroup,
            etsysOspfExtVirtNbrGroup,
            etsysOspfExtLocalLsdbGroup
        }
    ::= { etsysOspfExtCompliances 1 }

END
