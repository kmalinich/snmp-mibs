ENTERASYS-IEEE8021-CFM-EXT-MIB DEFINITIONS ::= BEGIN

--  enterasys-ieee8021-cfm-ext-mib.txt
--
--  Part Number:
--
--

--  This module provides authoritative definitions for Enterasys
--  Networks' IEEE8021-CFM-MIB extension mib

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2013 Enterasys Networks, Inc.

IMPORTS
    MODULE-IDENTITY, OBJECT-TYPE, Unsigned32, Counter32
        FROM SNMPv2-SMI
    OBJECT-GROUP, MODULE-COMPLIANCE
        FROM SNMPv2-CONF
    InterfaceIndexOrZero
        FROM IF-MIB
    TEXTUAL-CONVENTION, TruthValue, MacAddress, TimeStamp
        FROM SNMPv2-TC
    EnabledStatus
        FROM P-BRIDGE-MIB
    Dot1agCfmLowestAlarmPri, dot1agCfmMepEntry, dot1agCfmMdIndex,
    dot1agCfmMaIndex, Dot1agCfmFngState, Dot1agCfmHighestDefectPri,
    Dot1agCfmMepDefects, Dot1agCfmMDLevel, Dot1agCfmMpDirection
        FROM IEEE8021-CFM-MIB
    IEEE8021ServiceSelectorType, IEEE8021ServiceSelectorValue,
    IEEE8021PbbComponentIdentifier
        FROM IEEE8021-TC-MIB
    etsysModules
        FROM ENTERASYS-MIB-NAMES;

etsysIeee8021CfmMibExtMIB MODULE-IDENTITY
    LAST-UPDATED "201302151717Z"  -- Fri Feb 15 17:17 UTC 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"

    DESCRIPTION
        "This MIB module defines a portion of the SNMP MIB under
         the Enterasys Networks enterprise OID pertaining to
         proprietary extensions to the IEEE8021-CFM-MIB."

    REVISION    "201302151717Z"  -- Fri Feb 15 17:17 UTC 2013
    DESCRIPTION "Initial version of this MIB module."

    ::= { etsysModules 524 }

-- -------------------------------------------------------------
-- Textual Conventions
-- -------------------------------------------------------------

EtsysIeee8021CfmExtMemPoolMaxSize ::= TEXTUAL-CONVENTION
    DISPLAY-HINT "d"
    STATUS  current
    DESCRIPTION
        "Integer that especifies the maximum size of a memory pool."
    SYNTAX Unsigned32 (1..5000)

EtsysIeee8021CfmExtMemPool ::= TEXTUAL-CONVENTION
    STATUS  current
    DESCRIPTION
        "This textual convention defines the list of CFM-related
         memory pools, allocated on the managed entity, that will
         be monitored by the CFM application in order to provide
         the usage of each memory pool.

         memPoolMD(1)     Memory pool to store Maintenance Domain
                          (MD)-related information.
         memPoolMA(2)     Memory pool to store Maintenance Association
                          (MA)-related information.
         memPoolMEP(3)    Memory pool to store Maintenace End Point
                          (MEP)-related information.
         memPoolMAMEP(4)  Memory pool to store MA MEP List Entry-related
                          information.
         memPoolRMEP(5)   Memory pool to store Remote MEP-related
                          information
         memPoolMHF(6)    Memory pool to store MIP Half Function (MHF)-
                          related information.
         memPoolMACOMP(7) Memory pool to store  part of the MA Table
                          that is variable accross the Bridges in a MD,
                          or across the components of a single Bridge."
    SYNTAX       INTEGER {
                     memPoolMD(1),
                     memPoolMA(2),
                     memPoolMEP(3),
                     memPoolMAMEP(4),
                     memPoolRMEP(5),
                     memPoolMHF(6),
                     memPoolMACOMP(7)
                 }

-- -------------------------------------------------------------
-- Object and Conformance Definitions
-- -------------------------------------------------------------

etsysIeee8021CfmMibExtObjects
    OBJECT IDENTIFIER ::= { etsysIeee8021CfmMibExtMIB 1 }

etsysIeee8021CfmMibExtConformance
    OBJECT IDENTIFIER ::= { etsysIeee8021CfmMibExtMIB 2 }

-- -------------------------------------------------------------
-- Enterasys CFM Extension Definition
-- -------------------------------------------------------------

etsysIeee8021CfmExtGlobal
     OBJECT IDENTIFIER ::= { etsysIeee8021CfmMibExtObjects 1 }

etsysIeee8021CfmExtMep
     OBJECT IDENTIFIER ::= { etsysIeee8021CfmMibExtObjects 2 }

-- -------------------------------------------------------------
-- Enterasys CFM Global leave
-- -------------------------------------------------------------

etsysIeee8021CfmExtStatus OBJECT-TYPE
    SYNTAX      EnabledStatus
    MAX-ACCESS  read-write
    STATUS      current
    DESCRIPTION
        "The global enabled/disabled status of the CFM functionality
         on the managed entity.

         enabled(1) - CFM is enabled globally on the managed entity.
         disabled(2)- CFM is disabled globally on the managed entity."
    DEFVAL { disabled }
    ::= { etsysIeee8021CfmExtGlobal 1 }

etsysIeee8021CfmExtMemPoolTable OBJECT-TYPE
    SYNTAX      SEQUENCE OF EtsysIeee8021CfmExtMemPoolEntry
    MAX-ACCESS  not-accessible
    STATUS      current
    DESCRIPTION
        "Provides information related to the memory pools allocated
         on the managed entity to support configuration of CFM elements.

         The following information is provided:
         - Memory pool size
         - Current number of elements in use
         - High water mark of pool usage."
    ::= { etsysIeee8021CfmExtGlobal 2 }

etsysIeee8021CfmExtMemPoolEntry OBJECT-TYPE
    SYNTAX      EtsysIeee8021CfmExtMemPoolEntry
    MAX-ACCESS  not-accessible
    STATUS      current
    DESCRIPTION
        "Enterasys Memory Pool table entry."
    INDEX { etsysIeee8021CfmExtMemPoolIndex }
    ::= { etsysIeee8021CfmExtMemPoolTable 1 }

EtsysIeee8021CfmExtMemPoolEntry ::=
    SEQUENCE {
        etsysIeee8021CfmExtMemPoolIndex
             EtsysIeee8021CfmExtMemPool,
        etsysIeee8021CfmExtMemPoolSize
             EtsysIeee8021CfmExtMemPoolMaxSize,
        etsysIeee8021CfmExtMemPoolInUse
             EtsysIeee8021CfmExtMemPoolMaxSize,
        etsysIeee8021CfmExtMemPoolHighWaterMark
             EtsysIeee8021CfmExtMemPoolMaxSize
    }

etsysIeee8021CfmExtMemPoolIndex OBJECT-TYPE
    SYNTAX      EtsysIeee8021CfmExtMemPool
    MAX-ACCESS  not-accessible
    STATUS      current
    DESCRIPTION
        "The index to the Mem Pool Table."
    ::= { etsysIeee8021CfmExtMemPoolEntry 1 }

etsysIeee8021CfmExtMemPoolSize OBJECT-TYPE
    SYNTAX      EtsysIeee8021CfmExtMemPoolMaxSize
    MAX-ACCESS  read-only
    STATUS      current
    DESCRIPTION
        "The total number of elements of the memory pool."
    ::= { etsysIeee8021CfmExtMemPoolEntry 2 }

etsysIeee8021CfmExtMemPoolInUse OBJECT-TYPE
    SYNTAX      EtsysIeee8021CfmExtMemPoolMaxSize
    MAX-ACCESS  read-only
    STATUS      current
    DESCRIPTION
        "The current number of elements of the memory pool
         in use."
    ::= { etsysIeee8021CfmExtMemPoolEntry 3 }

etsysIeee8021CfmExtMemPoolHighWaterMark OBJECT-TYPE
    SYNTAX      EtsysIeee8021CfmExtMemPoolMaxSize
    MAX-ACCESS  read-only
    STATUS      current
    DESCRIPTION
        "The high water mark of memory pool usage."
    ::= { etsysIeee8021CfmExtMemPoolEntry 4 }

-- -------------------------------------------------------------
-- Enterasys CFM MEP Table
-- -------------------------------------------------------------

etsysIeee8021CfmExtMepTable OBJECT-TYPE
    SYNTAX      SEQUENCE OF EtsysIeee8021CfmExtMepEntry
    MAX-ACCESS  not-accessible
    STATUS      current
    DESCRIPTION
        "Extensions to the dot1agCfmMepTable."
    ::= { etsysIeee8021CfmExtMep 1 }

etsysIeee8021CfmExtMepEntry OBJECT-TYPE
    SYNTAX      EtsysIeee8021CfmExtMepEntry
    MAX-ACCESS  not-accessible
    STATUS      current
    DESCRIPTION
        "Enterasys CFM MEP extension table entry."
    AUGMENTS { dot1agCfmMepEntry }
    ::= { etsysIeee8021CfmExtMepTable 1 }

EtsysIeee8021CfmExtMepEntry ::=
    SEQUENCE {
        etsysIeee8021CfmExtMepLowPrDefSyslog
             Dot1agCfmLowestAlarmPri,
        etsysIeee8021CfmExtMepFngStateSyslog
             Dot1agCfmFngState,
        etsysIeee8021CfmExtMepHighestPrDefectSyslog
             Dot1agCfmHighestDefectPri,
        etsysIeee8021CfmExtMepDefectsSyslog
             Dot1agCfmMepDefects,
        etsysIeee8021CfmExtMepClearCcmDatabase
             TruthValue,
        etsysIeee8021CfmExtRxDiscardCount
             Counter32,
        etsysIeee8021CfmExtRxForwardCount
             Counter32,
        etsysIeee8021CfmExtRxErrorCount
             Counter32,
        etsysIeee8021CfmExtTxErrorCount
             Counter32,
        etsysIeee8021CfmExtMepRxCcmCount
             Counter32,
        etsysIeee8021CfmExtMepRxCcmErrCount
             Counter32,
        etsysIeee8021CfmExtMepRxCcmXconCount
             Counter32,
        etsysIeee8021CfmExtMepTxCcmCount
             Counter32,
        etsysIeee8021CfmExtMepTxCcmErrCount
             Counter32,
        etsysIeee8021CfmExtMepRxLbmCount
             Counter32,
        etsysIeee8021CfmExtMepTxLbmCount
             Counter32,
        etsysIeee8021CfmExtMepRxLbrCount
             Counter32,
        etsysIeee8021CfmExtMepTxLbrCount
             Counter32,
        etsysIeee8021CfmExtMepRxLtmCount
             Counter32,
        etsysIeee8021CfmExtMepTxLtmCount
             Counter32,
        etsysIeee8021CfmExtMepRxLtrCount
             Counter32,
        etsysIeee8021CfmExtMepTxLtrCount
             Counter32,
        etsysIeee8021CfmExtMepClearMepCounters
             TruthValue
    }

etsysIeee8021CfmExtMepLowPrDefSyslog OBJECT-TYPE
    SYNTAX      Dot1agCfmLowestAlarmPri
    MAX-ACCESS  read-create
    STATUS      current
    DESCRIPTION
        "An integer value specifying the lowest priority defect
         that is allowed to generate syslog message."
    DEFVAL { macRemErrXcon }
    ::= { etsysIeee8021CfmExtMepEntry 1 }

etsysIeee8021CfmExtMepFngStateSyslog OBJECT-TYPE
    SYNTAX      Dot1agCfmFngState
    MAX-ACCESS  read-only
    STATUS      current
    DESCRIPTION
       "Current state of the MEP Fault Notification Generator
        State Machine for Syslog.
       "
    ::= { etsysIeee8021CfmExtMepEntry 2 }

etsysIeee8021CfmExtMepHighestPrDefectSyslog OBJECT-TYPE
    SYNTAX      Dot1agCfmHighestDefectPri
    MAX-ACCESS  read-only
    STATUS      current
    DESCRIPTION
       "The highest priority defect that has been present since the
        MEPs Fault Notification Generator State Machine for Syslog
        was last in the FNG_RESET state.
       "
    ::= { etsysIeee8021CfmExtMepEntry 3 }

etsysIeee8021CfmExtMepDefectsSyslog OBJECT-TYPE
    SYNTAX      Dot1agCfmMepDefects
    MAX-ACCESS  read-only
    STATUS      current
    DESCRIPTION
       "A vector of Boolean error conditions maintained by the MEPs
        Fault Notification Generator State Machine for Syslog from
        Table 20-1, any of which may be true:

        DefRDICCM(0)
        DefMACstatus(1)
        DefRemoteCCM(2)
        DefErrorCCM(3)
        DefXconCCM(4)
       "
    ::= { etsysIeee8021CfmExtMepEntry 4 }

etsysIeee8021CfmExtMepClearCcmDatabase OBJECT-TYPE
    SYNTAX      TruthValue
    MAX-ACCESS  read-write
    STATUS      current
    DESCRIPTION
        "If set to true, the MEP CCM database will be cleared."
    ::= { etsysIeee8021CfmExtMepEntry 5 }

etsysIeee8021CfmExtRxDiscardCount OBJECT-TYPE
    SYNTAX      Counter32
    MAX-ACCESS  read-only
    STATUS      current
    DESCRIPTION
        "The total number of CFM frames received and discarded
         since the last reboot.

         This value should not be maintained across reboot."
    ::= { etsysIeee8021CfmExtMepEntry 6 }

etsysIeee8021CfmExtRxForwardCount OBJECT-TYPE
    SYNTAX      Counter32
    MAX-ACCESS  read-only
    STATUS      current
    DESCRIPTION
        "The total number of CFM frames received and forwarded
         since the last reboot.

         This value should not be maintained across reboot."
    ::= { etsysIeee8021CfmExtMepEntry 7 }

etsysIeee8021CfmExtRxErrorCount OBJECT-TYPE
    SYNTAX      Counter32
    MAX-ACCESS  read-only
    STATUS      current
    DESCRIPTION
        "The total number of CFM frames received with errors
         since the last reboot.

         This value should not be maintained across reboot."
    ::= { etsysIeee8021CfmExtMepEntry 8 }

etsysIeee8021CfmExtTxErrorCount OBJECT-TYPE
    SYNTAX      Counter32
    MAX-ACCESS  read-only
    STATUS      current
    DESCRIPTION
        "The total number of outbound CFM frames that could
         not be transmitted because of errors since the last
         reboot.

         This value should not be maintained across reboot."
    ::= { etsysIeee8021CfmExtMepEntry 9 }

etsysIeee8021CfmExtMepRxCcmCount OBJECT-TYPE
    SYNTAX      Counter32
    MAX-ACCESS  read-only
    STATUS      current
    DESCRIPTION
        "The total number of CFM Continuity Check PDUs
         received since the last reboot.

         This value should not be maintained across reboot."
    ::= { etsysIeee8021CfmExtMepEntry 10 }

etsysIeee8021CfmExtMepRxCcmErrCount OBJECT-TYPE
    SYNTAX      Counter32
    MAX-ACCESS  read-only
    STATUS      current
    DESCRIPTION
        "The total number of CFM Continuity Check PDUs
         that triggered a Remote MEP Error received since
         the last reboot.

         This value should not be maintained across reboot."
    ::= { etsysIeee8021CfmExtMepEntry 11 }

etsysIeee8021CfmExtMepRxCcmXconCount OBJECT-TYPE
    SYNTAX      Counter32
    MAX-ACCESS  read-only
    STATUS      current
    DESCRIPTION
        "The total number of CFM Continuity Check PDUs
         that triggered a MEP Cross Connect defect received
         since the last reboot.

         This value should not be maintained across reboot."
    ::= { etsysIeee8021CfmExtMepEntry 12 }

etsysIeee8021CfmExtMepTxCcmCount OBJECT-TYPE
    SYNTAX      Counter32
    MAX-ACCESS  read-only
    STATUS      current
    DESCRIPTION
        "The total number of CFM Continuity Check PDUs
         transmitted since the last reboot.

         This value should not be maintained across reboot."
    ::= { etsysIeee8021CfmExtMepEntry 13 }

etsysIeee8021CfmExtMepTxCcmErrCount OBJECT-TYPE
    SYNTAX      Counter32
    MAX-ACCESS  read-only
    STATUS      current
    DESCRIPTION
        "The total number of outbound CFM Continuity Check
         PDUs that could not be transmitted because of errors
         since the last reboot.

         This value should not be maintained across reboot."
    ::= { etsysIeee8021CfmExtMepEntry 14 }

etsysIeee8021CfmExtMepRxLbmCount OBJECT-TYPE
    SYNTAX      Counter32
    MAX-ACCESS  read-only
    STATUS      current
    DESCRIPTION
        "The total number of CFM Loopback Message PDUs
         received since the last reboot.

         This value should not be maintained across reboot."
    ::= { etsysIeee8021CfmExtMepEntry 15 }

etsysIeee8021CfmExtMepTxLbmCount OBJECT-TYPE
    SYNTAX      Counter32
    MAX-ACCESS  read-only
    STATUS      current
    DESCRIPTION
        "The total number of CFM Loopback Message PDUs
         transmitted since the last reboot.

         This value should not be maintained across reboot."
    ::= { etsysIeee8021CfmExtMepEntry 16 }

etsysIeee8021CfmExtMepRxLbrCount OBJECT-TYPE
    SYNTAX      Counter32
    MAX-ACCESS  read-only
    STATUS      current
    DESCRIPTION
        "The total number of CFM Loopback Response PDUs
         received since the last reboot.

         This value should not be maintained across reboot."
    ::= { etsysIeee8021CfmExtMepEntry 17 }

etsysIeee8021CfmExtMepTxLbrCount OBJECT-TYPE
    SYNTAX      Counter32
    MAX-ACCESS  read-only
    STATUS      current
    DESCRIPTION
        "The total number of CFM Loopback Response PDUs
         transmitted since the last reboot.

         This value should not be maintained across reboot."
    ::= { etsysIeee8021CfmExtMepEntry 18 }

etsysIeee8021CfmExtMepRxLtmCount OBJECT-TYPE
    SYNTAX      Counter32
    MAX-ACCESS  read-only
    STATUS      current
    DESCRIPTION
        "The total number of CFM Linktrace Message PDUs
         received since the last reboot.

         This value should not be maintained across reboot."
    ::= { etsysIeee8021CfmExtMepEntry 19 }

etsysIeee8021CfmExtMepTxLtmCount OBJECT-TYPE
    SYNTAX      Counter32
    MAX-ACCESS  read-only
    STATUS      current
    DESCRIPTION
        "The total number of CFM Linktrace Message PDUs
         transmitted since last reboot.

         This value should not be maintained across reboot."
    ::= { etsysIeee8021CfmExtMepEntry 20 }

etsysIeee8021CfmExtMepRxLtrCount OBJECT-TYPE
    SYNTAX      Counter32
    MAX-ACCESS  read-only
    STATUS      current
    DESCRIPTION
        "The total number of CFM Linktrace Response PDUs
         received since the last reboot.

         This value should not be maintained across reboot."
    ::= { etsysIeee8021CfmExtMepEntry 21 }

etsysIeee8021CfmExtMepTxLtrCount OBJECT-TYPE
    SYNTAX      Counter32
    MAX-ACCESS  read-only
    STATUS      current
    DESCRIPTION
        "The total number of CFM Linktrace Response PDUs
         transmitted since the last reboot.

         This value should not be maintained across reboot."
    ::= { etsysIeee8021CfmExtMepEntry 22 }

etsysIeee8021CfmExtMepClearMepCounters OBJECT-TYPE
    SYNTAX      TruthValue
    MAX-ACCESS  read-write
    STATUS      current
    DESCRIPTION
        "If set to true, the CFM MEP counters will be cleared."
    ::= { etsysIeee8021CfmExtMepEntry 23 }


-- -------------------------------------------------------------
-- The MIP CCM Database Table
-- -------------------------------------------------------------

etsysIeee8021CfmMipCcmDbTable OBJECT-TYPE
    SYNTAX      SEQUENCE OF EtsysIeee8021CfmMipCcmDbEntry
    MAX-ACCESS  not-accessible
    STATUS      current
    DESCRIPTION
       "The MIP CCM Database. A database, maintained by every
        MEP and MHF, that maintains Continuity Check information
        about other MEPs in the Maintenance Domain.
       "
    REFERENCE
       "19.3"
    ::= { etsysIeee8021CfmExtGlobal 3 }

etsysIeee8021CfmMipCcmDbEntry OBJECT-TYPE
    SYNTAX      EtsysIeee8021CfmMipCcmDbEntry
    MAX-ACCESS  not-accessible
    STATUS      current
    DESCRIPTION
       "The MIP CCM Database table entry."
    INDEX { dot1agCfmMdIndex,
            dot1agCfmMaIndex,
            etsysIeee8021CfmMipCcmDbMpIdentifier,
            etsysIeee8021CfmMipCcmDbFid,
            etsysIeee8021CfmMipCcmDbMacAddress
          }
    ::= { etsysIeee8021CfmMipCcmDbTable 1 }

EtsysIeee8021CfmMipCcmDbEntry ::=
    SEQUENCE {
        etsysIeee8021CfmMipCcmDbMpIdentifier
             Unsigned32,
        etsysIeee8021CfmMipCcmDbFid
             Unsigned32,
        etsysIeee8021CfmMipCcmDbMacAddress
             MacAddress,
        etsysIeee8021CfmMipCcmDbMpIfIndex
             InterfaceIndexOrZero,
        etsysIeee8021CfmMipCcmDbMpMdLevel
             Dot1agCfmMDLevel,
        etsysIeee8021CfmMipCcmDbMpDirection
             Dot1agCfmMpDirection,
        etsysIeee8021CfmMipCcmDbLearnedIfIndex
             InterfaceIndexOrZero,
        etsysIeee8021CfmMipCcmDbTimeStamp
              TimeStamp,
        etsysIeee8021CfmMipCcmDbComponentId
             IEEE8021PbbComponentIdentifier,
        etsysIeee8021CfmMipCcmDbPrimarySelectorType
             IEEE8021ServiceSelectorType,
        etsysIeee8021CfmMipCcmDbPrimarySelector
             IEEE8021ServiceSelectorValue
    }

etsysIeee8021CfmMipCcmDbMpIdentifier OBJECT-TYPE
    SYNTAX      Unsigned32 (1..8191 | 16383..32767)
    MAX-ACCESS  not-accessible
    STATUS      current
    DESCRIPTION
       "Identifier of a MP whose information from the MIP
        CCM Database is to be returned.
       "
    ::= { etsysIeee8021CfmMipCcmDbEntry 1 }

etsysIeee8021CfmMipCcmDbFid OBJECT-TYPE
    SYNTAX      Unsigned32 ( 0..4094 )
    MAX-ACCESS  not-accessible
    STATUS      current
    DESCRIPTION
       "FID of the item in the MIP CCM Database to be returned."
    ::= { etsysIeee8021CfmMipCcmDbEntry 2 }

etsysIeee8021CfmMipCcmDbMacAddress OBJECT-TYPE
    SYNTAX      MacAddress
    MAX-ACCESS  not-accessible
    STATUS      current
    DESCRIPTION
       "The MAC address of the item in the MIP CCM Database to be
        returned."
    ::= { etsysIeee8021CfmMipCcmDbEntry 3 }

etsysIeee8021CfmMipCcmDbMpIfIndex OBJECT-TYPE
    SYNTAX      InterfaceIndexOrZero
    MAX-ACCESS  read-only
    STATUS      current
    DESCRIPTION
       "The interface index of the interface of the MP of the
        item in the MIP CCM Database to be returned."
    ::= { etsysIeee8021CfmMipCcmDbEntry 4 }

etsysIeee8021CfmMipCcmDbMpMdLevel OBJECT-TYPE
    SYNTAX      Dot1agCfmMDLevel
    MAX-ACCESS  read-only
    STATUS      current
    DESCRIPTION
       "The MD Level of the MP of the item in the MIP CCM
        Database to be returned."
    REFERENCE
       "12.14.2.1.2:b"
    ::= { etsysIeee8021CfmMipCcmDbEntry 5 }

etsysIeee8021CfmMipCcmDbMpDirection OBJECT-TYPE
    SYNTAX      Dot1agCfmMpDirection
    MAX-ACCESS  read-only
    STATUS      current
    DESCRIPTION
       "The Direction in which the MP faces on the Bridge Port of
        the item in the MIP CCM Database to be returned."
    REFERENCE
       "12.14.2.1.2:c"
    ::= { etsysIeee8021CfmMipCcmDbEntry 6 }

etsysIeee8021CfmMipCcmDbLearnedIfIndex OBJECT-TYPE
    SYNTAX      InterfaceIndexOrZero
    MAX-ACCESS  read-only
    STATUS      current
    DESCRIPTION
       "The interface index of the interface on which the MIP CCM
        of the MIP CCM database item was learned on."
    ::= { etsysIeee8021CfmMipCcmDbEntry 7 }

etsysIeee8021CfmMipCcmDbTimeStamp OBJECT-TYPE
    SYNTAX      TimeStamp
    MAX-ACCESS  read-only
    STATUS      current
    DESCRIPTION
       "TimeStamp of the item in the MIP CCM Database to be returned.
        It is the value of sysUpTime at the last time it was
        modified."
    ::= { etsysIeee8021CfmMipCcmDbEntry 8 }

etsysIeee8021CfmMipCcmDbComponentId OBJECT-TYPE
    SYNTAX      IEEE8021PbbComponentIdentifier
    MAX-ACCESS  read-only
    STATUS      current
    DESCRIPTION
       "The bridge component within the system to which the information
        in this etsysIeee8021CfmMipCcmDbEntry applies.  If the system is
        not a Bridge, or if only one component is present in the Bridge,
        then this variable (index) MUST be equal to 1.
       "
    REFERENCE
       "12.3 l)"
    ::= { etsysIeee8021CfmMipCcmDbEntry 9 }

etsysIeee8021CfmMipCcmDbPrimarySelectorType OBJECT-TYPE
    SYNTAX      IEEE8021ServiceSelectorType
    MAX-ACCESS  read-only
    STATUS      current
    DESCRIPTION
       "Type of the Primary Service Selector identifier indicated by
        etsysIeee8021CfmMipCcmDbPrimarySelector. See textual
        convention IEEE8021ServiceSelectorType for details.
       "
    ::= { etsysIeee8021CfmMipCcmDbEntry 10 }

etsysIeee8021CfmMipCcmDbPrimarySelector OBJECT-TYPE
    SYNTAX      IEEE8021ServiceSelectorValue
    MAX-ACCESS  read-only
    STATUS      current
    DESCRIPTION
       "Primary Service Selector identifier of a Service Instance.  See
        IEEE8021ServiceSelectorValue for details.
       "
    ::= { etsysIeee8021CfmMipCcmDbEntry 11 }

etsysIeee8021CfmClearBridgeCcmDatabase OBJECT-TYPE
    SYNTAX      TruthValue
    MAX-ACCESS  read-write
    STATUS      current
    DESCRIPTION
        "If set to true, the bridge CCM database will be cleared."
    DEFVAL { false }
    ::= { etsysIeee8021CfmExtGlobal 4 }

-- -------------------------------------------------------------
-- Conformance Information
-- -------------------------------------------------------------

etsysIeee8021CfmMibExtGroups      OBJECT IDENTIFIER
    ::= { etsysIeee8021CfmMibExtConformance 1 }

etsysIeee8021CfmMibExtCompliances OBJECT IDENTIFIER
    ::= { etsysIeee8021CfmMibExtConformance 2 }

-- -------------------------------------------------------------
-- Units of conformance
-- -------------------------------------------------------------

etsysIeee8021CfmExtStatusGroup OBJECT-GROUP
    OBJECTS {
        etsysIeee8021CfmExtStatus
    }
    STATUS      current
    DESCRIPTION
        "A collection of objects providing global control of CFM
         on the managed entity."
    ::= { etsysIeee8021CfmMibExtGroups 1 }

etsysIeee8021CfmExtMemPoolGroup OBJECT-GROUP
    OBJECTS {
        etsysIeee8021CfmExtMemPoolSize,
        etsysIeee8021CfmExtMemPoolInUse,
        etsysIeee8021CfmExtMemPoolHighWaterMark
    }
    STATUS      current
    DESCRIPTION
        "A collection of objects providing information related to
         the CFM-related memory pool of the managed entity."
    ::= { etsysIeee8021CfmMibExtGroups 2 }

etsysIeee8021CfmExtMepGroup OBJECT-GROUP
    OBJECTS {
        etsysIeee8021CfmExtMepLowPrDefSyslog,
        etsysIeee8021CfmExtMepFngStateSyslog,
        etsysIeee8021CfmExtMepHighestPrDefectSyslog,
        etsysIeee8021CfmExtMepDefectsSyslog,
        etsysIeee8021CfmExtMepClearCcmDatabase,
        etsysIeee8021CfmExtRxDiscardCount,
        etsysIeee8021CfmExtRxForwardCount,
        etsysIeee8021CfmExtRxErrorCount,
        etsysIeee8021CfmExtTxErrorCount,
        etsysIeee8021CfmExtMepRxCcmCount,
        etsysIeee8021CfmExtMepRxCcmErrCount,
        etsysIeee8021CfmExtMepRxCcmXconCount,
        etsysIeee8021CfmExtMepTxCcmCount,
        etsysIeee8021CfmExtMepTxCcmErrCount,
        etsysIeee8021CfmExtMepRxLbmCount,
        etsysIeee8021CfmExtMepTxLbmCount,
        etsysIeee8021CfmExtMepRxLbrCount,
        etsysIeee8021CfmExtMepTxLbrCount,
        etsysIeee8021CfmExtMepRxLtmCount,
        etsysIeee8021CfmExtMepTxLtmCount,
        etsysIeee8021CfmExtMepRxLtrCount,
        etsysIeee8021CfmExtMepTxLtrCount,
        etsysIeee8021CfmExtMepClearMepCounters
    }
    STATUS      current
    DESCRIPTION
        "A collection of objects for the enterasys CFM
         MEP group."
    ::= { etsysIeee8021CfmMibExtGroups 3 }

etsysIeee8021CfmExtMipGroup OBJECT-GROUP
    OBJECTS {
        etsysIeee8021CfmMipCcmDbMpIfIndex,
        etsysIeee8021CfmMipCcmDbMpMdLevel,
        etsysIeee8021CfmMipCcmDbMpDirection,
        etsysIeee8021CfmMipCcmDbLearnedIfIndex,
        etsysIeee8021CfmMipCcmDbTimeStamp,
        etsysIeee8021CfmMipCcmDbComponentId,
        etsysIeee8021CfmMipCcmDbPrimarySelectorType,
        etsysIeee8021CfmMipCcmDbPrimarySelector
    }
    STATUS      current
    DESCRIPTION
        "A collection of objects for the enterasys CFM
         MIP group."
    ::= { etsysIeee8021CfmMibExtGroups 4 }

etsysIeee8021CfmClearBridgeCcmDatabaseGroup OBJECT-GROUP
    OBJECTS {
        etsysIeee8021CfmClearBridgeCcmDatabase
    }
    STATUS      current
    DESCRIPTION
        "A collection of objects providing method to clear CFM
         bridge CCM database."
    ::= { etsysIeee8021CfmMibExtGroups 5 }

-- -------------------------------------------------------------
-- Compliance statements
-- -------------------------------------------------------------

etsysIeee8021CfmMibExtCompliance MODULE-COMPLIANCE
    STATUS      current
    DESCRIPTION
        "The compliance statement for devices that support
         etsysIeee8021CfmMibExtMIB."
    MODULE
        MANDATORY-GROUPS {
            etsysIeee8021CfmExtStatusGroup,
            etsysIeee8021CfmExtMemPoolGroup,
            etsysIeee8021CfmExtMepGroup,
            etsysIeee8021CfmExtMipGroup,
            etsysIeee8021CfmClearBridgeCcmDatabaseGroup
        }
    ::= { etsysIeee8021CfmMibExtCompliances 1 }

END
