CTRON-FDDI-STAT-MIB DEFINITIONS ::= BEGIN

        --  ctron-fddi-stat-mib.txt.
        --  Revision: 1.00.00
        --  Date: February 5, 1996

        --  Cabletron Systems, Inc.
        --  35 Industrial Way, P.O. Box 5005
        --  Rochester, NH 03867-0505
        --  (603) 332-9400
        --  support@ctron.com

        --  This module provides authoritative definitions for Cabletron's
        --  enterprise-specific connection MIB.
        --
        --  This module will be extended, as needed.
        --

        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.

        --  Copyright August 95 Cabletron Systems

        IMPORTS
                TimeTicks
                        FROM RFC1155-SMI
                ctFDDIStats
                        FROM CTRON-MIB-NAMES
                OBJECT-TYPE
                        FROM RFC-1212;


        ctFDDIStatsUtil OBJECT IDENTIFIER ::= { ctFDDIStats 1 }

        ctFDDIStatsCtlTable     OBJECT-TYPE
            SYNTAX      SEQUENCE OF CtFDDIStatsCtlEntry
            ACCESS      not-accessible
            STATUS      mandatory
            DESCRIPTION
                "This table allows control over the creation of FDDI
                utilization statistics.  This is done by providing an
                object that when accessed latches the statistics into
                the stats table."
            ::= { ctFDDIStatsUtil 1 }

        ctFDDIStatsCtlEntry     OBJECT-TYPE
            SYNTAX      CtFDDIStatsCtlEntry
            ACCESS      not-accessible
            STATUS      mandatory
            DESCRIPTION
                "Defines a specific control entry."
            INDEX { ctFDDISlot, ctFDDISMT, ctFDDIPath }
            ::= { ctFDDIStatsCtlTable 1 }

        CtFDDIStatsCtlEntry ::= SEQUENCE {
                ctFDDISlot
                        INTEGER,
                ctFDDISMT
                        INTEGER,
                ctFDDIPath
                        INTEGER,
                ctFDDINextEntry
                        INTEGER,
                ctFDDIResetPeak
                        INTEGER
                }

        ctFDDISlot      OBJECT-TYPE
            SYNTAX      INTEGER
            ACCESS      read-only
            STATUS      mandatory
            DESCRIPTION
                "A specific slot for which this connection entry is
                defined.  If the entry corresponds to a slotless chassis
                system, then this entry will have the value of 0."
            ::= { ctFDDIStatsCtlEntry 1 }

        ctFDDISMT               OBJECT-TYPE
            SYNTAX      INTEGER
            ACCESS      read-only
            STATUS      mandatory
            DESCRIPTION
                "A specific instance of SMT for which this entry pertains."
            REFERENCE
                "The IETF RFC FDDI-SMT73-MIB, fddimibSMTIndex"
            ::= { ctFDDIStatsCtlEntry 2 }

        ctFDDIPath              OBJECT-TYPE
            SYNTAX      INTEGER
            ACCESS      read-only
            STATUS      mandatory
            DESCRIPTION
                "A specific FDDI Path that this connection entry pertains."
            REFERENCE
                "The IETF RFC FDDI-SMT73-MIB, fddimibPATHIndex"
            ::= { ctFDDIStatsCtlEntry 3 }

        ctFDDINextEntry OBJECT-TYPE
            SYNTAX      INTEGER
            ACCESS      read-only
            STATUS      mandatory
            DESCRIPTION
                "Provides an identifier of the next entry to be used
                in the ctFDDIStatsHistoryTable.

                Reading this object will latch FDDI performance data
                into a conceptual row in the ctFDDIStatsHistoryTable
                indexed by the value just read from ctFDDINextEntry."
            ::= { ctFDDIStatsCtlEntry 4 }

        ctFDDIResetPeak OBJECT-TYPE
            SYNTAX      INTEGER {
                normal(1),
                reset(2)
                }
            ACCESS      read-write
            STATUS      mandatory
            DESCRIPTION
                "This object provides the ability to reset the peak
                bytes and peak time stamp object.  This is accomplished
                by setting this object with a value of reset(2).  Setting
                a value of normal(1) will have no affect.

                When read this object will always return normal(1)."
            ::= { ctFDDIStatsCtlEntry 5 }



        ctFDDIStatsHistoryTable OBJECT-TYPE
            SYNTAX      SEQUENCE OF CtFDDIStatsHistoryEntry
            ACCESS      not-accessible
            STATUS      mandatory
            DESCRIPTION
                "Provides a history of latched FDDI performance objects.
                There is one such object for each entry that has been
                latched in the ctFDDIStatsCtlTable.

                This table will contain the 10 most recent entries.  All
                other entries will be lost."
            ::= { ctFDDIStatsUtil 2 }

        ctFDDIStatsHistoryEntry OBJECT-TYPE
            SYNTAX      CtFDDIStatsHistoryEntry
            ACCESS      not-accessible
            STATUS      mandatory
            DESCRIPTION
                ""
                INDEX { ctFDDISlot, ctFDDIStatsIndex }
            ::= { ctFDDIStatsHistoryTable 1 }

        CtFDDIStatsHistoryEntry ::= SEQUENCE {
                ctFDDIStatsIndex
                        INTEGER,
                ctFDDIStatsTimeStamp
                        TimeTicks,
                ctFDDIFrames
                        INTEGER,
                ctFDDIBytes
                        INTEGER,
                ctFDDIPeakBytes
                        INTEGER,
                ctFDDIPeakTime
                        INTEGER,
                ctFDDIStatsSMT
                        INTEGER,
                ctFDDIStatsPath
                        INTEGER
                }

        ctFDDIStatsIndex        OBJECT-TYPE
            SYNTAX      INTEGER
            ACCESS      read-only
            STATUS      mandatory
            DESCRIPTION
                "A unique entry that identifies a particular latched stats
                entry.  This corresponds directly to a value of
                ctFDDINextEntry."
            ::= { ctFDDIStatsHistoryEntry 1 }

        ctFDDIStatsTimeStamp    OBJECT-TYPE
            SYNTAX      TimeTicks
            ACCESS      read-only
            STATUS      mandatory
            DESCRIPTION
                "The value of sysUpTime when this entry was created."
            ::= { ctFDDIStatsHistoryEntry 2 }

        ctFDDIFrames    OBJECT-TYPE
            SYNTAX      INTEGER
            ACCESS      read-only
            STATUS      mandatory
            DESCRIPTION
                "The bandwidth utilization in frames per second."
        ::= { ctFDDIStatsHistoryEntry 3 }

        ctFDDIBytes     OBJECT-TYPE
            SYNTAX      INTEGER
            ACCESS      read-only
            STATUS      mandatory
            DESCRIPTION
                "The bandwidth utilization in bytes per second."
        ::= { ctFDDIStatsHistoryEntry 4 }

        ctFDDIPeakBytes OBJECT-TYPE
            SYNTAX      INTEGER
            ACCESS      read-only
            STATUS      mandatory
            DESCRIPTION
                "The peak bandwidth utilization in bytes per second."
        ::= { ctFDDIStatsHistoryEntry 5 }

        ctFDDIPeakTime  OBJECT-TYPE
            SYNTAX      INTEGER
            ACCESS      read-only
            STATUS      mandatory
            DESCRIPTION
                "A time stamp when the peak occured."
        ::= { ctFDDIStatsHistoryEntry 6 }

        ctFDDIStatsSMT  OBJECT-TYPE
            SYNTAX      INTEGER
            ACCESS      read-only
            STATUS      mandatory
            DESCRIPTION
                "The FDDI SMT index for which these statistics pertain.
                The value of the object must match a corresponding value
                of ctFDDISMT."
        ::= { ctFDDIStatsHistoryEntry 7 }

        ctFDDIStatsPath OBJECT-TYPE
            SYNTAX      INTEGER
            ACCESS      read-only
            STATUS      mandatory
            DESCRIPTION
                "The FDDI MAC path index for which these statistics pertain.
                The value of the object must match a corresponding value
                of ctFDDIPath."
        ::= { ctFDDIStatsHistoryEntry 8 }

END
