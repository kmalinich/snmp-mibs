CTRON-SFPS-POLICY-MIB DEFINITIONS ::= BEGIN

--  sfps-policy-mib.txt
--  Revision: 0.0.03
--
--  Cabletron Systems, Inc.
--  35 Industrial Way, P.O. Box 5005
--  Rochester, NH 03867-0505
--  (603) 332-9400
--  support@ctron.com

--  This module provides authoritative definitions for Cabletron's
--  enterprise specific Fast Packet Switching Services MIB.
--
--  This module will be extended, as required.
--

--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright October 93 Cabletron Systems
--


IMPORTS
      OBJECT-TYPE
                FROM RFC-1212
      DisplayString
                FROM RFC1213-MIB
--      enterprises,
--      IpAddress,
--      Counter, Gauge,
      TimeTicks
                FROM RFC1155-SMI

--  These Objects are defined in the file sfps-inc.mib.txt.0.0.2
        sfpsISPPolicy, sfpsVlanMatrix, sfpsVlanMatrixApi, sfpsVMMatrix

                FROM CTRON-SFPS-INCLUDE-MIB;

--  Textual Conventions

HexInteger ::= INTEGER
--  display this integer in hex format

-- POLICY

sfpsServiceCenterPolicyTable     OBJECT-TYPE
        SYNTAX  SEQUENCE OF SfpsServiceCenterPolicyEntry
        ACCESS  not-accessible
        STATUS  mandatory
        DESCRIPTION
                "This table gives policy semantics to call processing."
        ::= { sfpsISPPolicy 1 }

sfpsServiceCenterPolicyEntry    OBJECT-TYPE
        SYNTAX  SfpsServiceCenterPolicyEntry
        ACCESS  not-accessible
        STATUS  mandatory
        DESCRIPTION
                "Each entry contains the configuration of the Policy Entry."
        INDEX   { sfpsServiceCenterPolicyHashLeaf }
        ::= { sfpsServiceCenterPolicyTable 1 }

SfpsServiceCenterPolicyEntry ::=
        SEQUENCE {
                sfpsServiceCenterPolicyHashLeaf         HexInteger,
                sfpsServiceCenterPolicyMetric   INTEGER,
                sfpsServiceCenterPolicyName     DisplayString,
                sfpsServiceCenterPolicyOperStatus       INTEGER,
                sfpsServiceCenterPolicyAdminStatus     INTEGER,
                sfpsServiceCenterPolicyStatusTime       TimeTicks,
                sfpsServiceCenterPolicyRequests         INTEGER,
                sfpsServiceCenterPolicyResponses        INTEGER

         }

sfpsServiceCenterPolicyHashLeaf   OBJECT-TYPE
        SYNTAX  HexInteger
        ACCESS  read-only
        STATUS  mandatory
        DESCRIPTION
                "Server hash, part of instance key."
        ::= { sfpsServiceCenterPolicyEntry 1 }

sfpsServiceCenterPolicyMetric   OBJECT-TYPE
        SYNTAX  INTEGER
        ACCESS  read-only
        STATUS  mandatory
        DESCRIPTION
                "Defines order servers are called low to high."
        ::= { sfpsServiceCenterPolicyEntry 2 }

sfpsServiceCenterPolicyName   OBJECT-TYPE
        SYNTAX  DisplayString
        ACCESS  read-only
        STATUS  mandatory
        DESCRIPTION
                "Server name."
        ::= { sfpsServiceCenterPolicyEntry 3 }

sfpsServiceCenterPolicyOperStatus   OBJECT-TYPE
        SYNTAX  INTEGER  {
                        kStatusRunning(1),      --  all is well
                        kStatusHalted(2),       -- admin disabled
                        kStatusPending(3),      -- Trying to run, not there yet
                        kStatusFaulted(4),      -- Internal error, never will recover
                        kStatusNotStarted(5)    -- Not fully started yet
        }

        ACCESS  read-only
        STATUS  mandatory
        DESCRIPTION
                "Operational state of entry."
        ::= { sfpsServiceCenterPolicyEntry 4 }

sfpsServiceCenterPolicyAdminStatus   OBJECT-TYPE
        SYNTAX  INTEGER       {
                        other(1),               -- Not running or stopped
                        disable(2),             -- Please stop
                        enable(3)               -- Go
        }

        ACCESS  read-write
        STATUS  mandatory
        DESCRIPTION
                "Administrative State of Entry."
        ::= { sfpsServiceCenterPolicyEntry 5 }

sfpsServiceCenterPolicyStatusTime   OBJECT-TYPE
        SYNTAX  TimeTicks
        ACCESS  read-only
        STATUS  mandatory
        DESCRIPTION
                "Time Tick of last operStatus change."
        ::= { sfpsServiceCenterPolicyEntry 6 }

sfpsServiceCenterPolicyRequests   OBJECT-TYPE
        SYNTAX   INTEGER
        ACCESS  read-only
        STATUS  mandatory
        DESCRIPTION
                "Requests made to server."
        ::= { sfpsServiceCenterPolicyEntry 7 }

sfpsServiceCenterPolicyResponses   OBJECT-TYPE
        SYNTAX  INTEGER
        ACCESS  read-only
        STATUS  mandatory
        DESCRIPTION
                "GOOD replies by server."
        ::= { sfpsServiceCenterPolicyEntry 8 }

-- Matrix Table

sfpsMatrixTable     OBJECT-TYPE
        SYNTAX  SEQUENCE OF SfpsMatrixEntry
        ACCESS  not-accessible
        STATUS  mandatory
        DESCRIPTION
                " "
        ::= { sfpsVlanMatrix 1 }

sfpsMatrixEntry    OBJECT-TYPE
        SYNTAX  SfpsMatrixEntry
        ACCESS  not-accessible
        STATUS  mandatory
        DESCRIPTION
                ""
        INDEX   { sfpsMatrixRowId, sfpsMatrixColId }
        ::= { sfpsMatrixTable 1 }

SfpsMatrixEntry ::=
        SEQUENCE {
                sfpsMatrixRowId         INTEGER,
                sfpsMatrixColId         INTEGER,
                sfpsMatrixUser1Type     OCTET STRING,
                sfpsMatrixUser1Load     OCTET STRING,
                sfpsMatrixUser2Type     OCTET STRING,
                sfpsMatrixUser2Load     OCTET STRING,
                sfpsMatrixConnect       INTEGER,
                sfpsMatrixFlood         INTEGER
        }

sfpsMatrixRowId   OBJECT-TYPE
        SYNTAX  INTEGER
        ACCESS  read-only
        STATUS  mandatory
        DESCRIPTION
                ""
        ::= { sfpsMatrixEntry 1 }

sfpsMatrixColId   OBJECT-TYPE
        SYNTAX  INTEGER
        ACCESS  read-only
        STATUS  mandatory
        DESCRIPTION
                ""
        ::= { sfpsMatrixEntry 2 }

sfpsMatrixUser1Type   OBJECT-TYPE
        SYNTAX  OCTET STRING
        ACCESS  read-only
        STATUS  mandatory
        DESCRIPTION
                ""
        ::= { sfpsMatrixEntry 3 }

sfpsMatrixUser1Load   OBJECT-TYPE
        SYNTAX  OCTET STRING
        ACCESS  read-only
        STATUS  mandatory
        DESCRIPTION
                ""
        ::= { sfpsMatrixEntry 4 }

sfpsMatrixUser2Type   OBJECT-TYPE
        SYNTAX  OCTET STRING
        ACCESS  read-only
        STATUS  mandatory
        DESCRIPTION
                ""
        ::= { sfpsMatrixEntry 5 }

sfpsMatrixUser2Load   OBJECT-TYPE
        SYNTAX  OCTET STRING
        ACCESS  read-only
        STATUS  mandatory
        DESCRIPTION
                ""
        ::= { sfpsMatrixEntry 6 }

sfpsMatrixConnect   OBJECT-TYPE
        SYNTAX  INTEGER
        ACCESS  read-only
        STATUS  mandatory
        DESCRIPTION
                ""
        ::= { sfpsMatrixEntry 7 }

sfpsMatrixFlood   OBJECT-TYPE
        SYNTAX  INTEGER
        ACCESS  read-only
        STATUS  mandatory
        DESCRIPTION
                ""
        ::= { sfpsMatrixEntry 8 }


-- Matrix Information Table

sfpsMatrixInfoTable     OBJECT-TYPE
        SYNTAX  SEQUENCE OF SfpsMatrixInfoEntry
        ACCESS  not-accessible
        STATUS  mandatory
        DESCRIPTION
                " "
        ::= { sfpsVlanMatrix 2 }

sfpsMatrixInfoEntry    OBJECT-TYPE
        SYNTAX  SfpsMatrixInfoEntry
        ACCESS  not-accessible
        STATUS  mandatory
        DESCRIPTION
                ""
        INDEX   { sfpsMatrixInfoAddrType, sfpsMatrixInfoAddrHash, sfpsMatrixInfoHashIndex }
        ::= { sfpsMatrixInfoTable 1 }

SfpsMatrixInfoEntry ::=
        SEQUENCE {
                sfpsMatrixInfoAddrType          INTEGER,
                sfpsMatrixInfoAddrHash          INTEGER,
                sfpsMatrixInfoHashIndex         INTEGER,
                sfpsMatrixInfoAddrValue         OCTET STRING,
                sfpsMatrixInfoTableIndex        INTEGER,
                sfpsMatrixInfoDefConnect        INTEGER,
                sfpsMatrixInfoDefFlood          INTEGER
        }

sfpsMatrixInfoAddrType   OBJECT-TYPE
        SYNTAX  INTEGER
        ACCESS  read-only
        STATUS  mandatory
        DESCRIPTION
                ""
        ::= { sfpsMatrixInfoEntry 1 }

sfpsMatrixInfoAddrHash   OBJECT-TYPE
        SYNTAX  INTEGER
        ACCESS  read-only
        STATUS  mandatory
        DESCRIPTION
                ""
        ::= { sfpsMatrixInfoEntry 2 }

sfpsMatrixInfoHashIndex   OBJECT-TYPE
        SYNTAX  INTEGER
        ACCESS  read-only
        STATUS  mandatory
        DESCRIPTION
                ""
        ::= { sfpsMatrixInfoEntry 3 }

sfpsMatrixInfoAddrValue   OBJECT-TYPE
        SYNTAX  OCTET STRING
        ACCESS  read-only
        STATUS  mandatory
        DESCRIPTION
                ""
        ::= { sfpsMatrixInfoEntry 4 }

sfpsMatrixInfoTableIndex   OBJECT-TYPE
        SYNTAX  INTEGER
        ACCESS  read-only
        STATUS  mandatory
        DESCRIPTION
                ""
        ::= { sfpsMatrixInfoEntry 5 }

sfpsMatrixInfoDefConnect   OBJECT-TYPE
        SYNTAX  INTEGER
        ACCESS  read-only
        STATUS  mandatory
        DESCRIPTION
                ""
        ::= { sfpsMatrixInfoEntry 6 }

sfpsMatrixInfoDefFlood   OBJECT-TYPE
        SYNTAX  INTEGER
        ACCESS  read-only
        STATUS  mandatory
        DESCRIPTION
                ""
        ::= { sfpsMatrixInfoEntry 7 }

-- Matrix API

sfpsMatrixInfoVerb   OBJECT-TYPE
        SYNTAX  INTEGER {
                other(1),
                addEntry(2),
                deleteEntry(3),
                setFlagValue(4),
                clearFlagValue(5),
                setFlagGlobal(6),
                clearFlagGlobal(7),
                setDefaults(8),
                resetToDefaults(9),
                setFilter1(10),
                setFilter2(11),
                clearFilter1(12),
                clearFitler2(13),
                clearTable(14)
        }
        ACCESS  read-write
        STATUS  mandatory
        DESCRIPTION
                ""
        ::= { sfpsVlanMatrixApi 1 }

sfpsMatrixInfoIndex1Tag   OBJECT-TYPE
        SYNTAX  OCTET STRING
        ACCESS  read-write
        STATUS  mandatory
        DESCRIPTION
                ""
        ::= { sfpsVlanMatrixApi 2 }

sfpsMatrixInfoIndex1Load   OBJECT-TYPE
        SYNTAX  OCTET STRING
        ACCESS  read-write
        STATUS  mandatory
        DESCRIPTION
                ""
        ::= { sfpsVlanMatrixApi 3 }

sfpsMatrixInfoIndex2Tag   OBJECT-TYPE
        SYNTAX  INTEGER
        ACCESS  read-write
        STATUS  mandatory
        DESCRIPTION
                ""
        ::= { sfpsVlanMatrixApi 4 }

sfpsMatrixInfoIndex2Load   OBJECT-TYPE
        SYNTAX  OCTET STRING
        ACCESS  read-write
        STATUS  mandatory
        DESCRIPTION
                ""
        ::= { sfpsVlanMatrixApi 5 }

sfpsMatrixInfoMatrixFlag   OBJECT-TYPE
        SYNTAX  INTEGER         {
                connect(1),
                flood(2)
        }
        ACCESS  read-write
        STATUS  mandatory
        DESCRIPTION
                ""
        ::= { sfpsVlanMatrixApi 6 }

sfpsMatrixInfoFlagMask   OBJECT-TYPE
        SYNTAX  HexInteger
        ACCESS  read-write
        STATUS  mandatory
        DESCRIPTION
                ""
        ::= { sfpsVlanMatrixApi 7 }

sfpsMatrixInfoFilter1Tag   OBJECT-TYPE
        SYNTAX  OCTET STRING
        ACCESS  read-write
        STATUS  mandatory
        DESCRIPTION
                ""
        ::= { sfpsVlanMatrixApi 8 }

sfpsMatrixInfoFilter1Load   OBJECT-TYPE
        SYNTAX  OCTET STRING
        ACCESS  read-write
        STATUS  mandatory
        DESCRIPTION
                ""
        ::= { sfpsVlanMatrixApi 9 }

sfpsMatrixInfoFilter2Tag   OBJECT-TYPE
        SYNTAX  OCTET STRING
        ACCESS  read-write
        STATUS  mandatory
        DESCRIPTION
                ""
        ::= { sfpsVlanMatrixApi 10 }

sfpsMatrixInfoFilter2Load   OBJECT-TYPE
        SYNTAX  OCTET STRING
        ACCESS  read-write
        STATUS  mandatory
        DESCRIPTION
                ""
        ::= { sfpsVlanMatrixApi 11 }

-- VMMatrix

sfpsVMMatrixRowIndex   OBJECT-TYPE
        SYNTAX  INTEGER
        ACCESS  read-write
        STATUS  mandatory
        DESCRIPTION
                ""
        ::= { sfpsVMMatrix 1 }

sfpsVMMatrixCellIndexMask   OBJECT-TYPE
        SYNTAX  OCTET STRING
        ACCESS  read-write
        STATUS  mandatory
        DESCRIPTION
                ""
        ::= { sfpsVMMatrix 2 }

sfpsVMMatrixAction   OBJECT-TYPE
        SYNTAX  INTEGER
        ACCESS  read-write
        STATUS  mandatory
        DESCRIPTION
                ""
        ::= { sfpsVMMatrix 3 }

END
