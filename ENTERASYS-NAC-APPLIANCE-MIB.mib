ENTERASYS-NAC-APPLIANCE-MIB DEFINITIONS ::= BEGIN

--  enterasys-nac-appliance-mib.txt
--
--  Part Number:
--

--  This module provides authoritative definitions for Enterasys
--  Networks' NAC Appliance Status MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright March, 2010 Enterasys Networks, Inc


IMPORTS
    OBJECT-TYPE, Counter64, MODULE-IDENTITY
        FROM SNMPv2-SMI
    MODULE-COMPLIANCE, OBJECT-GROUP
        FROM SNMPv2-CONF
    etsysModules
        FROM ENTERASYS-MIB-NAMES;


etsysNacApplianceMIB MODULE-IDENTITY
    LAST-UPDATED "201003091303Z"  -- Tue Mar  9 13:03 UTC 2010
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP enterprise
         MIBs under Enterasys Networks' enterprise OID pertaining to
         NAC Appliance Status."

    REVISION    "201003091303Z"  -- Tue Mar  9 13:03 UTC 2010
    DESCRIPTION "The initial version of this MIB module."
    ::= { etsysModules 73 }


-- -------------------------------------------------------------
-- MIB Objects
-- -------------------------------------------------------------

etsysNacApplianceObjects   OBJECT IDENTIFIER
                           ::= { etsysNacApplianceMIB 1 }


etsysNacApplAuthenticationRequests OBJECT-TYPE
    SYNTAX      Counter64
    MAX-ACCESS  read-only
    STATUS      current
    DESCRIPTION
        "Represents the number of authentication requests made since the NAC
         was started."
    ::= { etsysNacApplianceObjects 1 }

etsysNacApplAuthenticationSuccesses OBJECT-TYPE
    SYNTAX      Counter64
    MAX-ACCESS  read-only
    STATUS      current
    DESCRIPTION
        "Represents the number of successful authentication requests made
         since the NAC was started."
    ::= { etsysNacApplianceObjects 2 }

etsysNacApplAuthenticationFailures OBJECT-TYPE
    SYNTAX      Counter64
    MAX-ACCESS  read-only
    STATUS      current
    DESCRIPTION
        "Represents the number of failed authentication requests made
         since the NAC was started."
    ::= { etsysNacApplianceObjects 3 }

etsysNacApplRadiusChallenges OBJECT-TYPE
    SYNTAX      Counter64
    MAX-ACCESS  read-only
    STATUS      current
    DESCRIPTION
        "Represents the number of Radius challenges made since the NAC
         was started."
    ::= { etsysNacApplianceObjects 4 }

etsysNacApplAuthenticationInvalidRequests OBJECT-TYPE
    SYNTAX      Counter64
    MAX-ACCESS  read-only
    STATUS      current
    DESCRIPTION
        "Represents the number of invalid authentication requests made
         since the NAC was started."
    ::= { etsysNacApplianceObjects 5 }

etsysNacApplAuthenticationDuplicateRequests OBJECT-TYPE
    SYNTAX      Counter64
    MAX-ACCESS  read-only
    STATUS      current
    DESCRIPTION
        "Represents the number of duplicate authentication requests made
         since the NAC was started."
    ::= { etsysNacApplianceObjects 6 }

etsysNacApplAuthenticationMalformedRequests OBJECT-TYPE
    SYNTAX      Counter64
    MAX-ACCESS  read-only
    STATUS      current
    DESCRIPTION
        "Represents the number of malformed authentication requests made
         since the NAC was started."
    ::= { etsysNacApplianceObjects 7 }

etsysNacApplAuthenticationBadRequests OBJECT-TYPE
    SYNTAX      Counter64
    MAX-ACCESS  read-only
    STATUS      current
    DESCRIPTION
        "Represents the number of bad authentication requests made since
         the NAC was started."
    ::= { etsysNacApplianceObjects 8 }

etsysNacApplAuthenticationDroppedPackets OBJECT-TYPE
    SYNTAX      Counter64
    MAX-ACCESS  read-only
    STATUS      current
    DESCRIPTION
        "Represents the number of dropped authentication packets since
         the NAC was started."
    ::= { etsysNacApplianceObjects 9 }

etsysNacApplAuthenticationUnknownTypes OBJECT-TYPE
    SYNTAX      Counter64
    MAX-ACCESS  read-only
    STATUS      current
    DESCRIPTION
        "Represents the number of unknown authentication types since
         the NAC was started."
    ::= { etsysNacApplianceObjects 10 }

etsysNacApplAssessmentRequests OBJECT-TYPE
    SYNTAX      Counter64
    MAX-ACCESS  read-only
    STATUS      current
    DESCRIPTION
        "Represents the number of assessment requests made since the
         NAC was started."
    ::= { etsysNacApplianceObjects 11 }

etsysNacApplCaptivePortalRequests OBJECT-TYPE
    SYNTAX      Counter64
    MAX-ACCESS  read-only
    STATUS      current
    DESCRIPTION
    "Represents the number of captive portal requests made since the NAC
         was started."
    ::= { etsysNacApplianceObjects 12 }

etsysNacApplContactLostSwitches OBJECT-TYPE
    SYNTAX      Counter64
    MAX-ACCESS  read-only
    STATUS      current
    DESCRIPTION
        "Represents the number of configured switches with which the NAC
         has lost SNMP contact."
    ::= { etsysNacApplianceObjects 13 }

etsysNacApplIPResolutionFailures OBJECT-TYPE
    SYNTAX      Counter64
    MAX-ACCESS  read-only
    STATUS      current
    DESCRIPTION
    "Represents the number of failed IP Resolution attempts made since
         the NAC was started."
    ::= { etsysNacApplianceObjects 14 }

etsysNacApplIPResolutionTimeouts OBJECT-TYPE
    SYNTAX      Counter64
    MAX-ACCESS  read-only
    STATUS      current
    DESCRIPTION
        "Represents the number of IP Resolution attempts that timed out
         since the NAC was started."
    ::= { etsysNacApplianceObjects 15 }

etsysNacApplConnectedAgents OBJECT-TYPE
    SYNTAX      Counter64
    MAX-ACCESS  read-only
    STATUS      current
    DESCRIPTION
        "Represents the number of End-System Assessment Agents currently
         connected to the NAC."
    ::= { etsysNacApplianceObjects 16 }

-- -------------------------------------------------------------
-- Conformance Information
-- -------------------------------------------------------------

etsysNacApplianceMIBConformance OBJECT IDENTIFIER
                                ::= { etsysNacApplianceMIB 2 }
etsysNacApplianceMIBGroups      OBJECT IDENTIFIER
                                ::= { etsysNacApplianceMIBConformance 1 }
etsysNacApplianceMIBCompliances OBJECT IDENTIFIER
                                ::= { etsysNacApplianceMIBConformance 2 }

-- -------------------------------------------------------------
-- Units of conformance
-- -------------------------------------------------------------

etsysNacApplianceMIBGroup OBJECT-GROUP
    OBJECTS {
        etsysNacApplAuthenticationRequests,
        etsysNacApplAuthenticationSuccesses,
        etsysNacApplAuthenticationFailures,
        etsysNacApplRadiusChallenges,
        etsysNacApplAuthenticationInvalidRequests,
        etsysNacApplAuthenticationDuplicateRequests,
        etsysNacApplAuthenticationMalformedRequests,
        etsysNacApplAuthenticationBadRequests,
        etsysNacApplAuthenticationDroppedPackets,
        etsysNacApplAuthenticationUnknownTypes,
        etsysNacApplAssessmentRequests,
        etsysNacApplCaptivePortalRequests,
        etsysNacApplContactLostSwitches,
        etsysNacApplIPResolutionFailures,
        etsysNacApplIPResolutionTimeouts,
        etsysNacApplConnectedAgents
    }
    STATUS current
    DESCRIPTION
        "The basic collection of objects providing status
         information about the NAC Appliance."
    ::= { etsysNacApplianceMIBGroups 1 }

-- -------------------------------------------------------------
-- Compliance statements
-- -------------------------------------------------------------

etsysNacApplianceMIBCompliance MODULE-COMPLIANCE
    STATUS  current
    DESCRIPTION
        "The compliance statement for clients implementing the NAC
         Appliance Status MIB."
    MODULE  -- this module
        MANDATORY-GROUPS { etsysNacApplianceMIBGroup }

    ::= { etsysNacApplianceMIBCompliances 1 }

END
