CTRON-Q-BRIDGE-MIB-EXT DEFINITIONS ::= BEGIN

--  ctron-q-bridge-mib-ext.txt
--
--  This module provides authoritative definitions for Cabletron's
--  CTRON-Q-BRIDGE-MIB-EXT.
--
--  This module will be extended, as needed.
--
--  Enterasys Networks reserves the right to make changes in
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys grants vendors, end-users, and other interested parties
--  a non-exclusive license to use this Specification in connection
--  with the management of Enterasys and Cabletron products.
--
--  Copyright April 2001 Cabletron Systems
--  Copyright 2002-2012 Enterasys Networks, Inc.

IMPORTS
    MODULE-IDENTITY, OBJECT-TYPE
        FROM SNMPv2-SMI
    MODULE-COMPLIANCE, OBJECT-GROUP
        FROM SNMPv2-CONF
    TruthValue
        FROM SNMPv2-TC
    dot1dBasePortEntry, dot1dBasePort
        FROM BRIDGE-MIB
    EnabledStatus
        FROM P-BRIDGE-MIB
    VlanIndex, dot1qVlanCurrentEntry, PortList, dot1qVlanIndex,
    dot1qFdbId, dot1qTpFdbAddress
        FROM Q-BRIDGE-MIB
    ctVlanExt
        FROM CTRON-MIB-NAMES;

ctQBridgeMibExt MODULE-IDENTITY
    LAST-UPDATED "201202141442Z"  -- Tue Feb 14 14:42 UTC 2012
    ORGANIZATION "Enterasys Networks, Inc."
    CONTACT-INFO
        "Postal:  Enterasys Networks
                  50 Minuteman Rd.
                  Andover, MA 01810-1008
                  USA
         Phone:   +1 978 684 1000
         E-mail:  support@enterasys.com
         WWW:     http://www.enterasys.com"

    DESCRIPTION
            "This MIB module defines a portion of the SNMP enterprise
             MIBs under the Cabletron enterprise OID pertaining to
             the configuration of switches that support IEEE 802.1Q
             [802.1Q] and the Q-BRIDGE-MIB [RFC2674]."

    REVISION    "201202141442Z"  -- Tue Feb 14 14:42 UTC 2012
    DESCRIPTION "Added the mvrp(8) enumeration to the
                 ctDot1qPortVlanEgressStatus object."

    REVISION    "201201091349Z"  -- Mon Jan  9 13:49 UTC 2012
    DESCRIPTION "Added the ctDot1qPortVlanStaticEgressTable to show
                 egress information for static VLANs regardless of
                 forwarding status."

    REVISION    "201006301825Z"  -- Wed Jun 30 18:25 UTC 2010
    DESCRIPTION "Added the ctDot1qVlanGvrpRestrictedTable to allow
                 GVRP participation to be controlled on a per VLAN
                 basis."

    REVISION    "200702161744Z"  -- Fri Feb 16 17:44 UTC 2007
    DESCRIPTION "Added the rfc3580VlanTunnelAttribute enumeration
                 to the ctDot1qPortVlanEgressStatus leaf."

    REVISION    "200501211717Z"  -- Fri Jan 21 17:17 GMT 2005
    DESCRIPTION "Added the ctDot1qTpFdbExtTable to allow a mechanism
                 for removing learned(3) entries from the filter
                 database."

    REVISION    "200406041241Z"  -- Fri Jun  4 12:41 GMT 2004
    DESCRIPTION "Added the ctDot1qPortVlanEgressTable to represent egress
                 information on a per port basis."

    REVISION    "200312152053Z"  -- Mon Dec 15 20:53 GMT 2003
    DESCRIPTION "Added ctDot1qPortReplaceTCI to allow the optional
                 replacement of the original Tag Control Information
                 (TCI) in an 802.1Q tagged frame."

    REVISION    "200207262045Z"  -- Fri Jul 26 20:45 GMT 2002
    DESCRIPTION "Changed the description of
                 ctDot1qVlanForbidEgressPorts."

    REVISION    "200207191412Z"  -- Fri Jul 19 14:12 GMT 2002
    DESCRIPTION "Added the ctDot1qVlanCurrentExtTable.
                 Changed CONTACT-INFO clause to Enterasys Networks."

    REVISION    "200104161816Z"
    DESCRIPTION "Minor grammatical changes."

    REVISION    "200101101329Z"
    DESCRIPTION "Added the ctDot1qPortDiscardTagged leaf for additional
                 backwards compatibility with the now obsolete
                 CTRON-VLAN-EXTENSIONS-MIB.  Fixed the INDEX clause of
                 the ctDot1qVlanDynamicEgressEntry.  Added the new
                 ctQBridgePortGroup2 OBJECT-GROUP and ctDot1qVlan2
                 MODULE-COMPLIANCE.  Deprecated the ctQBridgePortGroup
                 OBJECT-GROUP and ctDot1qVlan MODULE-COMPLIANCE."

    REVISION    "199910060812Z"
    DESCRIPTION "The initial version of this MIB module published as
                 01.00.00."
         ::= { ctVlanExt 7 }


-- branches used in this MIB
ctQBridgeMIBObjects OBJECT IDENTIFIER ::= { ctQBridgeMibExt 1 }

-- -------------------------------------------------------------
-- The VLAN Port Extension Configuration Table
-- -------------------------------------------------------------
ctDot1qPortVlanExtTable OBJECT-TYPE
    SYNTAX      SEQUENCE OF CtDot1qPortVlanEntry
    MAX-ACCESS  not-accessible
    STATUS      current
    DESCRIPTION
        "A table containing per port control and status information
        for Cabletron proprietary extensions pertaining to VLAN
        configuration in the device."
    ::= { ctQBridgeMIBObjects 1 }

ctDot1qPortVlanEntry OBJECT-TYPE
    SYNTAX      CtDot1qPortVlanEntry
    MAX-ACCESS  not-accessible
    STATUS      current
    DESCRIPTION
        "Information controlling proprietary VLAN configuration for
        a port on the device.  This is indexed by dot1dBasePort."
    AUGMENTS { dot1dBasePortEntry }
    ::= { ctDot1qPortVlanExtTable 1 }

CtDot1qPortVlanEntry ::=
    SEQUENCE {
        ctDot1qPortDefaultForwardMode
            INTEGER,
        ctDot1qPortDiscardTagged
            EnabledStatus,
        ctDot1qPortReplaceTCI
            EnabledStatus
    }

ctDot1qPortDefaultForwardMode OBJECT-TYPE
    SYNTAX      INTEGER {
                    forwardNoFrames(1),
                    forwardAllFramesAsTagged(2),
                    forwardAllFramesAsUntagged(3)
                }
    MAX-ACCESS  read-write
    STATUS      current
    DESCRIPTION
        "The method used to forward frames belonging to VLANs that
        do not have an entry in the dot1qVlanCurrentTable.

        When this is forwardNoFrames(1), the device will not forward
        traffic out this port, for any VLAN that does not have an
        entry in the dot1qVlanCurrentTable.

        When this is forwardAllFramesAsTagged(2), the device will
        forward all traffic out this port, with an 802.1Q VLAN tag,
        for any VLAN that does not have an entry in
        dot1qVlanCurrentTable.

        When this is forwardAllFramesAsUntagged(3), the device will
        forward all traffic out this port, without an 802.1Q VLAN tag,
        for any VLAN that does not have an entry in
        dot1qVlanCurrentTable.

        This control does not affect VLAN independent BPDU frames,
        such as GVRP and STP.  It does affect VLAN dependent BPDU
        frames, such as GMRP."
    DEFVAL      { forwardNoFrames }
    ::= { ctDot1qPortVlanEntry 1 }

ctDot1qPortDiscardTagged OBJECT-TYPE
    SYNTAX      EnabledStatus
    MAX-ACCESS  read-write
    STATUS      current
    DESCRIPTION
        "The method used to discard all incoming VLAN tagged frames
        for the port specified by the indexing of this entry.

        When this is enabled(1), the device will discard all 802.1Q
        tagged packets received on this port.

        When this is disabled(2), the device will NOT discard frames
        received on this port based on the presence of an 802.1Q tag.

        The behavior of this method in conjunction with the
        dot1qPortAcceptableFrameTypes leaf of Q-BRIDGE-MIB [RFC2674]
        is that of a logical OR."
    DEFVAL      { disabled }
    ::= { ctDot1qPortVlanEntry 2 }

ctDot1qPortReplaceTCI OBJECT-TYPE
    SYNTAX      EnabledStatus
    MAX-ACCESS  read-write
    STATUS      current
    DESCRIPTION
        "The method used to replace the Tag Control Information (TCI)
        field in all VLAN tagged frames received on the port specified
        by the indexing of this entry.

        When this is enabled(1), the device will replace the 802.1Q
        TCI field with results of the INGRESS stage of frame forwarding.
        Logically, this happens immediately prior to the PROGRESS stage
        of frame relay.

        When this is disabled(2), the device operates in compliance with
        the IEEE 802.1Q standard and honors the TCI field of incident
        frames."
    REFERENCE
        "IEEE Std. 802.1Q-1998: Section 9.3.2"
    DEFVAL      { disabled }
    ::= { ctDot1qPortVlanEntry 3 }

-- -------------------------------------------------------------
-- The Cabletron Dynamic Egress Configuration Table
-- -------------------------------------------------------------

ctDot1qVlanDynamicEgressTable OBJECT-TYPE
    SYNTAX      SEQUENCE OF CtDot1qVlanDynamicEgressEntry
    MAX-ACCESS  not-accessible
    STATUS      current
    DESCRIPTION
        "A table containing per VLAN control and status
        information for Cabletron proprietary egress extensions for
        VLAN configuration in the device."
    ::= { ctQBridgeMIBObjects 2 }

ctDot1qVlanDynamicEgressEntry OBJECT-TYPE
    SYNTAX      CtDot1qVlanDynamicEgressEntry
    MAX-ACCESS  not-accessible
    STATUS      current
    DESCRIPTION
        "Information controlling proprietary VLAN configuration
        for a device."
    INDEX { ctDot1qVlanDynamicEgressIndex }
    ::= { ctDot1qVlanDynamicEgressTable 1 }

CtDot1qVlanDynamicEgressEntry ::=
    SEQUENCE {
        ctDot1qVlanDynamicEgressIndex
            VlanIndex,
        ctDot1qVlanDynamicEgressStatus
            EnabledStatus
    }

ctDot1qVlanDynamicEgressIndex OBJECT-TYPE
    SYNTAX      VlanIndex
    MAX-ACCESS  not-accessible
    STATUS      current
    DESCRIPTION
        "The VLAN to which this entries' dynamic egress status
        applies."
    ::= { ctDot1qVlanDynamicEgressEntry 1 }

ctDot1qVlanDynamicEgressStatus OBJECT-TYPE
    SYNTAX      EnabledStatus
    MAX-ACCESS  read-write
    STATUS      current
    DESCRIPTION
        "The state of Dynamic Egress operation on this VLAN.  The
        value enabled(1) indicates that Dynamic Egress is enabled on
        this VLAN.  If Dynamic Egress is enabled for a VLAN the
        following rules are applied to received frames:

        1. If the frame is untagged, and

        2. The frame is successfully classified to the specified
           VLAN, and

        3. The port the frame was received on is not configured in
           dot1qVlanCurrentEgressPorts, dot1qVlanCurrentUntaggedPorts,
           or dot1qVlanForbiddenEgressPorts, for the classified VLAN,
           and

        4. The port is configured for forwardNoFrames(1) in
           ctDot1qPortDefaultForwardMode (if supported), then

        5. The port the frame was received on will be added to
           the dot1qVlanCurrentEgressPorts and
           dot1qVlanCurrentUntaggedPorts for the classified VLAN.
           If the VLAN was not preexisting the dot1qVlanStatus
           leaf for the VLAN will return other(1)."
    DEFVAL      { disabled }
    ::= { ctDot1qVlanDynamicEgressEntry 2 }

-- -------------------------------------------------------------
-- The VLAN Current Table Extension.
-- -------------------------------------------------------------
ctDot1qVlanCurrentExtTable OBJECT-TYPE
    SYNTAX      SEQUENCE OF CtDot1qVlanCurrentExtEntry
    MAX-ACCESS  not-accessible
    STATUS      current
    DESCRIPTION
        "A table containing current configuration information
        for each VLAN currently configured into the device by
        (local or network) management or created dynamically created.
        This table provides proprietary extensions to
        dot1qVlanCurrentTable as defined in RFC2674."
    ::= { ctQBridgeMIBObjects 3 }

ctDot1qVlanCurrentEntryExt OBJECT-TYPE
    SYNTAX      CtDot1qVlanCurrentExtEntry
    MAX-ACCESS  not-accessible
    STATUS      current
    DESCRIPTION
        "Information for a VLAN configured into the device by
        (local or network) management or created dynamically."
    AUGMENTS { dot1qVlanCurrentEntry }
    ::= { ctDot1qVlanCurrentExtTable 1 }

CtDot1qVlanCurrentExtEntry ::=
    SEQUENCE {
        ctDot1qVlanForbidEgressPorts
            PortList
    }

ctDot1qVlanForbidEgressPorts OBJECT-TYPE
    SYNTAX      PortList
    MAX-ACCESS  read-only
    STATUS      current
    DESCRIPTION
        "The current set of ports which are prohibited from being
        included in the egress list for this VLAN.  This object is a
        logical combination of dot1qVlanForbiddenEgressPorts and zero
        or more proprietary methods of forbidding egress on a per port
        per VLAN basis."
    ::= { ctDot1qVlanCurrentEntryExt 1 }


-- -------------------------------------------------------------
-- The VLAN Port Egress Information Configuration Table
-- -------------------------------------------------------------
ctDot1qPortVlanEgressTable OBJECT-TYPE
    SYNTAX      SEQUENCE OF CtDot1qPortVlanEgressEntry
    MAX-ACCESS  not-accessible
    STATUS      current
    DESCRIPTION
        "A table containing per port, per VLAN egress information.
        This table represents information contained in the
        dot1qVlanCurrentTable, but indexed by port instead of by VLAN.
        Only ports that a given VLAN is actively egressing are
        represented in this table."
    ::= { ctQBridgeMIBObjects 4 }

ctDot1qPortVlanEgressEntry OBJECT-TYPE
    SYNTAX      CtDot1qPortVlanEgressEntry
    MAX-ACCESS  not-accessible
    STATUS      current
    DESCRIPTION
        "Information related to egress on a per port, per VLAN basis.
         The entry also represents the method that caused the port
         to have egress."
    INDEX { dot1dBasePort, dot1qVlanIndex }
    ::= { ctDot1qPortVlanEgressTable 1 }

CtDot1qPortVlanEgressEntry ::=
    SEQUENCE {
        ctDot1qPortVlanEgressStatus
            INTEGER,
        ctDot1qPortVlanEgressType
            INTEGER
    }

ctDot1qPortVlanEgressStatus OBJECT-TYPE
    SYNTAX      INTEGER {
                    other(1),
                    static(2),
                    gvrp(3),
                    ctDynamicEgress(4),
                    etsysPolicyProfile(5),
                    ctPortDefFwdMode(6),
                    rfc3580VlanTunnelAttribute(7),
                    mvrp(8)
                }
    MAX-ACCESS  read-only
    STATUS      current
    DESCRIPTION
        "This object indicates the method that is causing the VLAN to
         egress on this port.

            other(1) - The VLAN is currently egressing on this port but
                the conditions under which it will remain so differ
                from the following values.

            static(2) - The VLAN is currently egressing on this port
                as a result of static configuration in the
                dot1qVlanStaticTable.

            gvrp(3) - The VLAN is currently egressing on this port
                as a result of GVRP.

            ctDynamicEgress(4) - The VLAN is currently egressing on this
                port as a result of ctDyanmicEgress.  This feature
                is controlled by the ctDot1qVlanDynamicEgressStatus
                object.

            etsysPolicyProfile(5) - The VLAN is currently egressing on
                this port as a result of policy configuration in the
                ENTERASYS-POLICY-PROFILE-MIB.

            ctPortDefFwdMode(6) - The VLAN is currently egressing on
                this port as a result of explicit configuration of the
                ctDot1qPortDefaultForwardMode object for this port.

            rfc3580VlanTunnelAttribute(7) - The VLAN is currently
                egressing on this port as a result of a specified
                RFC3580 VLAN Tunnel Attribute.

            mvrp(8) - The VLAN is currently egressing on this port
                as a result of MVRP."
    ::= { ctDot1qPortVlanEgressEntry 1 }

ctDot1qPortVlanEgressType OBJECT-TYPE
    SYNTAX      INTEGER {
                    tagged(1),
                    untagged(2),
                    forbidden(3)
                }
    MAX-ACCESS  read-only
    STATUS      current
    DESCRIPTION
        "This object indicates the type of egress the VLAN has on this
         port.

            tagged(1) - Frames for the specified VLAN egressing this port
                have an 802.1Q tag.

            untagged(2) - Frames for the specified VLAN egressing this port
                do not have an 802.1Q tag.

            forbidden(3) - Frames for the specified VLAN are not allowed
                to egress this port under any circumstances."
    ::= { ctDot1qPortVlanEgressEntry 2 }

-- -------------------------------------------------------------
-- The 802.1Q Transparent Filter Database Extension Table
-- -------------------------------------------------------------
ctDot1qTpFdbExtTable OBJECT-TYPE
    SYNTAX      SEQUENCE OF CtDot1qTpFdbExtEntry
    MAX-ACCESS  not-accessible
    STATUS      current
    DESCRIPTION
        "A table that extends the functionality provided by the
         dot1qTpFdbTable of Q-BRIDGE-MIB.  Only unicast
         MAC addresses with a dot1qTpFdbStatus of learned(3)
         will appear in this table."
    REFERENCE
        "RFC 2674, 'Definitions of Managed Objects for Bridges with
         Traffic Classes, Multicast Filtering and Virtual LAN
         Extensions'"
    ::= { ctQBridgeMIBObjects 5 }

ctDot1qTpFdbExtEntry OBJECT-TYPE
    SYNTAX      CtDot1qTpFdbExtEntry
    MAX-ACCESS  not-accessible
    STATUS      current
    DESCRIPTION
        "Information about a specific unicast MAC address for
         which the device has some forwarding and/or filtering
         information."
    INDEX { dot1qFdbId, dot1qTpFdbAddress }
    ::= { ctDot1qTpFdbExtTable 1 }

CtDot1qTpFdbExtEntry ::=
    SEQUENCE {
        ctDot1qTpFdbRemoveAddress
            TruthValue
    }

ctDot1qTpFdbRemoveAddress OBJECT-TYPE
    SYNTAX      TruthValue
    MAX-ACCESS  read-write
    STATUS      current
    DESCRIPTION
        "When this is object is set to true(1) the unicast MAC
         address specified by the indexing will be removed from
         transparent filter database.  A set to false(2) will
         have no effect.  This object will always return false(2)."
    DEFVAL      { false }
    ::= { ctDot1qTpFdbExtEntry 1 }

-- -------------------------------------------------------------
-- The Cabletron GVRP VLAN Restriction Configuration Table
-- -------------------------------------------------------------

ctDot1qVlanGvrpRestrictedTable OBJECT-TYPE
    SYNTAX      SEQUENCE OF CtDot1qVlanGvrpRestrictedEntry
    MAX-ACCESS  not-accessible
    STATUS      current
    DESCRIPTION
        "A table containing per VLAN control and status
        information for GVRP VLAN configuration in the device."
    ::= { ctQBridgeMIBObjects 6 }

ctDot1qVlanGvrpRestrictedEntry OBJECT-TYPE
    SYNTAX      CtDot1qVlanGvrpRestrictedEntry
    MAX-ACCESS  not-accessible
    STATUS      current
    DESCRIPTION
        "Information controlling proprietary VLAN configuration
        for GVRP on a device."
    INDEX { ctDot1qVlanGvrpRestrictedIndex }
    ::= { ctDot1qVlanGvrpRestrictedTable 1 }

CtDot1qVlanGvrpRestrictedEntry ::=
    SEQUENCE {
        ctDot1qVlanGvrpRestrictedIndex
            VlanIndex,
        ctDot1qVlanGvrpRestrictedStatus
            EnabledStatus
    }

ctDot1qVlanGvrpRestrictedIndex OBJECT-TYPE
    SYNTAX      VlanIndex
    MAX-ACCESS  not-accessible
    STATUS      current
    DESCRIPTION
        "The VLAN to which this entry's restricted GVRP status
        applies."
    ::= { ctDot1qVlanGvrpRestrictedEntry 1 }

ctDot1qVlanGvrpRestrictedStatus OBJECT-TYPE
    SYNTAX      EnabledStatus
    MAX-ACCESS  read-write
    STATUS      current
    DESCRIPTION
        "The state of restricted GVRP operation for this VLAN.  The
        value enabled(1) indicates that restricted GVRP operation is
	enabled for this VLAN.  This object affects GVRP Applicant
        and Registrar state machines for this VLAN on all ports.
        If restricted GVRP is enabled for a VLAN the following rules
        are applied:

        1. If GVRP is globally enabled and

        2. If GVRP is enabled at the port level, then

        3. Any ports that were members of the dot1qVlanCurrentEgressPorts
	   table due to GVRP will signal to remove this registration and no
           further registration requests received in GVRP PDUs for this
           VLAN will be processed and

        4. Any ports that were propagating registration information for
           this VLAN will cease propagation and all further GVRP PDUs
           transmitted after the initial withdrawal attempt will not
           include event notifications for this VLAN."
    DEFVAL      { disabled }
    ::= { ctDot1qVlanGvrpRestrictedEntry 2 }


-- -------------------------------------------------------------
-- The Static VLAN Port Egress Information Configuration Table
-- -------------------------------------------------------------
ctDot1qPortVlanStaticEgressTable OBJECT-TYPE
    SYNTAX      SEQUENCE OF CtDot1qPortVlanStaticEgressEntry
    MAX-ACCESS  not-accessible
    STATUS      current
    DESCRIPTION
        "A table containing per port, per VLAN egress information.
        This table represents information contained in the
        dot1qVlanStaticTable, but indexed by port instead of by VLAN.
        Only ports configured to static VLANs are represented in this table."
    ::= { ctQBridgeMIBObjects 7 }

ctDot1qPortVlanStaticEgressEntry OBJECT-TYPE
    SYNTAX      CtDot1qPortVlanStaticEgressEntry
    MAX-ACCESS  not-accessible
    STATUS      current
    DESCRIPTION
        "Information related to egress on a per port, per VLAN basis.
         Only statically configured VLANs are shown."
    INDEX { dot1dBasePort, dot1qVlanIndex }
    ::= { ctDot1qPortVlanStaticEgressTable 1 }

CtDot1qPortVlanStaticEgressEntry ::=
    SEQUENCE {
        ctDot1qPortVlanStaticEgressType
            INTEGER
    }

ctDot1qPortVlanStaticEgressType OBJECT-TYPE
    SYNTAX      INTEGER {
                    tagged(1),
                    untagged(2),
                    forbidden(3)
                }
    MAX-ACCESS  read-only
    STATUS      current
    DESCRIPTION
        "This object indicates the type of egress the statically configured
	 VLAN has on this port.

            tagged(1) - Frames for the specified VLAN egressing this port
                have an 802.1Q tag.

            untagged(2) - Frames for the specified VLAN egressing this port
                do not have an 802.1Q tag.

            forbidden(3) - Frames for the specified VLAN are not allowed
                to egress this port under any circumstances."
    ::= { ctDot1qPortVlanStaticEgressEntry 1 }


-- -------------------------------------------------------------
-- Conformance Information
-- -------------------------------------------------------------

ctQBridgeConformance OBJECT IDENTIFIER ::= { ctQBridgeMibExt 2 }

ctQBridgeGroups      OBJECT IDENTIFIER ::= { ctQBridgeConformance 1 }
ctQBridgeCompliances OBJECT IDENTIFIER ::= { ctQBridgeConformance 2 }

-- -------------------------------------------------------------
-- Units of conformance
-- -------------------------------------------------------------

ctQBridgePortGroup OBJECT-GROUP
    OBJECTS { ctDot1qPortDefaultForwardMode }
    STATUS      deprecated
    DESCRIPTION
        "********* THIS GROUP IS DEPRECATED **********

        A collection of objects providing port level control
        over the forwarding behavior of frames classified to
        unconfigured VLANs."
    ::= { ctQBridgeGroups 1 }


ctQBridgeVlanGroup OBJECT-GROUP
    OBJECTS { ctDot1qVlanDynamicEgressStatus }
    STATUS      current
    DESCRIPTION
        "A collection of objects providing device level control
        over the addition and deletion of unconfigured ports to
        the egress lists of VLANs."
    ::= { ctQBridgeGroups 2 }

ctQBridgePortGroup2 OBJECT-GROUP
    OBJECTS {
              ctDot1qPortDefaultForwardMode,
              ctDot1qPortDiscardTagged
            }
    STATUS      current
    DESCRIPTION
        "A collection of objects providing port level control
        over the ingress and egress of frames received by the device."
    ::= { ctQBridgeGroups 3 }

ctQBridgeVlanCurrentForbidGroup OBJECT-GROUP
    OBJECTS { ctDot1qVlanForbidEgressPorts }
    STATUS      current
    DESCRIPTION
        "A collection of objects providing read-only current operational
        information pertaining to forbidden egress on a per VLAN basis."
    ::= { ctQBridgeGroups 4 }

ctQBridgePortReplaceTCIGroup OBJECT-GROUP
    OBJECTS {
              ctDot1qPortReplaceTCI
            }
    STATUS      current
    DESCRIPTION
        "An object providing port level control TCI replacement."
    ::= { ctQBridgeGroups 5 }

ctQBridgePortVlanEgressGroup OBJECT-GROUP
    OBJECTS {
              ctDot1qPortVlanEgressStatus,
              ctDot1qPortVlanEgressType
            }
    STATUS      deprecated
    DESCRIPTION
        "********* THIS GROUP IS DEPRECATED **********

         Objects providing per port, per VLAN egress information."
    ::= { ctQBridgeGroups 6 }

ctQBridgeTpFdbTableExtGroup OBJECT-GROUP
    OBJECTS {
              ctDot1qTpFdbRemoveAddress
            }
    STATUS      current
    DESCRIPTION
        "Objects providing per 802.1Q unicast MAC address configuration."
    ::= { ctQBridgeGroups 7 }

ctQBridgeVlanGvrpGroup OBJECT-GROUP
    OBJECTS { ctDot1qVlanGvrpRestrictedStatus }
    STATUS      current
    DESCRIPTION
        "A collection of objects providing device level control over
         the ability of GVRP to add and remove unconfigured ports to
         the egress list of particular VLANs."
    ::= { ctQBridgeGroups 8 }

ctQBridgePortVlanEgressGroup2 OBJECT-GROUP
    OBJECTS {
              ctDot1qPortVlanEgressStatus,
              ctDot1qPortVlanEgressType,
              ctDot1qPortVlanStaticEgressType
            }
    STATUS      current
    DESCRIPTION
        "Objects providing per port, per VLAN egress information."
    ::= { ctQBridgeGroups 9 }

-- -------------------------------------------------------------
-- Compliance statements
-- -------------------------------------------------------------

ctDot1qVlan MODULE-COMPLIANCE
    STATUS      deprecated
    DESCRIPTION
        "******** THIS COMPLIANCE IS DEPRECATED ********

        The compliance statement for devices that support
        Cabletron extensions to Q-BRIDGE-MIB."

    MODULE
        MANDATORY-GROUPS {
            ctQBridgePortGroup,
            ctQBridgeVlanGroup
        }
    ::= { ctQBridgeCompliances  1 }

ctDot1qVlan2 MODULE-COMPLIANCE
    STATUS      deprecated
    DESCRIPTION
        "******** THIS COMPLIANCE IS DEPRECATED ********

        The compliance statement for devices that support
        Cabletron extensions to Q-BRIDGE-MIB."

    MODULE
        MANDATORY-GROUPS {
            ctQBridgeVlanGroup,
            ctQBridgePortGroup2
        }
        GROUP       ctQBridgePortReplaceTCIGroup
        DESCRIPTION
            "This group is REQUIRED for devices supporting TCI
            replacement."
    ::= { ctQBridgeCompliances  2 }

ctDot1qVlanCurentCompliance MODULE-COMPLIANCE
    STATUS      current
    DESCRIPTION
        "The compliance statement for devices that support
        Cabletron extensions to the dot1qVlanCurrentTable of
        the Q-BRIDGE-MIB."

    MODULE
        GROUP       ctQBridgeVlanCurrentForbidGroup
        DESCRIPTION
           "This group is mandatory for all devices that support a
           mechanism of configuring forbidden egress beyond the
           capabilities provided by dot1qVlanForbiddenEgressPorts."
    ::= { ctQBridgeCompliances  3 }

ctDot1qPortVlanEgressCompliance MODULE-COMPLIANCE
    STATUS      deprecated
    DESCRIPTION
        "******** THIS COMPLIANCE IS DEPRECATED ********

        The compliance statement for devices that support
        reporting of VLAN egress on a per port, per VLAN basis."

    MODULE
        GROUP       ctQBridgePortVlanEgressGroup
        DESCRIPTION
           "This group is mandatory for all devices that support a
           mechanism of configuring egress beyond the
           capabilities provided by Q-BRIDGE-MIB."
    ::= { ctQBridgeCompliances  4 }

ctDot1qTpFdbTableExtCompliance MODULE-COMPLIANCE
    STATUS      current
    DESCRIPTION
        "The compliance statement for devices that support
        extensions to the dot1qTpFdbTable of Q-BRIDGE-MIB."

    MODULE
        GROUP       ctQBridgeTpFdbTableExtGroup
        DESCRIPTION
           "This group is mandatory for all devices that support a
           mechanism of removing learned unicast MAC addresses from the
           transparent filter database."
    ::= { ctQBridgeCompliances  5 }

ctDot1qVlan3 MODULE-COMPLIANCE
    STATUS      current
    DESCRIPTION
        "The compliance statement for devices that support
        Cabletron extensions to Q-BRIDGE-MIB."

    MODULE
        MANDATORY-GROUPS {
            ctQBridgeVlanGroup,
            ctQBridgePortGroup2
        }
        GROUP       ctQBridgePortReplaceTCIGroup
        DESCRIPTION
            "This group is REQUIRED for devices supporting TCI
            replacement."
        GROUP       ctQBridgeVlanGvrpGroup
        DESCRIPTION
            "This group is REQUIRED for devices that support the ability
            to include or exclude individual VLANs from participating in
            GVRP."
    ::= { ctQBridgeCompliances  6 }

ctDot1qPortVlanEgressCompliance2 MODULE-COMPLIANCE
    STATUS      current
    DESCRIPTION
        "The compliance statement for devices that support
        reporting of VLAN egress on a per port, per VLAN basis."

    MODULE
        GROUP       ctQBridgePortVlanEgressGroup2
        DESCRIPTION
           "This group is mandatory for all devices that support a
           mechanism of configuring egress beyond the
           capabilities provided by Q-BRIDGE-MIB."
    ::= { ctQBridgeCompliances  7 }

END
