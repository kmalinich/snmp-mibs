-- *********************************************************************
-- CISCO-UNIFIED-COMPUTING-SW-MIB.my
--
-- MIB representation of the Cisco Unified Computing System
-- SW management information model package
--
-- Created July 2018 by Charles Bullis
--
-- Copyright (c) 2005-2018 Cisco Systems, Inc. All rights reserved.
--
-- *********************************************************************

CISCO-UNIFIED-COMPUTING-SW-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsDpsecForgedTransmit,
    CucsFabricAVlanAssocPrimaryVlanSwitchId,
    CucsFabricAVlanSharing,
    CucsFabricAVlanTransport,
    CucsFabricAVlanType,
    CucsFabricAVsanTransport,
    CucsFabricAVsanType,
    CucsFabricAdminState,
    CucsFabricDefaultZoningState,
    CucsFabricDirection,
    CucsFabricEpVlanVlanType,
    CucsFabricEthEstcPortMode,
    CucsFabricEthPcProtocol,
    CucsFabricExternalEpLocale,
    CucsFabricFcZoneSharingMode,
    CucsFabricFillPattern,
    CucsFabricFlowMonIpv4Keys,
    CucsFabricFlowMonIpv6Keys,
    CucsFabricFlowMonKeyType,
    CucsFabricFlowMonL2Keys,
    CucsFabricFlowMonNonKeys,
    CucsFabricNFExporterVersion,
    CucsFabricNFTransport,
    CucsFabricPIoEpIfType,
    CucsFabricPIoEpOperState,
    CucsFabricPIoEpPortId,
    CucsFabricPIoEpSlotId,
    CucsFabricRecoveryAction,
    CucsFabricTrafficDirection,
    CucsFabricVlanAssocPrimaryVlanState,
    CucsFabricVlanOperState,
    CucsFabricVlanOverlapState,
    CucsFabricVnetEpIfRole,
    CucsFabricVnetEpLocale,
    CucsFabricVnetEpPolicyOwner,
    CucsFabricVsanOperState,
    CucsFabricWarnings,
    CucsFabricZoningState,
    CucsFlowctrlFlowControl,
    CucsFlowctrlPriorityPause,
    CucsFsmCompletion,
    CucsFsmFlags,
    CucsFsmFsmStageStatus,
    CucsFsmLifecycle,
    CucsLicenseState,
    CucsLsFcZoneState,
    CucsNetworkConnectionType,
    CucsNetworkCountStatus,
    CucsNetworkLocale,
    CucsNetworkPortRole,
    CucsNetworkSwitchId,
    CucsNetworkTransport,
    CucsNetworkVnetEpIfType,
    CucsNwctrlAdminState,
    CucsNwctrlLinkFailAction,
    CucsPortEthAdminSpeed,
    CucsPortEthSpeed,
    CucsPortSpeed,
    CucsSwAccessDomainFsmCurrentFsm,
    CucsSwAccessDomainFsmStageName,
    CucsSwAccessDomainFsmTaskItem,
    CucsSwAccessDomainLocale,
    CucsSwAccessDomainType,
    CucsSwAccessEpLocale,
    CucsSwAccessEpTransport,
    CucsSwBorderDomainLocale,
    CucsSwBorderEpLocale,
    CucsSwBorderPcLocale,
    CucsSwBreakoutType,
    CucsSwCIoEpIfType,
    CucsSwCardEnvStatsHistThresholded,
    CucsSwCardEnvStatsThresholded,
    CucsSwCimcId,
    CucsSwConfMode,
    CucsSwConfigStatus,
    CucsSwEnvStatsHistThresholded,
    CucsSwEnvStatsThresholded,
    CucsSwEstcEpLocale,
    CucsSwEthEstcEpTransport,
    CucsSwEthEstcPcTransport,
    CucsSwEthFlowMonSessionTransport,
    CucsSwEthFlowMonSessionType,
    CucsSwEthLanBorderFsmCurrentFsm,
    CucsSwEthLanBorderFsmStageName,
    CucsSwEthLanBorderFsmTaskFlags,
    CucsSwEthLanBorderFsmTaskItem,
    CucsSwEthLanBorderTransport,
    CucsSwEthLanEpTransport,
    CucsSwEthLanEpUdldAdminState,
    CucsSwEthLanEpUdldMode,
    CucsSwEthLanFlowMonExporterTransport,
    CucsSwEthLanFlowMonExporterType,
    CucsSwEthLanFlowMonFsmCurrentFsm,
    CucsSwEthLanFlowMonFsmStageName,
    CucsSwEthLanFlowMonFsmTaskItem,
    CucsSwEthLanFlowMonTransport,
    CucsSwEthLanFlowMonitorTransport,
    CucsSwEthLanFlowMonitorType,
    CucsSwEthLanFlowRecordDefTransport,
    CucsSwEthLanFlowRecordDefType,
    CucsSwEthLanMonTransport,
    CucsSwEthLanPcTransport,
    CucsSwEthMonDestEpTransport,
    CucsSwEthMonFsmCurrentFsm,
    CucsSwEthMonFsmStageName,
    CucsSwEthMonFsmTaskItem,
    CucsSwEthMonSrcEpTransport,
    CucsSwEthMonTransport,
    CucsSwEthMonType,
    CucsSwEthTargetEpAdminState,
    CucsSwEthTargetEpTransport,
    CucsSwEtherPortAggrPortId,
    CucsSwEtherPortPortId,
    CucsSwEtherPortSlotId,
    CucsSwExtUtilityFsmCurrentFsm,
    CucsSwExtUtilityFsmStageName,
    CucsSwExtUtilityFsmTaskItem,
    CucsSwFabricZoneNsAllocStatus,
    CucsSwFabricZoneNsUserZoneAllocStatus,
    CucsSwFcEstcEpTransport,
    CucsSwFcMonDestEpTransport,
    CucsSwFcMonFsmCurrentFsm,
    CucsSwFcMonFsmStageName,
    CucsSwFcMonFsmTaskItem,
    CucsSwFcMonSrcEpTransport,
    CucsSwFcMonTransport,
    CucsSwFcMonType,
    CucsSwFcSanBorderFsmCurrentFsm,
    CucsSwFcSanBorderFsmStageName,
    CucsSwFcSanBorderFsmTaskFlags,
    CucsSwFcSanBorderFsmTaskItem,
    CucsSwFcSanBorderTransport,
    CucsSwFcSanBorderUplinkTrunking,
    CucsSwFcSanEpTransport,
    CucsSwFcSanMonTransport,
    CucsSwFcSanPcTransport,
    CucsSwFcServerZoneGroupLc,
    CucsSwFcUserZoneGroupLc,
    CucsSwFcUserZoneLc,
    CucsSwFcZoneLc,
    CucsSwFcZoneMemberLc,
    CucsSwFcZoneSetLc,
    CucsSwFcoeEstcEpTransport,
    CucsSwFcoeSanEpTransport,
    CucsSwFcoeSanEpUdldAdminState,
    CucsSwFcoeSanEpUdldMode,
    CucsSwFcoeSanPcTransport,
    CucsSwFlowMonitorAdminState,
    CucsSwLanBorderType,
    CucsSwLanEpIfRole,
    CucsSwLanEpType,
    CucsSwLanMonType,
    CucsSwLanPcIfRole,
    CucsSwLanPcType,
    CucsSwMonAdminState,
    CucsSwMonDomainLocale,
    CucsSwMonLifeCycle,
    CucsSwMonSrcEpLocale,
    CucsSwNFConfigStatus,
    CucsSwNetflowExporterProtocol,
    CucsSwNetflowMonSessionProtocol,
    CucsSwNetflowMonitorProtocol,
    CucsSwNetflowRecordDefProtocol,
    CucsSwPIoEpIfType,
    CucsSwPIoEpLc,
    CucsSwPeerStatus,
    CucsSwPhysFsmCurrentFsm,
    CucsSwPhysFsmStageName,
    CucsSwPhysFsmTaskItem,
    CucsSwPortBreakoutPortId,
    CucsSwPortBreakoutSlotId,
    CucsSwPortDiscoverFsmCurrentFsm,
    CucsSwPortDiscoverFsmStageName,
    CucsSwPortDiscoverFsmTaskItem,
    CucsSwSanBorderType,
    CucsSwSanEpIfRole,
    CucsSwSanEpType,
    CucsSwSanMonType,
    CucsSwSanPcIfRole,
    CucsSwSanPcType,
    CucsSwSubGroupAggrPortId,
    CucsSwSubGroupSlotId,
    CucsSwSystemStatsHistThresholded,
    CucsSwSystemStatsThresholded,
    CucsSwTargetEpType,
    CucsSwUlanPurpose,
    CucsSwUtilityDomainFsmCurrentFsm,
    CucsSwUtilityDomainFsmStageName,
    CucsSwUtilityDomainFsmTaskItem,
    CucsSwUtilityDomainLocale,
    CucsSwUtilityDomainType,
    CucsSwVlanCompType,
    CucsSwVlanConfigStatusType,
    CucsSwVlanGroupType,
    CucsSwVlanLc,
    CucsSwVlanLimitStatus,
    CucsSwVlanPortNsAllocStatus
        FROM CISCO-UNIFIED-COMPUTING-TC-MIB;

cucsSwObjects MODULE-IDENTITY
    LAST-UPDATED    "201807260000Z"
    ORGANIZATION    "Cisco Systems Inc."
    CONTACT-INFO
        "Cisco Systems
        Customer Service

        Postal: 170 W Tasman Drive
        San Jose, CA  95134
        USA

        Tel: +1 800 553 -NETS

        E-mail: cs-san@cisco.com, cs-lan-switch-snmp@cisco.com"
    DESCRIPTION
        "MIB representation of the Cisco Unified Computing System
        SW management information model package"
    ::= { ciscoUnifiedComputingMIBObjects 46 }

cucsSwAccessDomainTable OBJECT-TYPE
    SYNTAX           SEQUENCE OF CucsSwAccessDomainEntry
    MAX-ACCESS       not-accessible
    STATUS           current
    DESCRIPTION
        "Cisco UCS sw:AccessDomain managed object table"
    ::= { cucsSwObjects 1 }

cucsSwAccessDomainEntry OBJECT-TYPE
    SYNTAX           CucsSwAccessDomainEntry
    MAX-ACCESS       not-accessible
    STATUS           current
    DESCRIPTION
        "Entry for the cucsSwAccessDomainTable table."
    INDEX { cucsSwAccessDomainInstanceId }
    ::= { cucsSwAccessDomainTable 1 }

CucsSwAccessDomainEntry ::= SEQUENCE {
    cucsSwAccessDomainInstanceId                                     CucsManagedObjectId,
    cucsSwAccessDomainDn                                             CucsManagedObjectDn,
    cucsSwAccessDomainRn                                             SnmpAdminString,
    cucsSwAccessDomainFsmDescr                                       SnmpAdminString,
    cucsSwAccessDomainFsmPrev                                        SnmpAdminString,
    cucsSwAccessDomainFsmProgr                                       Gauge32,
    cucsSwAccessDomainFsmRmtInvErrCode                               Gauge32,
    cucsSwAccessDomainFsmRmtInvErrDescr                              SnmpAdminString,
    cucsSwAccessDomainFsmRmtInvRslt                                  CucsConditionRemoteInvRslt,
    cucsSwAccessDomainFsmStageDescr                                  SnmpAdminString,
    cucsSwAccessDomainFsmStamp                                       DateAndTime,
    cucsSwAccessDomainFsmStatus                                      SnmpAdminString,
    cucsSwAccessDomainFsmTry                                         Gauge32,
    cucsSwAccessDomainLocale                                         CucsSwAccessDomainLocale,
    cucsSwAccessDomainName                                           SnmpAdminString,
    cucsSwAccessDomainSwitchId                                       CucsNetworkSwitchId,
    cucsSwAccessDomainTransport                                      CucsNetworkTransport,
    cucsSwAccessDomainType                                           CucsSwAccessDomainType
}

cucsSwAccessDomainInstanceId OBJECT-TYPE
    SYNTAX       CucsManagedObjectId
    MAX-ACCESS   not-accessible
    STATUS       current
    DESCRIPTION
        "Instance identifier of the managed object."
    ::= { cucsSwAccessDomainEntry 1 }

cucsSwAccessDomainDn OBJECT-TYPE
    SYNTAX       CucsManagedObjectDn
    MAX-ACCESS   read-only
    STATUS       current
    DESCRIPTION
        "Cisco UCS sw:AccessDomain:dn managed object property"
    ::= { cucsSwAccessDomainEntry 2 }

cucsSwAccessDomainRn OBJECT-TYPE
    SYNTAX       SnmpAdminString
    MAX-ACCESS   read-only
    STATUS       current
    DESCRIPTION
        "Cisco UCS sw:AccessDomain:rn managed object property"
    ::= { cucsSwAccessDomainEntry 3 }

cucsSwAccessDomainFsmDescr OBJECT-TYPE
    SYNTAX       SnmpAdminString
    MAX-ACCESS   read-only
    STATUS       current
    DESCRIPTION
        "Cisco UCS sw:AccessDomain:fsmDescr managed object property"
    ::= { cucsSwAccessDomainEntry 4 }

cucsSwAccessDomainFsmPrev OBJECT-TYPE
    SYNTAX       SnmpAdminString
    MAX-ACCESS   read-only
    STATUS       current
    DESCRIPTION
        "Cisco UCS sw:AccessDomain:fsmPrev managed object property"
    ::= { cucsSwAccessDomainEntry 5 }

cucsSwAccessDomainFsmProgr OBJECT-TYPE
    SYNTAX       Gauge32
    MAX-ACCESS   read-only
    STATUS       current
    DESCRIPTION
        "Cisco UCS sw:AccessDomain:fsmProgr managed object property"
    ::= { cucsSwAccessDomainEntry 6 }

cucsSwAccessDomainFsmRmtInvErrCode OBJECT-TYPE
    SYNTAX       Gauge32
    MAX-ACCESS   read-only
    STATUS       current
    DESCRIPTION
        "Cisco UCS sw:AccessDomain:fsmRmtInvErrCode managed
        object property"
    ::= { cucsSwAccessDomainEntry 7 }

cucsSwAccessDomainFsmRmtInvErrDescr OBJECT-TYPE
    SYNTAX       SnmpAdminString
    MAX-ACCESS   read-only
    STATUS       current
    DESCRIPTION
        "Cisco UCS sw:AccessDomain:fsmRmtInvErrDescr managed
        object property"
    ::= { cucsSwAccessDomainEntry 8 }

cucsSwAccessDomainFsmRmtInvRslt OBJECT-TYPE
    SYNTAX       CucsConditionRemoteInvRslt
    MAX-ACCESS   read-only
    STATUS       current
    DESCRIPTION
        "Cisco UCS sw:AccessDomain:fsmRmtInvRslt managed object property"
    ::= { cucsSwAccessDomainEntry 9 }

cucsSwAccessDomainFsmStageDescr OBJECT-TYPE
    SYNTAX       SnmpAdminString
    MAX-ACCESS   read-only
    STATUS       current
    DESCRIPTION
        "Cisco UCS sw:AccessDomain:fsmStageDescr managed object property"
    ::= { cucsSwAccessDomainEntry 10 }

cucsSwAccessDomainFsmStamp OBJECT-TYPE
    SYNTAX       DateAndTime
    MAX-ACCESS   read-only
    STATUS       current
    DESCRIPTION
        "Cisco UCS sw:AccessDomain:fsmStamp managed object property"
    ::= { cucsSwAccessDomainEntry 11 }

cucsSwAccessDomainFsmStatus OBJECT-TYPE
    SYNTAX       SnmpAdminString
    MAX-ACCESS   read-only
    STATUS       current
    DESCRIPTION
        "Cisco UCS sw:AccessDomain:fsmStatus managed object property"
    ::= { cucsSwAccessDomainEntry 12 }

cucsSwAccessDomainFsmTry OBJECT-TYPE
    SYNTAX       Gauge32
    MAX-ACCESS   read-only
    STATUS       current
    DESCRIPTION
        "Cisco UCS sw:AccessDomain:fsmTry managed object property"
    ::= { cucsSwAccessDomainEntry 13 }

cucsSwAccessDomainLocale OBJECT-TYPE
    SYNTAX       CucsSwAccessDomainLocale
    MAX-ACCESS   read-only
    STATUS       current
    DESCRIPTION
        "Cisco UCS sw:AccessDomain:locale managed object property"
    ::= { cucsSwAccessDomainEntry 14 }

cucsSwAccessDomainName OBJECT-TYPE
    SYNTAX       SnmpAdminString
    MAX-ACCESS   read-only
    STATUS       current
    DESCRIPTION
        "Cisco UCS sw:AccessDomain:name managed object property"
    ::= { cucsSwAccessDomainEntry 15 }

cucsSwAccessDomainSwitchId OBJECT-TYPE
    SYNTAX       CucsNetworkSwitchId
    MAX-ACCESS   read-only
    STATUS       current
    DESCRIPTION
        "Cisco UCS sw:AccessDomain:switchId managed object property"
    ::= { cucsSwAccessDomainEntry 16 }

cucsSwAccessDomainTransport OBJECT-TYPE
    SYNTAX       CucsNetworkTransport
    MAX-ACCESS   read-only
    STATUS       current
    DESCRIPTION
        "Cisco UCS sw:AccessDomain:transport managed object property"
    ::= { cucsSwAccessDomainEntry 17 }

cucsSwAccessDomainType OBJECT-TYPE
    SYNTAX       CucsSwAccessDomainType
    MAX-ACCESS   read-only
    STATUS       current
    DESCRIPTION
        "Cisco UCS sw:AccessDomain:type managed object property"
    ::= { cucsSwAccessDomainEntry 18 }

cucsSwAccessDomainFsmTable OBJECT-TYPE
    SYNTAX           SEQUENCE OF CucsSwAccessDomainFsmEntry
    MAX-ACCESS       not-accessible
    STATUS           current
    DESCRIPTION
        "Cisco UCS sw:AccessDomainFsm managed object table"
    ::= { cucsSwObjects 42 }

cucsSwAccessDomainFsmEntry OBJECT-TYPE
    SYNTAX           CucsSwAccessDomainFsmEntry
    MAX-ACCESS       not-accessible
    STATUS           current
    DESCRIPTION
        "Entry for the cucsSwAccessDomainFsmTable table."
    INDEX { cucsSwAccessDomainFsmInstanceId }
    ::= { cucsSwAccessDomainFsmTable 1 }

CucsSwAccessDomainFsmEntry ::= SEQUENCE {
    cucsSwAccessDomainFsmInstanceId                                  CucsManagedObjectId,
    cucsSwAccessDomainFsmDn                                          CucsManagedObjectDn,
    cucsSwAccessDomainFsmRn                                          SnmpAdminString,
    cucsSwAccessDomainFsmCompletionTime                              DateAndTime,
    cucsSwAccessDomainFsmCurrentFsm                                  CucsSwAccessDomainFsmCurrentFsm,
    cucsSwAccessDomainFsmDescrData                                   SnmpAdminString,
    cucsSwAccessDomainFsmFsmStatus                                   CucsFsmFsmStageStatus,
    cucsSwAccessDomainFsmProgress                                    Gauge32,
    cucsSwAccessDomainFsmRmtErrCode                                  Gauge32,
    cucsSwAccessDomainFsmRmtErrDescr                                 SnmpAdminString,
    cucsSwAccessDomainFsmRmtRslt                                     CucsConditionRemoteInvRslt
}

cucsSwAccessDomainFsmInstanceId OBJECT-TYPE
    SYNTAX       CucsManagedObjectId
    MAX-ACCESS   not-accessible
    STATUS       current
    DESCRIPTION
        "Instance identifier of the managed object."
    ::= { cucsSwAccessDomainFsmEntry 1 }

cucsSwAccessDomainFsmDn OBJECT-TYPE
    SYNTAX       CucsManagedObjectDn
    MAX-ACCESS   read-only
    STATUS       current
    DESCRIPTION
        "Cisco UCS sw:AccessDomainFsm:dn managed object property"
    ::= { cucsSwAccessDomainFsmEntry 2 }

cucsSwAccessDomainFsmRn OBJECT-TYPE
    SYNTAX       SnmpAdminString
    MAX-ACCESS   read-only
    STATUS       current
    DESCRIPTION
        "Cisco UCS sw:AccessDomainFsm:rn managed object property"
    ::= { cucsSwAccessDomainFsmEntry 3 }

cucsSwAccessDomainFsmCompletionTime OBJECT-TYPE
    SYNTAX       DateAndTime
    MAX-ACCESS   read-only
    STATUS       current
    DESCRIPTION
        "Cisco UCS sw:AccessDomainFsm:completionTime managed
        object property"
    ::= { cucsSwAccessDomainFsmEntry 4 }

cucsSwAccessDomainFsmCurrentFsm OBJECT-TYPE
    SYNTAX       CucsSwAccessDomainFsmCurrentFsm
    MAX-ACCESS   read-only
    STATUS       current
    DESCRIPTION
        "Cisco UCS sw:AccessDomainFsm:currentFsm managed object property"
    ::= { cucsSwAccessDomainFsmEntry 5 }

cucsSwAccessDomainFsmDescrData OBJECT-TYPE
    SYNTAX       SnmpAdminString
    MAX-ACCESS   read-only
    STATUS       current
    DESCRIPTION
        "Cisco UCS sw:AccessDomainFsm:descr managed object property"
    ::= { cucsSwAccessDomainFsmEntry 6 }

cucsSwAccessDomainFsmFsmStatus OBJECT-TYPE
    SYNTAX       CucsFsmFsmStageStatus
    MAX-ACCESS   read-only
    STATUS       current
    DESCRIPTION
        "Cisco UCS sw:AccessDomainFsm:fsmStatus managed object property"
    ::= { cucsSwAccessDomainFsmEntry 7 }

cucsSwAccessDomainFsmProgress OBJECT-TYPE
    SYNTAX       Gauge32
    MAX-ACCESS   read-only
    STATUS       current
    DESCRIPTION
        "Cisco UCS sw:AccessDomainFsm:progress managed object property"
    ::= { cucsSwAccessDomainFsmEntry 8 }

cucsSwAccessDomainFsmRmtErrCode OBJECT-TYPE
    SYNTAX       Gauge32
    MAX-ACCESS   read-only
    STATUS       current
    DESCRIPTION
        "Cisco UCS sw:AccessDomainFsm:rmtErrCode managed object property"
    ::= { cucsSwAccessDomainFsmEntry 9 }

cucsSwAccessDomainFsmRmtErrDescr OBJECT-TYPE
    SYNTAX       SnmpAdminString
    MAX-ACCESS   read-only
    STATUS       current
    DESCRIPTION
        "Cisco UCS sw:AccessDomainFsm:rmtErrDescr managed object property"
    ::= { cucsSwAccessDomainFsmEntry 10 }

cucsSwAccessDomainFsmRmtRslt OBJECT-TYPE
    SYNTAX       CucsConditionRemoteInvRslt
    MAX-ACCESS   read-only
    STATUS       current
    DESCRIPTION
        "Cisco UCS sw:AccessDomainFsm:rmtRslt managed object property"
    ::= { cucsSwAccessDomainFsmEntry 11 }

cucsSwAccessDomainFsmStageTable OBJECT-TYPE
    SYNTAX           SEQUENCE OF CucsSwAccessDomainFsmStageEntry
    MAX-ACCESS       not-accessible
    STATUS           current
    DESCRIPTION
        "Cisco UCS sw:AccessDomainFsmStage managed object table"
    ::= { cucsSwObjects 43 }

cucsSwAccessDomainFsmStageEntry OBJECT-TYPE
    SYNTAX           CucsSwAccessDomainFsmStageEntry
    MAX-ACCESS       not-accessible
    STATUS           current
    DESCRIPTION
        "Entry for the cucsSwAccessDomainFsmStageTable table."
    INDEX { cucsSwAccessDomainFsmStageInstanceId }
    ::= { cucsSwAccessDomainFsmStageTable 1 }

CucsSwAccessDomainFsmStageEntry ::= SEQUENCE {
    cucsSwAccessDomainFsmStageInstanceId                             CucsManagedObjectId,
    cucsSwAccessDomainFsmStageDn                                     CucsManagedObjectDn,
    cucsSwAccessDomainFsmStageRn                                     SnmpAdminString,
    cucsSwAccessDomainFsmStageDescrData                              SnmpAdminString,
    cucsSwAccessDomainFsmStageLastUpdateTime                         DateAndTime,
    cucsSwAccessDomainFsmStageName                                   CucsSwAccessDomainFsmStageName,
    cucsSwAccessDomainFsmStageOrder                                  Gauge32,
    cucsSwAccessDomainFsmStageRetry                                  Gauge32,
    cucsSwAccessDomainFsmStageStageStatus                            CucsFsmFsmStageStatus
}

cucsSwAccessDomainFsmStageInstanceId OBJECT-TYPE
    SYNTAX       CucsManagedObjectId
    MAX-ACCESS   not-accessible
    STATUS       current
    DESCRIPTION
        "Instance identifier of the managed object."
    ::= { cucsSwAccessDomainFsmStageEntry 1 }

cucsSwAccessDomainFsmStageDn OBJECT-TYPE
    SYNTAX       CucsManagedObjectDn
    MAX-ACCESS   read-only
    STATUS       current
    DESCRIPTION
        "Cisco UCS sw:AccessDomainFsmStage:dn managed object property"
    ::= { cucsSwAccessDomainFsmStageEntry 2 }

cucsSwAccessDomainFsmStageRn OBJECT-TYPE
    SYNTAX       SnmpAdminString
    MAX-ACCESS   read-only
    STATUS       current
    DESCRIPTION
        "Cisco UCS sw:AccessDomainFsmStage:rn managed object property"
    ::= { cucsSwAccessDomainFsmStageEntry 3 }

cucsSwAccessDomainFsmStageDescrData OBJECT-TYPE
    SYNTAX       SnmpAdminString
    MAX-ACCESS   read-only
    STATUS       current
    DESCRIPTION
        "Cisco UCS sw:AccessDomainFsmStage:descr managed object property"
    ::= { cucsSwAccessDomainFsmStageEntry 4 }

cucsSwAccessDomainFsmStageLastUpdateTime OBJECT-TYPE
    SYNTAX       DateAndTime
    MAX-ACCESS   read-only
    STATUS       current
    DESCRIPTION
        "Cisco UCS sw:AccessDomainFsmStage:lastUpdateTime
        managed object property"
    ::= { cucsSwAccessDomainFsmStageEntry 5 }

cucsSwAccessDomainFsmStageName OBJECT-TYPE
    SYNTAX       CucsSwAccessDomainFsmStageName
    MAX-ACCESS   read-only
    STATUS       current
    DESCRIPTION
        "Cisco UCS sw:AccessDomainFsmStage:name managed object property"
    ::= { cucsSwAccessDomainFsmStageEntry 6 }

cucsSwAccessDomainFsmStageOrder OBJECT-TYPE
    SYNTAX       Gauge32
    MAX-ACCESS   read-only
    STATUS       current
    DESCRIPTION
        "Cisco UCS sw:AccessDomainFsmStage:order managed object property"
    ::= { cucsSwAccessDomainFsmStageEntry 7 }

cucsSwAccessDomainFsmStageRetry OBJECT-TYPE
    SYNTAX       Gauge32
    MAX-ACCESS   read-only
    STATUS       current
    DESCRIPTION
        "Cisco UCS sw:AccessDomainFsmStage:retry managed object property"
    ::= { cucsSwAccessDomainFsmStageEntry 8 }

cucsSwAccessDomainFsmStageStageStatus OBJECT-TYPE
    SYNTAX       CucsFsmFsmStageStatus
    MAX-ACCESS   read-only
    STATUS       current
    DESCRIPTION
        "Cisco UCS sw:AccessDomainFsmStage:stageStatus
        managed object property"
    ::= { cucsSwAccessDomainFsmStageEntry 9 }

cucsSwAccessDomainFsmTaskTable OBJECT-TYPE
    SYNTAX           SEQUENCE OF CucsSwAccessDomainFsmTaskEntry
    MAX-ACCESS       not-accessible
    STATUS           current
    DESCRIPTION
        "Cisco UCS sw:AccessDomainFsmTask managed object table"
    ::= { cucsSwObjects 2 }

cucsSwAccessDomainFsmTaskEntry OBJECT-TYPE
    SYNTAX           CucsSwAccessDomainFsmTaskEntry
    MAX-ACCESS       not-accessible
    STATUS           current
    DESCRIPTION
        "Entry for the cucsSwAccessDomainFsmTaskTable table."
    INDEX { cucsSwAccessDomainFsmTaskInstanceId }
    ::= { cucsSwAccessDomainFsmTaskTable 1 }

CucsSwAccessDomainFsmTaskEntry ::= SEQUENCE {
    cucsSwAccessDomainFsmTaskInstanceId                              CucsManagedObjectId,
    cucsSwAccessDomainFsmTaskDn                                      CucsManagedObjectDn,
    cucsSwAccessDomainFsmTaskRn                                      SnmpAdminString,
    cucsSwAccessDomainFsmTaskCompletion                              CucsFsmCompletion,
    cucsSwAccessDomainFsmTaskFlags                                   CucsFsmFlags,
    cucsSwAccessDomainFsmTaskItem                                    CucsSwAccessDomainFsmTaskItem,
    cucsSwAccessDomainFsmTaskSeqId                                   Gauge32
}

cucsSwAccessDomainFsmTaskInstanceId OBJECT-TYPE
    SYNTAX       CucsManagedObjectId
    MAX-ACCESS   not-accessible
    STATUS       current
    DESCRIPTION
        "Instance identifier of the managed object."
    ::= { cucsSwAccessDomainFsmTaskEntry 1 }

cucsSwAccessDomainFsmTaskDn OBJECT-TYPE
    SYNTAX       CucsManagedObjectDn
    MAX-ACCESS   read-only
    STATUS       current
    DESCRIPTION
        "Cisco UCS sw:AccessDomainFsmTask:dn managed object property"
    ::= { cucsSwAccessDomainFsmTaskEntry 2 }

cucsSwAccessDomainFsmTaskRn OBJECT-TYPE
    SYNTAX       SnmpAdminString
    MAX-ACCESS   read-only
    STATUS       current
    DESCRIPTION
        "Cisco UCS sw:AccessDomainFsmTask:rn managed object property"
    ::= { cucsSwAccessDomainFsmTaskEntry 3 }

cucsSwAccessDomainFsmTaskCompletion OBJECT-TYPE
    SYNTAX       CucsFsmCompletion
    MAX-ACCESS   read-only
    STATUS       current
    DESCRIPTION
        "Cisco UCS sw:AccessDomainFsmTask:completion managed
        object property"
    ::= { cucsSwAccessDomainFsmTaskEntry 4 }

cucsSwAccessDomainFsmTaskFlags OBJECT-TYPE
    SYNTAX       CucsFsmFlags
    MAX-ACCESS   read-only
    STATUS       current
    DESCRIPTION
        "Cisco UCS sw:AccessDomainFsmTask:flags managed object property"
    ::= { cucsSwAccessDomainFsmTaskEntry 5 }

cucsSwAccessDomainFsmTaskItem OBJECT-TYPE
    SYNTAX       CucsSwAccessDomainFsmTaskItem
    MAX-ACCESS   read-only
    STATUS       current
    DESCRIPTION
        "Cisco UCS sw:AccessDomainFsmTask:item managed object property"
    ::= { cucsSwAccessDomainFsmTaskEntry 6 }

cucsSwAccessDomainFsmTaskSeqId OBJECT-TYPE
    SYNTAX       Gauge32
    MAX-ACCESS   read-only
    STATUS       current
    DESCRIPTION
        "Cisco UCS sw:AccessDomainFsmTask:seqId managed object property"
    ::= { cucsSwAccessDomainFsmTaskEntry 7 }

cucsSwAccessEpTable OBJECT-TYPE
    SYNTAX           SEQUENCE OF CucsSwAccessEpEntry
    MAX-ACCESS       not-accessible
    STATUS           current
    DESCRIPTION
        "Cisco UCS sw:AccessEp managed object table"
    ::= { cucsSwObjects 3 }

cucsSwAccessEpEntry OBJECT-TYPE
    SYNTAX           CucsSwAccessEpEntry
    MAX-ACCESS       not-accessible
    STATUS           current
    DESCRIPTION
        "Entry for the cucsSwAccessEpTable table."
    INDEX { cucsSwAccessEpInstanceId }
    ::= { cucsSwAccessEpTable 1 }

CucsSwAccessEpEntry ::= SEQUENCE {
    cucsSwAccessEpInstanceId                                         CucsManagedObjectId,
    cucsSwAccessEpDn                                                 CucsManagedObjectDn,
    cucsSwAccessEpRn                                                 SnmpAdminString,
    cucsSwAccessEpAdminState                                         CucsFabricAdminState,
    cucsSwAccessEpChassisId                                          Gauge32,
    cucsSwAccessEpEpDn                                               SnmpAdminString,
    cucsSwAccessEpIfRole                                             CucsNetworkPortRole,
    cucsSwAccessEpIfType                                             CucsSwPIoEpIfType,
    cucsSwAccessEpLocale                                             CucsSwAccessEpLocale,
    cucsSwAccessEpName                                               SnmpAdminString,
    cucsSwAccessEpPeerDn                                             SnmpAdminString,
    cucsSwAccessEpPeerPortId                                         Gauge32,
    cucsSwAccessEpPeerSlotId                                         Gauge32,
    cucsSwAccessEpPortId                                             Gauge32,
    cucsSwAccessEpSlotId                                             Gauge32,
    cucsSwAccessEpSwitchId                                           CucsNetworkSwitchId,
    cucsSwAccessEpTransport                                          CucsSwAccessEpTransport,
    cucsSwAccessEpType                                               CucsNetworkConnectionType,
    cucsSwAccessEpEncap                                              Gauge32,
    cucsSwAccessEpNsSize                                             Gauge32,
    cucsSwAccessEpPeerChassisId                                      Gauge32,
    cucsSwAccessEpLc                                                 CucsSwPIoEpLc,
    cucsSwAccessEpAggrPortId                                         Gauge32,
    cucsSwAccessEpPeerAggrPortId                                     Gauge32,
    cucsSwAccessEpPriorityFlowCtrl                                   CucsFlowctrlPriorityPause,
    cucsSwAccessEpRecvFlowCtrl                                       CucsFlowctrlFlowControl,
    cucsSwAccessEpSendFlowCtrl                                       CucsFlowctrlFlowControl
}

cucsSwAccessEpInstanceId OBJECT-TYPE
    SYNTAX       CucsManagedObjectId
    MAX-ACCESS   not-accessible
    STATUS       current
    DESCRIPTION
        "Instance identifier of the managed object."
    ::= { cucsSwAccessEpEntry 1 }

cucsSwAccessEpDn OBJECT-TYPE
    SYNTAX       CucsManagedObjectDn
    MAX-ACCESS   read-only
    STATUS       current
    DESCRIPTION
        "Cisco UCS sw:AccessEp:dn managed object property"
    ::= { cucsSwAccessEpEntry 2 }

cucsSwAccessEpRn OBJECT-TYPE
    SYNTAX       SnmpAdminString
    MAX-ACCESS   read-only
    STATUS       current
    DESCRIPTION
        "Cisco UCS sw:AccessEp:rn managed object property"
    ::= { cucsSwAccessEpEntry 3 }

cucsSwAccessEpAdminState OBJECT-TYPE
    SYNTAX       CucsFabricAdminState
    MAX-ACCESS   read-only
    STATUS       current
    DESCRIPTION
        "Cisco UCS sw:AccessEp:adminState managed object property"
    ::= { cucsSwAccessEpEntry 4 }

cucsSwAccessEpChassisId OBJECT-TYPE
    SYNTAX       Gauge32
    MAX-ACCESS   read-only
    STATUS       current
    DESCRIPTION
        "Cisco UCS sw:AccessEp:chassisId managed object property"
    ::= { cucsSwAccessEpEntry 5 }

cucsSwAccessEpEpDn OBJECT-TYPE
    SYNTAX       SnmpAdminString
    MAX-ACCESS   read-only
    STATUS       current
    DESCRIPTION
        "Cisco UCS sw:AccessEp:epDn managed object property"
    ::= { cucsSwAccessEpEntry 6 }

cucsSwAccessEpIfRole OBJECT-TYPE
    SYNTAX       CucsNetworkPortRole
    MAX-ACCESS   read-only
    STATUS       current
    DESCRIPTION
        "Cisco UCS sw:AccessEp:ifRole managed object property"
    ::= { cucsSwAccessEpEntry 7 }

cucsSwAccessEpIfType OBJECT-TYPE
    SYNTAX       CucsSwPIoEpIfType
    MAX-ACCESS   read-only
    STATUS       current
    DESCRIPTION
        "Cisco UCS sw:AccessEp:ifType managed object property"
    ::= { cucsSwAccessEpEntry 8 }

cucsSwAccessEpLocale OBJECT-TYPE
    SYNTAX       CucsSwAccessEpLocale
    MAX-ACCESS   read-only
    STATUS       current
    DESCRIPTION
        "Cisco UCS sw:AccessEp:locale managed object property"
    ::= { cucsSwAccessEpEntry 9 }

cucsSwAccessEpName OBJECT-TYPE
    SYNTAX       SnmpAdminString
    MAX-ACCESS   read-only
    STATUS       current
    DESCRIPTION
        "Cisco UCS sw:AccessEp:name managed object property"
    ::= { cucsSwAccessEpEntry 10 }

cucsSwAccessEpPeerDn OBJECT-TYPE
    SYNTAX       SnmpAdminString
    MAX-ACCESS   read-only
    STATUS       current
    DESCRIPTION
        "Cisco UCS sw:AccessEp:peerDn managed object property"
    ::= { cucsSwAccessEpEntry 11 }

cucsSwAccessEpPeerPortId OBJECT-TYPE
    SYNTAX       Gauge32
    MAX-ACCESS   read-only
    STATUS       current
    DESCRIPTION
        "Cisco UCS sw:AccessEp:peerPortId managed object property"
    ::= { cucsSwAccessEpEntry 12 }

cucsSwAccessEpPeerSlotId OBJECT-TYPE
    SYNTAX       Gauge32
    MAX-ACCESS   read-only
    STATUS       current
    DESCRIPTION
        "Cisco UCS sw:AccessEp:peerSlotId managed object property"
    ::= { cucsSwAccessEpEntry 13 }

cucsSwAccessEpPortId OBJECT-TYPE
    SYNTAX       Gauge32
    MAX-ACCESS   read-only
    STATUS       current
    DESCRIPTION
        "Cisco UCS sw:AccessEp:portId managed object property"
    ::= { cucsSwAccessEpEntry 14 }

cucsSwAccessEpSlotId OBJECT-TYPE
    SYNTAX       Gauge32
    MAX-ACCESS   read-only
    STATUS       current
    DESCRIPTION
        "Cisco UCS sw:AccessEp:slotId managed object property"
    ::= { cucsSwAccessEpEntry 15 }

cucsSwAccessEpSwitchId OBJECT-TYPE
    SYNTAX       CucsNetworkSwitchId
    MAX-ACCESS   read-only
    STATUS       current
    DESCRIPTION
        "Cisco UCS sw:AccessEp:switchId managed object property"
    ::= { cucsSwAccessEpEntry 16 }

cucsSwAccessEpTransport OBJECT-TYPE
    SYNTAX       CucsSwAccessEpTransport
    MAX-ACCESS   read-only
    STATUS       current
    DESCRIPTION
        "Cisco UCS sw:AccessEp:transport managed object property"
    ::= { cucsSwAccessEpEntry 17 }

cucsSwAccessEpType OBJECT-TYPE
    SYNTAX       CucsNetworkConnectionType
    MAX-ACCESS   read-only
    STATUS       current
    DESCRIPTION
        "Cisco UCS sw:AccessEp:type managed object property"
    ::= { cucsSwAccessEpEntry 18 }

cucsSwAccessEpEncap OBJECT-TYPE
    SYNTAX       Gauge32
    MAX-ACCESS   read-only
    STATUS       current
    DESCRIPTION
        "Cisco UCS sw:AccessEp:encap managed object property"
    ::= { cucsSwAccessEpEntry 19 }

cucsSwAccessEpNsSize OBJECT-TYPE
    SYNTAX       Gauge32
    MAX-ACCESS   read-only
    STATUS       current
    DESCRIPTION
        "Cisco UCS sw:AccessEp:nsSize managed object property"
    ::= { cucsSwAccessEpEntry 20 }

cucsSwAccessEpPeerChassisId OBJECT-TYPE
    SYNTAX       Gauge32
    MAX-ACCESS   read-only
    STATUS       current
    DESCRIPTION
        "Cisco UCS sw:AccessEp:peerChassisId managed object property"
    ::= { cucsSwAccessEpEntry 21 }

cucsSwAccessEpLc OBJECT-TYPE
    SYNTAX       CucsSwPIoEpLc
    MAX-ACCESS   read-only
    STATUS       current
    DESCRIPTION
        "Cisco UCS sw:AccessEp:lc managed object property"
    ::= { cucsSwAccessEpEntry 22 }

cucsSwAccessEpAggrPortId OBJECT-TYPE
    SYNTAX       Gauge32
    MAX-ACCESS   read-only
    STATUS       current
    DESCRIPTION
        "Cisco UCS sw:AccessEp:aggrPortId managed object property"
    ::= { cucsSwAccessEpEntry 23 }

cucsSwAccessEpPeerAggrPortId OBJECT-TYPE
    SYNTAX       Gauge32
    MAX-ACCESS   read-only
    STATUS       current
    DESCRIPTION
        "Cisco UCS sw:AccessEp:peerAggrPortId managed object property"
    ::= { cucsSwAccessEpEntry 24 }

cucsSwAccessEpPriorityFlowCtrl OBJECT-TYPE
    SYNTAX       CucsFlowctrlPriorityPause
    MAX-ACCESS   read-only
    STATUS       current
    DESCRIPTION
        "Cisco UCS sw:AccessEp:priorityFlowCtrl managed object property"
    ::= { cucsSwAccessEpEntry 26 }

cucsSwAccessEpRecvFlowCtrl OBJECT-TYPE
    SYNTAX       CucsFlowctrlFlowControl
    MAX-ACCESS   read-only
    STATUS       current
    DESCRIPTION
        "Cisco UCS sw:AccessEp:recvFlowCtrl managed object property"
    ::= { cucsSwAccessEpEntry 27 }

cucsSwAccessEpSendFlowCtrl OBJECT-TYPE
    SYNTAX       CucsFlowctrlFlowControl
    MAX-ACCESS   read-only
    STATUS       current
    DESCRIPTION
        "Cisco UCS sw:AccessEp:sendFlowCtrl managed object property"
    ::= { cucsSwAccessEpEntry 28 }

cucsSwCardEnvStatsTable OBJECT-TYPE
    SYNTAX           SEQUENCE OF CucsSwCardEnvStatsEntry
    MAX-ACCESS       not-accessible
    STATUS           current
    DESCRIPTION
        "Cisco UCS sw:CardEnvStats managed object table"
    ::= { cucsSwObjects 44 }

cucsSwCardEnvStatsEntry OBJECT-TYPE
    SYNTAX           CucsSwCardEnvStatsEntry
    MAX-ACCESS       not-accessible
    STATUS           current
    DESCRIPTION
        "Entry for the cucsSwCardEnvStatsTable table."
    INDEX { cucsSwCardEnvStatsInstanceId }
    ::= { cucsSwCardEnvStatsTable 1 }

CucsSwCardEnvStatsEntry ::= SEQUENCE {
    cucsSwCardEnvStatsInstanceId                                     CucsManagedObjectId,
    cucsSwCardEnvStatsDn                                             CucsManagedObjectDn,
    cucsSwCardEnvStatsRn                                             SnmpAdminString,
    cucsSwCardEnvStatsSlotOutlet1                                    INTEGER,
    cucsSwCardEnvStatsSlotOutlet1Avg                                 INTEGER,
    cucsSwCardEnvStatsSlotOutlet1Max                                 INTEGER,
    cucsSwCardEnvStatsSlotOutlet1Min                                 INTEGER,
    cucsSwCardEnvStatsSlotOutlet2                                    INTEGER,
    cucsSwCardEnvStatsSlotOutlet2Avg                                 INTEGER,
    cucsSwCardEnvStatsSlotOutlet2Max                                 INTEGER,
    cucsSwCardEnvStatsSlotOutlet2Min                                 INTEGER,
    cucsSwCardEnvStatsSlotOutlet3                                    INTEGER,
    cucsSwCardEnvStatsSlotOutlet3Avg                                 INTEGER,
    cucsSwCardEnvStatsSlotOutlet3Max                                 INTEGER,
    cucsSwCardEnvStatsSlotOutlet3Min                                 INTEGER,
    cucsSwCardEnvStatsIntervals                                      Gauge32,
    cucsSwCardEnvStatsSuspect                                        TruthValue,
    cucsSwCardEnvStatsThresholded                                    CucsSwCardEnvStatsThresholded,
    cucsSwCardEnvStatsTimeCollected                                  DateAndTime,
    cucsSwCardEnvStatsUpdate                                         Gauge32
}

cucsSwCardEnvStatsInstanceId OBJECT-TYPE
    SYNTAX       CucsManagedObjectId
    MAX-ACCESS   not-accessible
    STATUS       current
    DESCRIPTION
        "Instance identifier of the managed object."
    ::= { cucsSwCardEnvStatsEntry 1 }

cucsSwCardEnvStatsDn OBJECT-TYPE
    SYNTAX       CucsManagedObjectDn
    MAX-ACCESS   read-only
    STATUS       current
    DESCRIPTION
        "Cisco UCS sw:CardEnvStats:dn managed object property"
    ::= { cucsSwCardEnvStatsEntry 2 }

cucsSwCardEnvStatsRn OBJECT-TYPE
    SYNTAX       SnmpAdminString
    MAX-ACCESS   read-only
    STATUS       current
    DESCRIPTION
        "Cisco UCS sw:CardEnvStats:rn managed object property"
    ::= { cucsSwCardEnvStatsEntry 3 }

cucsSwCardEnvStatsSlotOutlet1 OBJECT-TYPE
    SYNTAX       INTEGER
    MAX-ACCESS   read-only
    STATUS       current
    DESCRIPTION
        "Cisco UCS sw:CardEnvStats:SlotOutlet1 managed object property"
    ::= { cucsSwCardEnvStatsEntry 4 }

cucsSwCardEnvStatsSlotOutlet1Avg OBJECT-TYPE
    SYNTAX       INTEGER
    MAX-ACCESS   read-only
    STATUS       current
    DESCRIPTION
        "Cisco UCS sw:CardEnvStats:SlotOutlet1Avg managed object property"
    ::= { cucsSwCardEnvStatsEntry 5 }

cucsSwCardEnvStatsSlotOutlet1Max OBJECT-TYPE
    SYNTAX       INTEGER
    MAX-ACCESS   read-only
    STATUS       current
    DESCRIPTION
        "Cisco UCS sw:CardEnvStats:SlotOutlet1Max managed object property"
    ::= { cucsSwCardEnvStatsEntry 6 }

cucsSwCardEnvStatsSlotOutlet1Min OBJECT-TYPE
    SYNTAX       INTEGER
    MAX-ACCESS   read-only
    STATUS       current
    DESCRIPTION
        "Cisco UCS sw:CardEnvStats:SlotOutlet1Min managed object property"
    ::= { cucsSwCardEnvStatsEntry 7 }

cucsSwCardEnvStatsSlotOutlet2 OBJECT-TYPE
    SYNTAX       INTEGER
    MAX-ACCESS   read-only
    STATUS       current
    DESCRIPTION
        "Cisco UCS sw:CardEnvStats:SlotOutlet2 managed object property"
    ::= { cucsSwCardEnvStatsEntry 8 }

cucsSwCardEnvStatsSlotOutlet2Avg OBJECT-TYPE
    SYNTAX       INTEGER
    MAX-ACCESS   read-only
    STATUS       current
    DESCRIPTION
        "Cisco UCS sw:CardEnvStats:SlotOutlet2Avg managed object property"
    ::= { cucsSwCardEnvStatsEntry 9 }

cucsSwCardEnvStatsSlotOutlet2Max OBJECT-TYPE
    SYNTAX       INTEGER
    MAX-ACCESS   read-only
    STATUS       current
    DESCRIPTION
        "Cisco UCS sw:CardEnvStats:SlotOutlet2Max managed object property"
    ::= { cucsSwCardEnvStatsEntry 10 }

cucsSwCardEnvStatsSlotOutlet2Min OBJECT-TYPE
    SYNTAX       INTEGER
    MAX-ACCESS   read-only
    STATUS       current
    DESCRIPTION
        "Cisco UCS sw:CardEnvStats:SlotOutlet2Min managed object property"
    ::= { cucsSwCardEnvStatsEntry 11 }

cucsSwCardEnvStatsSlotOutlet3 OBJECT-TYPE
    SYNTAX       INTEGER
    MAX-ACCESS   read-only
    STATUS       current
    DESCRIPTION
        "Cisco UCS sw:CardEnvStats:SlotOutlet3 managed object property"
    ::= { cucsSwCardEnvStatsEntry 12 }

cucsSwCardEnvStatsSlotOutlet3Avg OBJECT-TYPE
    SYNTAX       INTEGER
    MAX-ACCESS   read-only
    STATUS       current
    DESCRIPTION
        "Cisco UCS sw:CardEnvStats:SlotOutlet3Avg managed object property"
    ::= { cucsSwCardEnvStatsEntry 13 }

cucsSwCardEnvStatsSlotOutlet3Max OBJECT-TYPE
    SYNTAX       INTEGER
    MAX-ACCESS   read-only
    STATUS       current
    DESCRIPTION
        "Cisco UCS sw:CardEnvStats:SlotOutlet3Max managed object property"
    ::= { cucsSwCardEnvStatsEntry 14 }

cucsSwCardEnvStatsSlotOutlet3Min OBJECT-TYPE
    SYNTAX       INTEGER
    MAX-ACCESS   read-only
    STATUS       current
    DESCRIPTION
        "Cisco UCS sw:CardEnvStats:SlotOutlet3Min managed object property"
    ::= { cucsSwCardEnvStatsEntry 15 }

cucsSwCardEnvStatsIntervals OBJECT-TYPE
    SYNTAX       Gauge32
    MAX-ACCESS   read-only
    STATUS       current
    DESCRIPTION
        "Cisco UCS sw:CardEnvStats:intervals managed object property"
    ::= { cucsSwCardEnvStatsEntry 16 }

cucsSwCardEnvStatsSuspect OBJECT-TYPE
    SYNTAX       TruthValue
    MAX-ACCESS   read-only
    STATUS       current
    DESCRIPTION
        "Cisco UCS sw:CardEnvStats:suspect managed object property"
    ::= { cucsSwCardEnvStatsEntry 17 }

cucsSwCardEnvStatsThresholded OBJECT-TYPE
    SYNTAX       CucsSwCardEnvStatsThresholded
    MAX-ACCESS   read-only
    STATUS       current
    DESCRIPTION
        "Cisco UCS sw:CardEnvStats:thresholded managed object property"
    ::= { cucsSwCardEnvStatsEntry 18 }

cucsSwCardEnvStatsTimeCollected OBJECT-TYPE
    SYNTAX       DateAndTime
    MAX-ACCESS   read-only
    STATUS       current
    DESCRIPTION
        "Cisco UCS sw:CardEnvStats:timeCollected managed object property"
    ::= { cucsSwCardEnvStatsEntry 19 }

cucsSwCardEnvStatsUpdate OBJECT-TYPE
    SYNTAX       Gauge32
    MAX-ACCESS   read-only
    STATUS       current
    DESCRIPTION
        "Cisco UCS sw:CardEnvStats:update managed object property"
    ::= { cucsSwCardEnvStatsEntry 20 }

cucsSwCardEnvStatsHistTable OBJECT-TYPE
    SYNTAX           SEQUENCE OF CucsSwCardEnvStatsHistEntry
    MAX-ACCESS       not-accessible
    STATUS           current
    DESCRIPTION
        "Cisco UCS sw:CardEnvStatsHist managed object table"
    ::= { cucsSwObjects 45 }

cucsSwCardEnvStatsHistEntry OBJECT-TYPE
    SYNTAX           CucsSwCardEnvStatsHistEntry
    MAX-ACCESS       not-accessible
    STATUS           current
    DESCRIPTION
        "Entry for the cucsSwCardEnvStatsHistTable table."
    INDEX { cucsSwCardEnvStatsHistInstanceId }
    ::= { cucsSwCardEnvStatsHistTable 1 }

CucsSwCardEnvStatsHistEntry ::= SEQUENCE {
    cucsSwCardEnvStatsHistInstanceId                                 CucsManagedObjectId,
    cucsSwCardEnvStatsHistDn                                         CucsManagedObjectDn,
    cucsSwCardEnvStatsHistRn                                         SnmpAdminString,
    cucsSwCardEnvStatsHistSlotOutlet1                                INTEGER,
    cucsSwCardEnvStatsHistSlotOutlet1Avg                             INTEGER,
    cucsSwCardEnvStatsHistSlotOutlet1Max                             INTEGER,
    cucsSwCardEnvStatsHistSlotOutlet1Min                             INTEGER,
    cucsSwCardEnvStatsHistSlotOutlet2                                INTEGER,
    cucsSwCardEnvStatsHistSlotOutlet2Avg                             INTEGER,
    cucsSwCardEnvStatsHistSlotOutlet2Max                             INTEGER,
    cucsSwCardEnvStatsHistSlotOutlet2Min                             INTEGER,
    cucsSwCardEnvStatsHistSlotOutlet3                                INTEGER,
    cucsSwCardEnvStatsHistSlotOutlet3Avg                             INTEGER,
    cucsSwCardEnvStatsHistSlotOutlet3Max                             INTEGER,
    cucsSwCardEnvStatsHistSlotOutlet3Min                             INTEGER,
    cucsSwCardEnvStatsHistId                                         Unsigned64,
    cucsSwCardEnvStatsHistMostRecent                                 TruthValue,
    cucsSwCardEnvStatsHistSuspect                                    TruthValue,
    cucsSwCardEnvStatsHistThresholded                                CucsSwCardEnvStatsHistThresholded,
    cucsSwCardEnvStatsHistTimeCollected                              DateAndTime
}

cucsSwCardEnvStatsHistInstanceId OBJECT-TYPE
    SYNTAX       CucsManagedObjectId
    MAX-ACCESS   not-accessible
    STATUS       current
    DESCRIPTION
        "Instance identifier of the managed object."
    ::= { cucsSwCardEnvStatsHistEntry 1 }

cucsSwCardEnvStatsHistDn OBJECT-TYPE
    SYNTAX       CucsManagedObjectDn
    MAX-ACCESS   read-only
    STATUS       current
    DESCRIPTION
        "Cisco UCS sw:CardEnvStatsHist:dn managed object property"
    ::= { cucsSwCardEnvStatsHistEntry 2 }

cucsSwCardEnvStatsHistRn OBJECT-TYPE
    SYNTAX       SnmpAdminString
    MAX-ACCESS   read-only
    STATUS       current
    DESCRIPTION
        "Cisco UCS sw:CardEnvStatsHist:rn managed object property"
    ::= { cucsSwCardEnvStatsHistEntry 3 }

cucsSwCardEnvStatsHistSlotOutlet1 OBJECT-TYPE
    SYNTAX       INTEGER
    MAX-ACCESS   read-only
    STATUS       current
    DESCRIPTION
        "Cisco UCS sw:CardEnvStatsHist:SlotOutlet1 managed
        object property"
    ::= { cucsSwCardEnvStatsHistEntry 4 }

cucsSwCardEnvStatsHistSlotOutlet1Avg OBJECT-TYPE
    SYNTAX       INTEGER
    MAX-ACCESS   read-only
    STATUS       current
    DESCRIPTION
        "Cisco UCS sw:CardEnvStatsHist:SlotOutlet1Avg managed
        object property"
    ::= { cucsSwCardEnvStatsHistEntry 5 }

cucsSwCardEnvStatsHistSlotOutlet1Max OBJECT-TYPE
    SYNTAX       INTEGER
    MAX-ACCESS   read-only
    STATUS       current
    DESCRIPTION
        "Cisco UCS sw:CardEnvStatsHist:SlotOutlet1Max managed
        object property"
    ::= { cucsSwCardEnvStatsHistEntry 6 }

cucsSwCardEnvStatsHistSlotOutlet1Min OBJECT-TYPE
    SYNTAX       INTEGER
    MAX-ACCESS   read-only
    STATUS       current
    DESCRIPTION
        "Cisco UCS sw:CardEnvStatsHist:SlotOutlet1Min managed
        object property"
    ::= { cucsSwCardEnvStatsHistEntry 7 }

cucsSwCardEnvStatsHistSlotOutlet2 OBJECT-TYPE
    SYNTAX       INTEGER
    MAX-ACCESS   read-only
    STATUS       current
    DESCRIPTION
        "Cisco UCS sw:CardEnvStatsHist:SlotOutlet2 managed
        object property"
    ::= { cucsSwCardEnvStatsHistEntry 8 }

cucsSwCardEnvStatsHistSlotOutlet2Avg OBJECT-TYPE
    SYNTAX       INTEGER
    MAX-ACCESS   read-only
    STATUS       current
    DESCRIPTION
        "Cisco UCS sw:CardEnvStatsHist:SlotOutlet2Avg managed
        object property"
    ::= { cucsSwCardEnvStatsHistEntry 9 }

cucsSwCardEnvStatsHistSlotOutlet2Max OBJECT-TYPE
    SYNTAX       INTEGER
    MAX-ACCESS   read-only
    STATUS       current
    DESCRIPTION
        "Cisco UCS sw:CardEnvStatsHist:SlotOutlet2Max managed
        object property"
    ::= { cucsSwCardEnvStatsHistEntry 10 }

cucsSwCardEnvStatsHistSlotOutlet2Min OBJECT-TYPE
    SYNTAX       INTEGER
    MAX-ACCESS   read-only
    STATUS       current
    DESCRIPTION
        "Cisco UCS sw:CardEnvStatsHist:SlotOutlet2Min managed
        object property"
    ::= { cucsSwCardEnvStatsHistEntry 11 }

cucsSwCardEnvStatsHistSlotOutlet3 OBJECT-TYPE
    SYNTAX       INTEGER
    MAX-ACCESS   read-only
    STATUS       current
    DESCRIPTION
        "Cisco UCS sw:CardEnvStatsHist:SlotOutlet3 managed
        object property"
    ::= { cucsSwCardEnvStatsHistEntry 12 }

cucsSwCardEnvStatsHistSlotOutlet3Avg OBJECT-TYPE
    SYNTAX       INTEGER
    MAX-ACCESS   read-only
    STATUS       current
    DESCRIPTION
        "Cisco UCS sw:CardEnvStatsHist:SlotOutlet3Avg managed
        object property"
    ::= { cucsSwCardEnvStatsHistEntry 13 }

cucsSwCardEnvStatsHistSlotOutlet3Max OBJECT-TYPE
    SYNTAX       INTEGER
    MAX-ACCESS   read-only
    STATUS       current
    DESCRIPTION
        "Cisco UCS sw:CardEnvStatsHist:SlotOutlet3Max managed
        object property"
    ::= { cucsSwCardEnvStatsHistEntry 14 }

cucsSwCardEnvStatsHistSlotOutlet3Min OBJECT-TYPE
    SYNTAX       INTEGER
    MAX-ACCESS   read-only
    STATUS       current
    DESCRIPTION
        "Cisco UCS sw:CardEnvStatsHist:SlotOutlet3Min managed
        object property"
    ::= { cucsSwCardEnvStatsHistEntry 15 }

cucsSwCardEnvStatsHistId OBJECT-TYPE
    SYNTAX       Unsigned64
    MAX-ACCESS   read-only
    STATUS       current
    DESCRIPTION
        "Cisco UCS sw:CardEnvStatsHist:id managed object property"
    ::= { cucsSwCardEnvStatsHistEntry 16 }

cucsSwCardEnvStatsHistMostRecent OBJECT-TYPE
    SYNTAX       TruthValue
    MAX-ACCESS   read-only
    STATUS       current
    DESCRIPTION
        "Cisco UCS sw:CardEnvStatsHist:mostRecent managed object property"
    ::= { cucsSwCardEnvStatsHistEntry 17 }

cucsSwCardEnvStatsHistSuspect OBJECT-TYPE
    SYNTAX       TruthValue
    MAX-ACCESS   read-only
    STATUS       current
    DESCRIPTION
        "Cisco UCS sw:CardEnvStatsHist:suspect managed object property"
    ::= { cucsSwCardEnvStatsHistEntry 18 }

cucsSwCardEnvStatsHistThresholded OBJECT-TYPE
    SYNTAX       CucsSwCardEnvStatsHistThresholded
    MAX-ACCESS   read-only
    STATUS       current
    DESCRIPTION
        "Cisco UCS sw:CardEnvStatsHist:thresholded managed
        object property"
    ::= { cucsSwCardEnvStatsHistEntry 19 }

cucsSwCardEnvStatsHistTimeCollected OBJECT-TYPE
    SYNTAX       DateAndTime
    MAX-ACCESS   read-only
    STATUS       current
    DESCRIPTION
        "Cisco UCS sw:CardEnvStatsHist:timeCollected managed
        object property"
    ::= { cucsSwCardEnvStatsHistEntry 20 }

cucsSwCmclanTable OBJECT-TYPE
    SYNTAX           SEQUENCE OF CucsSwCmclanEntry
    MAX-ACCESS       not-accessible
    STATUS           current
    DESCRIPTION
        "Cisco UCS sw:Cmclan managed object table"
    ::= { cucsSwObjects 69 }

cucsSwCmclanEntry OBJECT-TYPE
    SYNTAX           CucsSwCmclanEntry
    MAX-ACCESS       not-accessible
    STATUS           current
    DESCRIPTION
        "Entry for the cucsSwCmclanTable table."
    INDEX { cucsSwCmclanInstanceId }
    ::= { cucsSwCmclanTable 1 }

CucsSwCmclanEntry ::= SEQUENCE {
    cucsSwCmclanInstanceId                                           CucsManagedObjectId,
    cucsSwCmclanDn                                                   CucsManagedObjectDn,
    cucsSwCmclanRn                                                   SnmpAdminString,
    cucsSwCmclanCimcIds                                              CucsSwCimcId,
    cucsSwCmclanEpDn                                                 SnmpAdminString,
    cucsSwCmclanId                                                   Gauge32,
    cucsSwCmclanIfRole                                               CucsNetworkPortRole,
    cucsSwCmclanIfType                                               CucsNetworkVnetEpIfType,
    cucsSwCmclanLocale                                               CucsNetworkLocale,
    cucsSwCmclanName                                                 SnmpAdminString,
    cucsSwCmclanPeerDn                                               SnmpAdminString,
    cucsSwCmclanTransport                                            CucsNetworkTransport,
    cucsSwCmclanType                                                 CucsNetworkConnectionType
}

cucsSwCmclanInstanceId OBJECT-TYPE
    SYNTAX       CucsManagedObjectId
    MAX-ACCESS   not-accessible
    STATUS       current
    DESCRIPTION
        "Instance identifier of the managed object."
    ::= { cucsSwCmclanEntry 1 }

cucsSwCmclanDn OBJECT-TYPE
    SYNTAX       CucsManagedObjectDn
    MAX-ACCESS   read-only
    STATUS       current
    DESCRIPTION
        "Cisco UCS sw:Cmclan:dn managed object property"
    ::= { cucsSwCmclanEntry 2 }

cucsSwCmclanRn OBJECT-TYPE
    SYNTAX       SnmpAdminString
    MAX-ACCESS   read-only
    STATUS       current
    DESCRIPTION
        "Cisco UCS sw:Cmclan:rn managed object property"
    ::= { cucsSwCmclanEntry 3 }

cucsSwCmclanCimcIds OBJECT-TYPE
    SYNTAX       CucsSwCimcId
    MAX-ACCESS   read-only
    STATUS       current
    DESCRIPTION
        "Cisco UCS sw:Cmclan:cimcIds managed object property"
    ::= { cucsSwCmclanEntry 4 }

cucsSwCmclanEpDn OBJECT-TYPE
    SYNTAX       SnmpAdminString
    MAX-ACCESS   read-only
    STATUS       current
    DESCRIPTION
        "Cisco UCS sw:Cmclan:epDn managed object property"
    ::= { cucsSwCmclanEntry 5 }

cucsSwCmclanId OBJECT-TYPE
    SYNTAX       Gauge32
    MAX-ACCESS   read-only
    STATUS       current
    DESCRIPTION
        "Cisco UCS sw:Cmclan:id managed object property"
    ::= { cucsSwCmclanEntry 6 }

cucsSwCmclanIfRole OBJECT-TYPE
    SYNTAX       CucsNetworkPortRole
    MAX-ACCESS   read-only
    STATUS       current
    DESCRIPTION
        "Cisco UCS sw:Cmclan:ifRole managed object property"
    ::= { cucsSwCmclanEntry 7 }

cucsSwCmclanIfType OBJECT-TYPE
    SYNTAX       CucsNetworkVnetEpIfType
    MAX-ACCESS   read-only
    STATUS       current
    DESCRIPTION
        "Cisco UCS sw:Cmclan:ifType managed object property"
    ::= { cucsSwCmclanEntry 8 }

cucsSwCmclanLocale OBJECT-TYPE
    SYNTAX       CucsNetworkLocale
    MAX-ACCESS   read-only
    STATUS       current
    DESCRIPTION
        "Cisco UCS sw:Cmclan:locale managed object property"
    ::= { cucsSwCmclanEntry 9 }

cucsSwCmclanName OBJECT-TYPE
    SYNTAX       SnmpAdminString
    MAX-ACCESS   read-only
    STATUS       current
    DESCRIPTION
        "Cisco UCS sw:Cmclan:name managed object property"
    ::= { cucsSwCmclanEntry 10 }

cucsSwCmclanPeerDn OBJECT-TYPE
    SYNTAX       SnmpAdminString
    MAX-ACCESS   read-only
    STATUS       current
    DESCRIPTION
        "Cisco UCS sw:Cmclan:peerDn managed object property"
    ::= { cucsSwCmclanEntry 11 }

cucsSwCmclanTransport OBJECT-TYPE
    SYNTAX       CucsNetworkTransport
    MAX-ACCESS   read-only
    STATUS       current
    DESCRIPTION
        "Cisco UCS sw:Cmclan:transport managed object property"
    ::= { cucsSwCmclanEntry 12 }

cucsSwCmclanType OBJECT-TYPE
    SYNTAX       CucsNetworkConnectionType
    MAX-ACCESS   read-only
    STATUS       current
    DESCRIPTION
        "Cisco UCS sw:Cmclan:type managed object property"
    ::= { cucsSwCmclanEntry 13 }

cucsSwEnvStatsTable OBJECT-TYPE
    SYNTAX           SEQUENCE OF CucsSwEnvStatsEntry
    MAX-ACCESS       not-accessible
    STATUS           current
    DESCRIPTION
        "Cisco UCS sw:EnvStats managed object table"
    ::= { cucsSwObjects 4 }

cucsSwEnvStatsEntry OBJECT-TYPE
    SYNTAX           CucsSwEnvStatsEntry
    MAX-ACCESS       not-accessible
    STATUS           current
    DESCRIPTION
        "Entry for the cucsSwEnvStatsTable table."
    INDEX { cucsSwEnvStatsInstanceId }
    ::= { cucsSwEnvStatsTable 1 }

CucsSwEnvStatsEntry ::= SEQUENCE {
    cucsSwEnvStatsInstanceId                                         CucsManagedObjectId,
    cucsSwEnvStatsDn                                                 CucsManagedObjectDn,
    cucsSwEnvStatsRn                                                 SnmpAdminString,
    cucsSwEnvStatsFanCtrlrInlet1                                     INTEGER,
    cucsSwEnvStatsFanCtrlrInlet1Avg                                  INTEGER,
    cucsSwEnvStatsFanCtrlrInlet1Max                                  INTEGER,
    cucsSwEnvStatsFanCtrlrInlet1Min                                  INTEGER,
    cucsSwEnvStatsFanCtrlrInlet2                                     INTEGER,
    cucsSwEnvStatsFanCtrlrInlet2Avg                                  INTEGER,
    cucsSwEnvStatsFanCtrlrInlet2Max                                  INTEGER,
    cucsSwEnvStatsFanCtrlrInlet2Min                                  INTEGER,
    cucsSwEnvStatsFanCtrlrInlet3                                     INTEGER,
    cucsSwEnvStatsFanCtrlrInlet3Avg                                  INTEGER,
    cucsSwEnvStatsFanCtrlrInlet3Max                                  INTEGER,
    cucsSwEnvStatsFanCtrlrInlet3Min                                  INTEGER,
    cucsSwEnvStatsFanCtrlrInlet4                                     INTEGER,
    cucsSwEnvStatsFanCtrlrInlet4Avg                                  INTEGER,
    cucsSwEnvStatsFanCtrlrInlet4Max                                  INTEGER,
    cucsSwEnvStatsFanCtrlrInlet4Min                                  INTEGER,
    cucsSwEnvStatsIntervals                                          Gauge32,
    cucsSwEnvStatsMainBoardOutlet1                                   INTEGER,
    cucsSwEnvStatsMainBoardOutlet1Avg                                INTEGER,
    cucsSwEnvStatsMainBoardOutlet1Max                                INTEGER,
    cucsSwEnvStatsMainBoardOutlet1Min                                INTEGER,
    cucsSwEnvStatsMainBoardOutlet2                                   INTEGER,
    cucsSwEnvStatsMainBoardOutlet2Avg                                INTEGER,
    cucsSwEnvStatsMainBoardOutlet2Max                                INTEGER,
    cucsSwEnvStatsMainBoardOutlet2Min                                INTEGER,
    cucsSwEnvStatsPsuCtrlrInlet1                                     INTEGER,
    cucsSwEnvStatsPsuCtrlrInlet1Avg                                  INTEGER,
    cucsSwEnvStatsPsuCtrlrInlet1Max                                  INTEGER,
    cucsSwEnvStatsPsuCtrlrInlet1Min                                  INTEGER,
    cucsSwEnvStatsPsuCtrlrInlet2                                     INTEGER,
    cucsSwEnvStatsPsuCtrlrInlet2Avg                                  INTEGER,
    cucsSwEnvStatsPsuCtrlrInlet2Max                                  INTEGER,
    cucsSwEnvStatsPsuCtrlrInlet2Min                                  INTEGER,
    cucsSwEnvStatsSuspect                                            TruthValue,
    cucsSwEnvStatsThresholded                                        CucsSwEnvStatsThresholded,
    cucsSwEnvStatsTimeCollected                                      DateAndTime,
    cucsSwEnvStatsUpdate                                             Gauge32,
    cucsSwEnvStatsDonner                                             SnmpAdminString,
    cucsSwEnvStatsDonnerAvg                                          SnmpAdminString,
    cucsSwEnvStatsDonnerMax                                          SnmpAdminString,
    cucsSwEnvStatsDonnerMin                                          SnmpAdminString,
    cucsSwEnvStatsTd2                                                SnmpAdminString,
    cucsSwEnvStatsTd2Avg                                             SnmpAdminString,
    cucsSwEnvStatsTd2Max                                             SnmpAdminString,
    cucsSwEnvStatsTd2Min                                             SnmpAdminString,
    cucsSwEnvStatsTiburon                                            SnmpAdminString,
    cucsSwEnvStatsTiburonAvg                                         SnmpAdminString,
    cucsSwEnvStatsTiburonMax                                         SnmpAdminString,
    cucsSwEnvStatsTiburonMin                                         SnmpAdminString
}

cucsSwEnvStatsInstanceId OBJECT-TYPE
    SYNTAX       CucsManagedObjectId
    MAX-ACCESS   not-accessible
    STATUS       current
    DESCRIPTION
        "Instance identifier of the managed object."
    ::= { cucsSwEnvStatsEntry 1 }

cucsSwEnvStatsDn OBJECT-TYPE
    SYNTAX       CucsManagedObjectDn
    MAX-ACCESS   read-only
    STATUS       current
    DESCRIPTION
        "Cisco UCS sw:EnvStats:dn managed object property"
    ::= { cucsSwEnvStatsEntry 2 }

cucsSwEnvStatsRn OBJECT-TYPE
    SYNTAX       SnmpAdminString
    MAX-ACCESS   read-only
    STATUS       current
    DESCRIPTION
        "Cisco UCS sw:EnvStats:rn managed object property"
    ::= { cucsSwEnvStatsEntry 3 }

cucsSwEnvStatsFanCtrlrInlet1 OBJECT-TYPE
    SYNTAX       INTEGER
    MAX-ACCESS   read-only
    STATUS       current
    DESCRIPTION
        "Cisco UCS sw:EnvStats:fanCtrlrInlet1 managed object property"
    ::= { cucsSwEnvStatsEntry 4 }

cucsSwEnvStatsFanCtrlrInlet1Avg OBJECT-TYPE
    SYNTAX       INTEGER
    MAX-ACCESS   read-only
    STATUS       current
    DESCRIPTION
        "Cisco UCS sw:EnvStats:fanCtrlrInlet1Avg managed object property"
    ::= { cucsSwEnvStatsEntry 5 }

cucsSwEnvStatsFanCtrlrInlet1Max OBJECT-TYPE
    SYNTAX       INTEGER
    MAX-ACCESS   read-only
    STATUS       current
    DESCRIPTION
        "Cisco UCS sw:EnvStats:fanCtrlrInlet1Max managed object property"
    ::= { cucsSwEnvStatsEntry 6 }

cucsSwEnvStatsFanCtrlrInlet1Min OBJECT-TYPE
    SYNTAX       INTEGER
    MAX-ACCESS   read-only
    STATUS       current
    DESCRIPTION
        "Cisco UCS sw:EnvStats:fanCtrlrInlet1Min managed object property"
    ::= { cucsSwEnvStatsEntry 7 }

cucsSwEnvStatsFanCtrlrInlet2 OBJECT-TYPE
    SYNTAX       INTEGER
    MAX-ACCESS   read-only
    STATUS       current
    DESCRIPTION
        "Cisco UCS sw:EnvStats:fanCtrlrInlet2 managed object property"
    ::= { cucsSwEnvStatsEntry 8 }

cucsSwEnvStatsFanCtrlrInlet2Avg OBJECT-TYPE
    SYNTAX       INTEGER
    MAX-ACCESS   read-only
    STATUS       current
    DESCRIPTION
        "Cisco UCS sw:EnvStats:fanCtrlrInlet2Avg managed object property"
    ::= { cucsSwEnvStatsEntry 9 }

cucsSwEnvStatsFanCtrlrInlet2Max OBJECT-TYPE
    SYNTAX       INTEGER
    MAX-ACCESS   read-only
    STATUS       current
    DESCRIPTION
        "Cisco UCS sw:EnvStats:fanCtrlrInlet2Max managed object property"
    ::= { cucsSwEnvStatsEntry 10 }

cucsSwEnvStatsFanCtrlrInlet2Min OBJECT-TYPE
    SYNTAX       INTEGER
    MAX-ACCESS   read-only
    STATUS       current
    DESCRIPTION
        "Cisco UCS sw:EnvStats:fanCtrlrInlet2Min managed object property"
    ::= { cucsSwEnvStatsEntry 11 }

cucsSwEnvStatsFanCtrlrInlet3 OBJECT-TYPE
    SYNTAX       INTEGER
    MAX-ACCESS   read-only
    STATUS       current
    DESCRIPTION
        "Cisco UCS sw:EnvStats:fanCtrlrInlet3 managed object property"
    ::= { cucsSwEnvStatsEntry 12 }

cucsSwEnvStatsFanCtrlrInlet3Avg OBJECT-TYPE
    SYNTAX       INTEGER
    MAX-ACCESS   read-only
    STATUS       current
    DESCRIPTION
        "Cisco UCS sw:EnvStats:fanCtrlrInlet3Avg managed object property"
    ::= { cucsSwEnvStatsEntry 13 }

cucsSwEnvStatsFanCtrlrInlet3Max OBJECT-TYPE
    SYNTAX       INTEGER
    MAX-ACCESS   read-only
    STATUS       current
    DESCRIPTION
        "Cisco UCS sw:EnvStats:fanCtrlrInlet3Max managed object property"
    ::= { cucsSwEnvStatsEntry 14 }

cucsSwEnvStatsFanCtrlrInlet3Min OBJECT-TYPE
    SYNTAX       INTEGER
    MAX-ACCESS   read-only
    STATUS       current
    DESCRIPTION
        "Cisco UCS sw:EnvStats:fanCtrlrInlet3Min managed object property"
    ::= { cucsSwEnvStatsEntry 15 }

cucsSwEnvStatsFanCtrlrInlet4 OBJECT-TYPE
    SYNTAX       INTEGER
    MAX-ACCESS   read-only
    STATUS       current
    DESCRIPTION
        "Cisco UCS sw:EnvStats:fanCtrlrInlet4 managed object property"
    ::= { cucsSwEnvStatsEntry 16 }

cucsSwEnvStatsFanCtrlrInlet4Avg OBJECT-TYPE
    SYNTAX       INTEGER
    MAX-ACCESS   read-only
    STATUS       current
    DESCRIPTION
        "Cisco UCS sw:EnvStats:fanCtrlrInlet4Avg managed object property"
    ::= { cucsSwEnvStatsEntry 17 }

cucsSwEnvStatsFanCtrlrInlet4Max OBJECT-TYPE
    SYNTAX       INTEGER
    MAX-ACCESS   read-only
    STATUS       current
    DESCRIPTION
        "Cisco UCS sw:EnvStats:fanCtrlrInlet4Max managed object property"
    ::= { cucsSwEnvStatsEntry 18 }

cucsSwEnvStatsFanCtrlrInlet4Min OBJECT-TYPE
    SYNTAX       INTEGER
    MAX-ACCESS   read-only
    STATUS       current
    DESCRIPTION
        "Cisco UCS sw:EnvStats:fanCtrlrInlet4Min managed object property"
    ::= { cucsSwEnvStatsEntry 19 }

cucsSwEnvStatsIntervals OBJECT-TYPE
    SYNTAX       Gauge32
    MAX-ACCESS   read-only
    STATUS       current
    DESCRIPTION
        "Cisco UCS sw:EnvStats:intervals managed object property"
    ::= { cucsSwEnvStatsEntry 20 }

cucsSwEnvStatsMainBoardOutlet1 OBJECT-TYPE
    SYNTAX       INTEGER
    MAX-ACCESS   read-only
    STATUS       current
    DESCRIPTION
        "Cisco UCS sw:EnvStats:mainBoardOutlet1 managed object property"
    ::= { cucsSwEnvStatsEntry 21 }

cucsSwEnvStatsMainBoardOutlet1Avg OBJECT-TYPE
    SYNTAX       INTEGER
    MAX-ACCESS   read-only
    STATUS       current
    DESCRIPTION
        "Cisco UCS sw:EnvStats:mainBoardOutlet1Avg managed
        object property"
    ::= { cucsSwEnvStatsEntry 22 }

cucsSwEnvStatsMainBoardOutlet1Max OBJECT-TYPE
    SYNTAX       INTEGER
    MAX-ACCESS   read-only
    STATUS       current
    DESCRIPTION
        "Cisco UCS sw:EnvStats:mainBoardOutlet1Max managed
        object property"
    ::= { cucsSwEnvStatsEntry 23 }

cucsSwEnvStatsMainBoardOutlet1Min OBJECT-TYPE
    SYNTAX       INTEGER
    MAX-ACCESS   read-only
    STATUS       current
    DESCRIPTION
        "Cisco UCS sw:EnvStats:mainBoardOutlet1Min managed
        object property"
    ::= { cucsSwEnvStatsEntry 24 }

cucsSwEnvStatsMainBoardOutlet2 OBJECT-TYPE
    SYNTAX       INTEGER
    MAX-ACCESS   read-only
    STATUS       current
    DESCRIPTION
        "Cisco UCS sw:EnvStats:mainBoardOutlet2 managed object property"
    ::= { cucsSwEnvStatsEntry 25 }

cucsSwEnvStatsMainBoardOutlet2Avg OBJECT-TYPE
    SYNTAX       INTEGER
    MAX-ACCESS   read-only
    STATUS       current
    DESCRIPTION
        "Cisco UCS sw:EnvStats:mainBoardOutlet2Avg managed
        object property"
    ::= { cucsSwEnvStatsEntry 26 }

cucsSwEnvStatsMainBoardOutlet2Max OBJECT-TYPE
    SYNTAX       INTEGER
    MAX-ACCESS   read-only
    STATUS       current
    DESCRIPTION
        "Cisco UCS sw:EnvStats:mainBoardOutlet2Max managed
        object property"
    ::= { cucsSwEnvStatsEntry 27 }

cucsSwEnvStatsMainBoardOutlet2Min OBJECT-TYPE
    SYNTAX       INTEGER
    MAX-ACCESS   read-only
    STATUS       current
    DESCRIPTION
        "Cisco UCS sw:EnvStats:mainBoardOutlet2Min managed
        object property"
    ::= { cucsSwEnvStatsEntry 28 }

cucsSwEnvStatsPsuCtrlrInlet1 OBJECT-TYPE
    SYNTAX       INTEGER
    MAX-ACCESS   read-only
    STATUS       current
    DESCRIPTION
        "Cisco UCS sw:EnvStats:psuCtrlrInlet1 managed object property"
    ::= { cucsSwEnvStatsEntry 29 }

cucsSwEnvStatsPsuCtrlrInlet1Avg OBJECT-TYPE
    SYNTAX       INTEGER
    MAX-ACCESS   read-only
    STATUS       current
    DESCRIPTION
        "Cisco UCS sw:EnvStats:psuCtrlrInlet1Avg managed object property"
    ::= { cucsSwEnvStatsEntry 30 }

cucsSwEnvStatsPsuCtrlrInlet1Max OBJECT-TYPE
    SYNTAX       INTEGER
    MAX-ACCESS   read-only
    STATUS       current
    DESCRIPTION
        "Cisco UCS sw:EnvStats:psuCtrlrInlet1Max managed object property"
    ::= { cucsSwEnvStatsEntry 31 }

cucsSwEnvStatsPsuCtrlrInlet1Min OBJECT-TYPE
    SYNTAX       INTEGER
    MAX-ACCESS   read-only
    STATUS       current
    DESCRIPTION
        "Cisco UCS sw:EnvStats:psuCtrlrInlet1Min managed object property"
    ::= { cucsSwEnvStatsEntry 32 }

cucsSwEnvStatsPsuCtrlrInlet2 OBJECT-TYPE
    SYNTAX       INTEGER
    MAX-ACCESS   read-only
    STATUS       current
    DESCRIPTION
        "Cisco UCS sw:EnvStats:psuCtrlrInlet2 managed object property"
    ::= { cucsSwEnvStatsEntry 33 }

cucsSwEnvStatsPsuCtrlrInlet2Avg OBJECT-TYPE
    SYNTAX       INTEGER
    MAX-ACCESS   read-only
    STATUS       current
    DESCRIPTION
        "Cisco UCS sw:EnvStats:psuCtrlrInlet2Avg managed object property"
    ::= { cucsSwEnvStatsEntry 34 }

cucsSwEnvStatsPsuCtrlrInlet2Max OBJECT-TYPE
    SYNTAX       INTEGER
    MAX-ACCESS   read-only
    STATUS       current
    DESCRIPTION
        "Cisco UCS sw:EnvStats:psuCtrlrInlet2Max managed object property"
    ::= { cucsSwEnvStatsEntry 35 }

cucsSwEnvStatsPsuCtrlrInlet2Min OBJECT-TYPE
    SYNTAX       INTEGER
    MAX-ACCESS   read-only
    STATUS       current
    DESCRIPTION
        "Cisco UCS sw:EnvStats:psuCtrlrInlet2Min managed object property"
    ::= { cucsSwEnvStatsEntry 36 }

cucsSwEnvStatsSuspect OBJECT-TYPE
    SYNTAX       TruthValue
    MAX-ACCESS   read-only
    STATUS       current
    DESCRIPTION
        "Cisco UCS sw:EnvStats:suspect managed object property"
    ::= { cucsSwEnvStatsEntry 37 }

cucsSwEnvStatsThresholded OBJECT-TYPE
    SYNTAX       CucsSwEnvStatsThresholded
    MAX-ACCESS   read-only
    STATUS       current
    DESCRIPTION
        "Cisco UCS sw:EnvStats:thresholded managed object property"
    ::= { cucsSwEnvStatsEntry 38 }

cucsSwEnvStatsTimeCollected OBJECT-TYPE
    SYNTAX       DateAndTime
    MAX-ACCESS   read-only
    STATUS       current
    DESCRIPTION
        "Cisco UCS sw:EnvStats:timeCollected managed object property"
    ::= { cucsSwEnvStatsEntry 39 }

cucsSwEnvStatsUpdate OBJECT-TYPE
    SYNTAX       Gauge32
    MAX-ACCESS   read-only
    STATUS       current
    DESCRIPTION
        "Cisco UCS sw:EnvStats:update managed object property"
    ::= { cucsSwEnvStatsEntry 40 }

cucsSwEnvStatsDonner OBJECT-TYPE
    SYNTAX       SnmpAdminString
    MAX-ACCESS   read-only
    STATUS       current
    DESCRIPTION
        "Cisco UCS sw:EnvStats:donner managed object property"
    ::= { cucsSwEnvStatsEntry 43 }

cucsSwEnvStatsDonnerAvg OBJECT-TYPE
    SYNTAX       SnmpAdminString
    MAX-ACCESS   read-only
    STATUS       current
    DESCRIPTION
        "Cisco UCS sw:EnvStats:donnerAvg managed object property"
    ::= { cucsSwEnvStatsEntry 44 }

cucsSwEnvStatsDonnerMax OBJECT-TYPE
    SYNTAX       SnmpAdminString
    MAX-ACCESS   read-only
    STATUS       current
    DESCRIPTION
        "Cisco UCS sw:EnvStats:donnerMax managed object property"
    ::= { cucsSwEnvStatsEntry 45 }

cucsSwEnvStatsDonnerMin OBJECT-TYPE
    SYNTAX       SnmpAdminString
    MAX-ACCESS   read-only
    STATUS       current
    DESCRIPTION
        "Cisco UCS sw:EnvStats:donnerMin managed object property"
    ::= { cucsSwEnvStatsEntry 46 }

cucsSwEnvStatsTd2 OBJECT-TYPE
    SYNTAX       SnmpAdminString
    MAX-ACCESS   read-only
    STATUS       current
    DESCRIPTION
        "Cisco UCS sw:EnvStats:td2 managed object property"
    ::= { cucsSwEnvStatsEntry 47 }

cucsSwEnvStatsTd2Avg OBJECT-TYPE
    SYNTAX       SnmpAdminString
    MAX-ACCESS   read-only
    STATUS       current
    DESCRIPTION
        "Cisco UCS sw:EnvStats:td2Avg managed object property"
    ::= { cucsSwEnvStatsEntry 48 }

cucsSwEnvStatsTd2Max OBJECT-TYPE
    SYNTAX       SnmpAdminString
    MAX-ACCESS   read-only
    STATUS       current
    DESCRIPTION
        "Cisco UCS sw:EnvStats:td2Max managed object property"
    ::= { cucsSwEnvStatsEntry 49 }

cucsSwEnvStatsTd2Min OBJECT-TYPE
    SYNTAX       SnmpAdminString
    MAX-ACCESS   read-only
    STATUS       current
    DESCRIPTION
        "Cisco UCS sw:EnvStats:td2Min managed object property"
    ::= { cucsSwEnvStatsEntry 50 }

cucsSwEnvStatsTiburon OBJECT-TYPE
    SYNTAX       SnmpAdminString
    MAX-ACCESS   read-only
    STATUS       current
    DESCRIPTION
        "Cisco UCS sw:EnvStats:tiburon managed object property"
    ::= { cucsSwEnvStatsEntry 51 }

cucsSwEnvStatsTiburonAvg OBJECT-TYPE
    SYNTAX       SnmpAdminString
    MAX-ACCESS   read-only
    STATUS       current
    DESCRIPTION
        "Cisco UCS sw:EnvStats:tiburonAvg managed object property"
    ::= { cucsSwEnvStatsEntry 52 }

cucsSwEnvStatsTiburonMax OBJECT-TYPE
    SYNTAX       SnmpAdminString
    MAX-ACCESS   read-only
    STATUS       current
    DESCRIPTION
        "Cisco UCS sw:EnvStats:tiburonMax managed object property"
    ::= { cucsSwEnvStatsEntry 53 }

cucsSwEnvStatsTiburonMin OBJECT-TYPE
    SYNTAX       SnmpAdminString
    MAX-ACCESS   read-only
    STATUS       current
    DESCRIPTION
        "Cisco UCS sw:EnvStats:tiburonMin managed object property"
    ::= { cucsSwEnvStatsEntry 54 }

cucsSwEnvStatsHistTable OBJECT-TYPE
    SYNTAX           SEQUENCE OF CucsSwEnvStatsHistEntry
    MAX-ACCESS       not-accessible
    STATUS           current
    DESCRIPTION
        "Cisco UCS sw:EnvStatsHist managed object table"
    ::= { cucsSwObjects 5 }

cucsSwEnvStatsHistEntry OBJECT-TYPE
    SYNTAX           CucsSwEnvStatsHistEntry
    MAX-ACCESS       not-accessible
    STATUS           current
    DESCRIPTION
        "Entry for the cucsSwEnvStatsHistTable table."
    INDEX { cucsSwEnvStatsHistInstanceId }
    ::= { cucsSwEnvStatsHistTable 1 }

CucsSwEnvStatsHistEntry ::= SEQUENCE {
    cucsSwEnvStatsHistInstanceId                                     CucsManagedObjectId,
    cucsSwEnvStatsHistDn                                             CucsManagedObjectDn,
    cucsSwEnvStatsHistRn                                             SnmpAdminString,
    cucsSwEnvStatsHistFanCtrlrInlet1                                 INTEGER,
    cucsSwEnvStatsHistFanCtrlrInlet1Avg                              INTEGER,
    cucsSwEnvStatsHistFanCtrlrInlet1Max                              INTEGER,
    cucsSwEnvStatsHistFanCtrlrInlet1Min                              INTEGER,
    cucsSwEnvStatsHistFanCtrlrInlet2                                 INTEGER,
    cucsSwEnvStatsHistFanCtrlrInlet2Avg                              INTEGER,
    cucsSwEnvStatsHistFanCtrlrInlet2Max                              INTEGER,
    cucsSwEnvStatsHistFanCtrlrInlet2Min                              INTEGER,
    cucsSwEnvStatsHistFanCtrlrInlet3                                 INTEGER,
    cucsSwEnvStatsHistFanCtrlrInlet3Avg                              INTEGER,
    cucsSwEnvStatsHistFanCtrlrInlet3Max                              INTEGER,
    cucsSwEnvStatsHistFanCtrlrInlet3Min                              INTEGER,
    cucsSwEnvStatsHistFanCtrlrInlet4                                 INTEGER,
    cucsSwEnvStatsHistFanCtrlrInlet4Avg                              INTEGER,
    cucsSwEnvStatsHistFanCtrlrInlet4Max                              INTEGER,
    cucsSwEnvStatsHistFanCtrlrInlet4Min                              INTEGER,
    cucsSwEnvStatsHistId                                             Unsigned64,
    cucsSwEnvStatsHistMainBoardOutlet1                               INTEGER,
    cucsSwEnvStatsHistMainBoardOutlet1Avg                            INTEGER,
    cucsSwEnvStatsHistMainBoardOutlet1Max                            INTEGER,
    cucsSwEnvStatsHistMainBoardOutlet1Min                            INTEGER,
    cucsSwEnvStatsHistMainBoardOutlet2                               INTEGER,
    cucsSwEnvStatsHistMainBoardOutlet2Avg                            INTEGER,
    cucsSwEnvStatsHistMainBoardOutlet2Max                            INTEGER,
    cucsSwEnvStatsHistMainBoardOutlet2Min                            INTEGER,
    cucsSwEnvStatsHistMostRecent                                     TruthValue,
    cucsSwEnvStatsHistPsuCtrlrInlet1                                 INTEGER,
    cucsSwEnvStatsHistPsuCtrlrInlet1Avg                              INTEGER,
    cucsSwEnvStatsHistPsuCtrlrInlet1Max                              INTEGER,
    cucsSwEnvStatsHistPsuCtrlrInlet1Min                              INTEGER,
    cucsSwEnvStatsHistPsuCtrlrInlet2                                 INTEGER,
    cucsSwEnvStatsHistPsuCtrlrInlet2Avg                              INTEGER,
    cucsSwEnvStatsHistPsuCtrlrInlet2Max                              INTEGER,
    cucsSwEnvStatsHistPsuCtrlrInlet2Min                              INTEGER,
    cucsSwEnvStatsHistSuspect                                        TruthValue,
    cucsSwEnvStatsHistThresholded                                    CucsSwEnvStatsHistThresholded,
    cucsSwEnvStatsHistTimeCollected                                  DateAndTime,
    cucsSwEnvStatsHistDonner                                         SnmpAdminString,
    cucsSwEnvStatsHistDonnerAvg                                      SnmpAdminString,
    cucsSwEnvStatsHistDonnerMax                                      SnmpAdminString,
    cucsSwEnvStatsHistDonnerMin                                      SnmpAdminString,
    cucsSwEnvStatsHistTd2                                            SnmpAdminString,
    cucsSwEnvStatsHistTd2Avg                                         SnmpAdminString,
    cucsSwEnvStatsHistTd2Max                                         SnmpAdminString,
    cucsSwEnvStatsHistTd2Min                                         SnmpAdminString,
    cucsSwEnvStatsHistTiburon                                        SnmpAdminString,
    cucsSwEnvStatsHistTiburonAvg                                     SnmpAdminString,
    cucsSwEnvStatsHistTiburonMax                                     SnmpAdminString,
    cucsSwEnvStatsHistTiburonMin                                     SnmpAdminString
}

cucsSwEnvStatsHistInstanceId OBJECT-TYPE
    SYNTAX       CucsManagedObjectId
    MAX-ACCESS   not-accessible
    STATUS       current
    DESCRIPTION
        "Instance identifier of the managed object."
    ::= { cucsSwEnvStatsHistEntry 1 }

cucsSwEnvStatsHistDn OBJECT-TYPE
    SYNTAX       CucsManagedObjectDn
    MAX-ACCESS   read-only
    STATUS       current
    DESCRIPTION
        "Cisco UCS sw:EnvStatsHist:dn managed object property"
    ::= { cucsSwEnvStatsHistEntry 2 }

cucsSwEnvStatsHistRn OBJECT-TYPE
    SYNTAX       SnmpAdminString
    MAX-ACCESS   read-only
    STATUS       current
    DESCRIPTION
        "Cisco UCS sw:EnvStatsHist:rn managed object property"
    ::= { cucsSwEnvStatsHistEntry 3 }

cucsSwEnvStatsHistFanCtrlrInlet1 OBJECT-TYPE
    SYNTAX       INTEGER
    MAX-ACCESS   read-only
    STATUS       current
    DESCRIPTION
        "Cisco UCS sw:EnvStatsHist:fanCtrlrInlet1 managed object property"
    ::= { cucsSwEnvStatsHistEntry 4 }

cucsSwEnvStatsHistFanCtrlrInlet1Avg OBJECT-TYPE
    SYNTAX       INTEGER
    MAX-ACCESS   read-only
    STATUS       current
    DESCRIPTION
        "Cisco UCS sw:EnvStatsHist:fanCtrlrInlet1Avg managed
        object property"
    ::= { cucsSwEnvStatsHistEntry 5 }

cucsSwEnvStatsHistFanCtrlrInlet1Max OBJECT-TYPE
    SYNTAX       INTEGER
    MAX-ACCESS   read-only
    STATUS       current
    DESCRIPTION
        "Cisco UCS sw:EnvStatsHist:fanCtrlrInlet1Max managed
        object property"
    ::= { cucsSwEnvStatsHistEntry 6 }

cucsSwEnvStatsHistFanCtrlrInlet1Min OBJECT-TYPE
    SYNTAX       INTEGER
    MAX-ACCESS   read-only
    STATUS       current
    DESCRIPTION
        "Cisco UCS sw:EnvStatsHist:fanCtrlrInlet1Min managed
        object property"
    ::= { cucsSwEnvStatsHistEntry 7 }

cucsSwEnvStatsHistFanCtrlrInlet2 OBJECT-TYPE
    SYNTAX       INTEGER
    MAX-ACCESS   read-only
    STATUS       current
    DESCRIPTION
        "Cisco UCS sw:EnvStatsHist:fanCtrlrInlet2 managed object property"
    ::= { cucsSwEnvStatsHistEntry 8 }

cucsSwEnvStatsHistFanCtrlrInlet2Avg OBJECT-TYPE
    SYNTAX       INTEGER
    MAX-ACCESS   read-only
    STATUS       current
    DESCRIPTION
        "Cisco UCS sw:EnvStatsHist:fanCtrlrInlet2Avg managed
        object property"
    ::= { cucsSwEnvStatsHistEntry 9 }

cucsSwEnvStatsHistFanCtrlrInlet2Max OBJECT-TYPE
    SYNTAX       INTEGER
    MAX-ACCESS   read-only
    STATUS       current
    DESCRIPTION
        "Cisco UCS sw:EnvStatsHist:fanCtrlrInlet2Max managed
        object property"
    ::= { cucsSwEnvStatsHistEntry 10 }

cucsSwEnvStatsHistFanCtrlrInlet2Min OBJECT-TYPE
    SYNTAX       INTEGER
    MAX-ACCESS   read-only
    STATUS       current
    DESCRIPTION
        "Cisco UCS sw:EnvStatsHist:fanCtrlrInlet2Min managed
        object property"
    ::= { cucsSwEnvStatsHistEntry 11 }

cucsSwEnvStatsHistFanCtrlrInlet3 OBJECT-TYPE
    SYNTAX       INTEGER
    MAX-ACCESS   read-only
    STATUS       current
    DESCRIPTION
        "Cisco UCS sw:EnvStatsHist:fanCtrlrInlet3 managed object property"
    ::= { cucsSwEnvStatsHistEntry 12 }

cucsSwEnvStatsHistFanCtrlrInlet3Avg OBJECT-TYPE
    SYNTAX       INTEGER
    MAX-ACCESS   read-only
    STATUS       current
    DESCRIPTION
        "Cisco UCS sw:EnvStatsHist:fanCtrlrInlet3Avg managed
        object property"
    ::= { cucsSwEnvStatsHistEntry 13 }

cucsSwEnvStatsHistFanCtrlrInlet3Max OBJECT-TYPE
    SYNTAX       INTEGER
    MAX-ACCESS   read-only
    STATUS       current
    DESCRIPTION
        "Cisco UCS sw:EnvStatsHist:fanCtrlrInlet3Max managed
        object property"
    ::= { cucsSwEnvStatsHistEntry 14 }

cucsSwEnvStatsHistFanCtrlrInlet3Min OBJECT-TYPE
    SYNTAX       INTEGER
    MAX-ACCESS   read-only
    STATUS       current
    DESCRIPTION
        "Cisco UCS sw:EnvStatsHist:fanCtrlrInlet3Min managed
        object property"
    ::= { cucsSwEnvStatsHistEntry 15 }

cucsSwEnvStatsHistFanCtrlrInlet4 OBJECT-TYPE
    SYNTAX       INTEGER
    MAX-ACCESS   read-only
    STATUS       current
    DESCRIPTION
        "Cisco UCS sw:EnvStatsHist:fanCtrlrInlet4 managed object property"
    ::= { cucsSwEnvStatsHistEntry 16 }

cucsSwEnvStatsHistFanCtrlrInlet4Avg OBJECT-TYPE
    SYNTAX       INTEGER
    MAX-ACCESS   read-only
    STATUS       current
    DESCRIPTION
        "Cisco UCS sw:EnvStatsHist:fanCtrlrInlet4Avg managed
        object property"
    ::= { cucsSwEnvStatsHistEntry 17 }

cucsSwEnvStatsHistFanCtrlrInlet4Max OBJECT-TYPE
    SYNTAX       INTEGER
    MAX-ACCESS   read-only
    STATUS       current
    DESCRIPTION
        "Cisco UCS sw:EnvStatsHist:fanCtrlrInlet4Max managed
        object property"
    ::= { cucsSwEnvStatsHistEntry 18 }

cucsSwEnvStatsHistFanCtrlrInlet4Min OBJECT-TYPE
    SYNTAX       INTEGER
    MAX-ACCESS   read-only
    STATUS       current
    DESCRIPTION
        "Cisco UCS sw:EnvStatsHist:fanCtrlrInlet4Min managed
        object property"
    ::= { cucsSwEnvStatsHistEntry 19 }

cucsSwEnvStatsHistId OBJECT-TYPE
    SYNTAX       Unsigned64
    MAX-ACCESS   read-only
    STATUS       current
    DESCRIPTION
        "Cisco UCS sw:EnvStatsHist:id managed object property"
    ::= { cucsSwEnvStatsHistEntry 20 }

cucsSwEnvStatsHistMainBoardOutlet1 OBJECT-TYPE
    SYNTAX       INTEGER
    MAX-ACCESS   read-only
    STATUS       current
    DESCRIPTION
        "Cisco UCS sw:EnvStatsHist:mainBoardOutlet1 managed
        object property"
    ::= { cucsSwEnvStatsHistEntry 21 }

cucsSwEnvStatsHistMainBoardOutlet1Avg OBJECT-TYPE
    SYNTAX       INTEGER
    MAX-ACCESS   read-only
    STATUS       current
    DESCRIPTION
        "Cisco UCS sw:EnvStatsHist:mainBoardOutlet1Avg
        managed object property"
    ::= { cucsSwEnvStatsHistEntry 22 }

cucsSwEnvStatsHistMainBoardOutlet1Max OBJECT-TYPE
    SYNTAX       INTEGER
    MAX-ACCESS   read-only
    STATUS       current
    DESCRIPTION
        "Cisco UCS sw:EnvStatsHist:mainBoardOutlet1Max
        managed object property"
    ::= { cucsSwEnvStatsHistEntry 23 }

cucsSwEnvStatsHistMainBoardOutlet1Min OBJECT-TYPE
    SYNTAX       INTEGER
    MAX-ACCESS   read-only
    STATUS       current
    DESCRIPTION
        "Cisco UCS sw:EnvStatsHist:mainBoardOutlet1Min
        managed object property"
    ::= { cucsSwEnvStatsHistEntry 24 }

cucsSwEnvStatsHistMainBoardOutlet2 OBJECT-TYPE
    SYNTAX       INTEGER
    MAX-ACCESS   read-only
    STATUS       current
    DESCRIPTION
        "Cisco UCS sw:EnvStatsHist:mainBoardOutlet2 managed
        object property"
    ::= { cucsSwEnvStatsHistEntry 25 }

cucsSwEnvStatsHistMainBoardOutlet2Avg OBJECT-TYPE
    SYNTAX       INTEGER
    MAX-ACCESS   read-only
    STATUS       current
    DESCRIPTION
        "Cisco UCS sw:EnvStatsHist:mainBoardOutlet2Avg
        managed object property"
    ::= { cucsSwEnvStatsHistEntry 26 }

cucsSwEnvStatsHistMainBoardOutlet2Max OBJECT-TYPE
    SYNTAX       INTEGER
    MAX-ACCESS   read-only
    STATUS       current
    DESCRIPTION
        "Cisco UCS sw:EnvStatsHist:mainBoardOutlet2Max
        managed object property"
    ::= { cucsSwEnvStatsHistEntry 27 }

cucsSwEnvStatsHistMainBoardOutlet2Min OBJECT-TYPE
    SYNTAX       INTEGER
    MAX-ACCESS   read-only
    STATUS       current
    DESCRIPTION
        "Cisco UCS sw:EnvStatsHist:mainBoardOutlet2Min
        managed object property"
    ::= { cucsSwEnvStatsHistEntry 28 }

cucsSwEnvStatsHistMostRecent OBJECT-TYPE
    SYNTAX       TruthValue
    MAX-ACCESS   read-only
    STATUS       current
    DESCRIPTION
        "Cisco UCS sw:EnvStatsHist:mostRecent managed object property"
    ::= { cucsSwEnvStatsHistEntry 29 }

cucsSwEnvStatsHistPsuCtrlrInlet1 OBJECT-TYPE
    SYNTAX       INTEGER
    MAX-ACCESS   read-only
    STATUS       current
    DESCRIPTION
        "Cisco UCS sw:EnvStatsHist:psuCtrlrInlet1 managed object property"
    ::= { cucsSwEnvStatsHistEntry 30 }

cucsSwEnvStatsHistPsuCtrlrInlet1Avg OBJECT-TYPE
    SYNTAX       INTEGER
    MAX-ACCESS   read-only
    STATUS       current
    DESCRIPTION
        "Cisco UCS sw:EnvStatsHist:psuCtrlrInlet1Avg managed
        object property"
    ::= { cucsSwEnvStatsHistEntry 31 }

cucsSwEnvStatsHistPsuCtrlrInlet1Max OBJECT-TYPE
    SYNTAX       INTEGER
    MAX-ACCESS   read-only
    STATUS       current
    DESCRIPTION
        "Cisco UCS sw:EnvStatsHist:psuCtrlrInlet1Max managed
        object property"
    ::= { cucsSwEnvStatsHistEntry 32 }

cucsSwEnvStatsHistPsuCtrlrInlet1Min OBJECT-TYPE
    SYNTAX       INTEGER
    MAX-ACCESS   read-only
    STATUS       current
    DESCRIPTION
        "Cisco UCS sw:EnvStatsHist:psuCtrlrInlet1Min managed
        object property"
    ::= { cucsSwEnvStatsHistEntry 33 }

cucsSwEnvStatsHistPsuCtrlrInlet2 OBJECT-TYPE
    SYNTAX       INTEGER
    MAX-ACCESS   read-only
    STATUS       current
    DESCRIPTION
        "Cisco UCS sw:EnvStatsHist:psuCtrlrInlet2 managed object property"
    ::= { cucsSwEnvStatsHistEntry 34 }

cucsSwEnvStatsHistPsuCtrlrInlet2Avg OBJECT-TYPE
    SYNTAX       INTEGER
    MAX-ACCESS   read-only
    STATUS       current
    DESCRIPTION
        "Cisco UCS sw:EnvStatsHist:psuCtrlrInlet2Avg managed
        object property"
    ::= { cucsSwEnvStatsHistEntry 35 }

cucsSwEnvStatsHistPsuCtrlrInlet2Max OBJECT-TYPE
    SYNTAX       INTEGER
    MAX-ACCESS   read-only
    STATUS       current
    DESCRIPTION
        "Cisco UCS sw:EnvStatsHist:psuCtrlrInlet2Max managed
        object property"
    ::= { cucsSwEnvStatsHistEntry 36 }

cucsSwEnvStatsHistPsuCtrlrInlet2Min OBJECT-TYPE
    SYNTAX       INTEGER
    MAX-ACCESS   read-only
    STATUS       current
    DESCRIPTION
        "Cisco UCS sw:EnvStatsHist:psuCtrlrInlet2Min managed
        object property"
    ::= { cucsSwEnvStatsHistEntry 37 }

cucsSwEnvStatsHistSuspect OBJECT-TYPE
    SYNTAX       TruthValue
    MAX-ACCESS   read-only
    STATUS       current
    DESCRIPTION
        "Cisco UCS sw:EnvStatsHist:suspect managed object property"
    ::= { cucsSwEnvStatsHistEntry 38 }

cucsSwEnvStatsHistThresholded OBJECT-TYPE
    SYNTAX       CucsSwEnvStatsHistThresholded
    MAX-ACCESS   read-only
    STATUS       current
    DESCRIPTION
        "Cisco UCS sw:EnvStatsHist:thresholded managed object property"
    ::= { cucsSwEnvStatsHistEntry 39 }

cucsSwEnvStatsHistTimeCollected OBJECT-TYPE
    SYNTAX       DateAndTime
    MAX-ACCESS   read-only
    STATUS       current
    DESCRIPTION
        "Cisco UCS sw:EnvStatsHist:timeCollected managed object property"
    ::= { cucsSwEnvStatsHistEntry 40 }

cucsSwEnvStatsHistDonner OBJECT-TYPE
    SYNTAX       SnmpAdminString
    MAX-ACCESS   read-only
    STATUS       current
    DESCRIPTION
        "Cisco UCS sw:EnvStatsHist:donner managed object property"
    ::= { cucsSwEnvStatsHistEntry 41 }

cucsSwEnvStatsHistDonnerAvg OBJECT-TYPE
    SYNTAX       SnmpAdminString
    MAX-ACCESS   read-only
    STATUS       current
    DESCRIPTION
        "Cisco UCS sw:EnvStatsHist:donnerAvg managed object property"
    ::= { cucsSwEnvStatsHistEntry 42 }

cucsSwEnvStatsHistDonnerMax OBJECT-TYPE
    SYNTAX       SnmpAdminString
    MAX-ACCESS   read-only
    STATUS       current
    DESCRIPTION
        "Cisco UCS sw:EnvStatsHist:donnerMax managed object property"
    ::= { cucsSwEnvStatsHistEntry 43 }

cucsSwEnvStatsHistDonnerMin OBJECT-TYPE
    SYNTAX       SnmpAdminString
    MAX-ACCESS   read-only
    STATUS       current
    DESCRIPTION
        "Cisco UCS sw:EnvStatsHist:donnerMin managed object property"
    ::= { cucsSwEnvStatsHistEntry 44 }

cucsSwEnvStatsHistTd2 OBJECT-TYPE
    SYNTAX       SnmpAdminString
    MAX-ACCESS   read-only
    STATUS       current
    DESCRIPTION
        "Cisco UCS sw:EnvStatsHist:td2 managed object property"
    ::= { cucsSwEnvStatsHistEntry 45 }

cucsSwEnvStatsHistTd2Avg OBJECT-TYPE
    SYNTAX       SnmpAdminString
    MAX-ACCESS   read-only
    STATUS       current
    DESCRIPTION
        "Cisco UCS sw:EnvStatsHist:td2Avg managed object property"
    ::= { cucsSwEnvStatsHistEntry 46 }

cucsSwEnvStatsHistTd2Max OBJECT-TYPE
    SYNTAX       SnmpAdminString
    MAX-ACCESS   read-only
    STATUS       current
    DESCRIPTION
        "Cisco UCS sw:EnvStatsHist:td2Max managed object property"
    ::= { cucsSwEnvStatsHistEntry 47 }

cucsSwEnvStatsHistTd2Min OBJECT-TYPE
    SYNTAX       SnmpAdminString
    MAX-ACCESS   read-only
    STATUS       current
    DESCRIPTION
        "Cisco UCS sw:EnvStatsHist:td2Min managed object property"
    ::= { cucsSwEnvStatsHistEntry 48 }

cucsSwEnvStatsHistTiburon OBJECT-TYPE
    SYNTAX       SnmpAdminString
    MAX-ACCESS   read-only
    STATUS       current
    DESCRIPTION
        "Cisco UCS sw:EnvStatsHist:tiburon managed object property"
    ::= { cucsSwEnvStatsHistEntry 49 }

cucsSwEnvStatsHistTiburonAvg OBJECT-TYPE
    SYNTAX       SnmpAdminString
    MAX-ACCESS   read-only
    STATUS       current
    DESCRIPTION
        "Cisco UCS sw:EnvStatsHist:tiburonAvg managed object property"
    ::= { cucsSwEnvStatsHistEntry 50 }

cucsSwEnvStatsHistTiburonMax OBJECT-TYPE
    SYNTAX       SnmpAdminString
    MAX-ACCESS   read-only
    STATUS       current
    DESCRIPTION
        "Cisco UCS sw:EnvStatsHist:tiburonMax managed object property"
    ::= { cucsSwEnvStatsHistEntry 51 }

cucsSwEnvStatsHistTiburonMin OBJECT-TYPE
    SYNTAX       SnmpAdminString
    MAX-ACCESS   read-only
    STATUS       current
    DESCRIPTION
        "Cisco UCS sw:EnvStatsHist:tiburonMin managed object property"
    ::= { cucsSwEnvStatsHistEntry 52 }

cucsSwEthEstcEpTable OBJECT-TYPE
    SYNTAX           SEQUENCE OF CucsSwEthEstcEpEntry
    MAX-ACCESS       not-accessible
    STATUS           current
    DESCRIPTION
        "Cisco UCS sw:EthEstcEp managed object table"
    ::= { cucsSwObjects 6 }

cucsSwEthEstcEpEntry OBJECT-TYPE
    SYNTAX           CucsSwEthEstcEpEntry
    MAX-ACCESS       not-accessible
    STATUS           current
    DESCRIPTION
        "Entry for the cucsSwEthEstcEpTable table."
    INDEX { cucsSwEthEstcEpInstanceId }
    ::= { cucsSwEthEstcEpTable 1 }

CucsSwEthEstcEpEntry ::= SEQUENCE {
    cucsSwEthEstcEpInstanceId                                        CucsManagedObjectId,
    cucsSwEthEstcEpDn                                                CucsManagedObjectDn,
    cucsSwEthEstcEpRn                                                SnmpAdminString,
    cucsSwEthEstcEpAdminState                                        CucsFabricAdminState,
    cucsSwEthEstcEpBorderPortId                                      Gauge32,
    cucsSwEthEstcEpBorderSlotId                                      Gauge32,
    cucsSwEthEstcEpChassisId                                         Gauge32,
    cucsSwEthEstcEpCosValue                                          Gauge32,
    cucsSwEthEstcEpEpDn                                              SnmpAdminString,
    cucsSwEthEstcEpIfRole                                            CucsNetworkPortRole,
    cucsSwEthEstcEpIfType                                            CucsSwPIoEpIfType,
    cucsSwEthEstcEpLocale                                            CucsSwEstcEpLocale,
    cucsSwEthEstcEpName                                              SnmpAdminString,
    cucsSwEthEstcEpPeerDn                                            SnmpAdminString,
    cucsSwEthEstcEpPeerPortId                                        Gauge32,
    cucsSwEthEstcEpPeerSlotId                                        Gauge32,
    cucsSwEthEstcEpPinGroupName                                      SnmpAdminString,
    cucsSwEthEstcEpPortId                                            Gauge32,
    cucsSwEthEstcEpPortMode                                          CucsFabricEthEstcPortMode,
    cucsSwEthEstcEpSlotId                                            Gauge32,
    cucsSwEthEstcEpSwitchId                                          CucsNetworkSwitchId,
    cucsSwEthEstcEpTransport                                         CucsSwEthEstcEpTransport,
    cucsSwEthEstcEpType                                              CucsNetworkConnectionType,
    cucsSwEthEstcEpAdminSpeed                                        CucsPortEthSpeed,
    cucsSwEthEstcEpPcId                                              Gauge32,
    cucsSwEthEstcEpPeerChassisId                                     Gauge32,
    cucsSwEthEstcEpCdp                                               CucsNwctrlAdminState,
    cucsSwEthEstcEpForgeMac                                          CucsDpsecForgedTransmit,
    cucsSwEthEstcEpUplinkFailAction                                  CucsNwctrlLinkFailAction,
    cucsSwEthEstcEpLc                                                CucsSwPIoEpLc,
    cucsSwEthEstcEpPriorityFlowCtrl                                  CucsFlowctrlPriorityPause,
    cucsSwEthEstcEpRecvFlowCtrl                                      CucsFlowctrlFlowControl,
    cucsSwEthEstcEpSendFlowCtrl                                      CucsFlowctrlFlowControl,
    cucsSwEthEstcEpAggrPortId                                        Gauge32,
    cucsSwEthEstcEpBorderAggrPortId                                  Gauge32,
    cucsSwEthEstcEpPeerAggrPortId                                    Gauge32
}

cucsSwEthEstcEpInstanceId OBJECT-TYPE
    SYNTAX       CucsManagedObjectId
    MAX-ACCESS   not-accessible
    STATUS       current
    DESCRIPTION
        "Instance identifier of the managed object."
    ::= { cucsSwEthEstcEpEntry 1 }

cucsSwEthEstcEpDn OBJECT-TYPE
    SYNTAX       CucsManagedObjectDn
    MAX-ACCESS   read-only
    STATUS       current
    DESCRIPTION
        "Cisco UCS sw:EthEstcEp:dn managed object property"
    ::= { cucsSwEthEstcEpEntry 2 }

cucsSwEthEstcEpRn OBJECT-TYPE
    SYNTAX       SnmpAdminString
    MAX-ACCESS   read-only
    STATUS       current
    DESCRIPTION
        "Cisco UCS sw:EthEstcEp:rn managed object property"
    ::= { cucsSwEthEstcEpEntry 3 }

cucsSwEthEstcEpAdminState OBJECT-TYPE
    SYNTAX       CucsFabricAdminState
    MAX-ACCESS   read-only
    STATUS       current
    DESCRIPTION
        "Cisco UCS sw:EthEstcEp:adminState managed object property"
    ::= { cucsSwEthEstcEpEntry 4 }

cucsSwEthEstcEpBorderPortId OBJECT-TYPE
    SYNTAX       Gauge32
    MAX-ACCESS   read-only
    STATUS       current
    DESCRIPTION
        "Cisco UCS sw:EthEstcEp:borderPortId managed object property"
    ::= { cucsSwEthEstcEpEntry 5 }

cucsSwEthEstcEpBorderSlotId OBJECT-TYPE
    SYNTAX       Gauge32
    MAX-ACCESS   read-only
    STATUS       current
    DESCRIPTION
        "Cisco UCS sw:EthEstcEp:borderSlotId managed object property"
    ::= { cucsSwEthEstcEpEntry 6 }

cucsSwEthEstcEpChassisId OBJECT-TYPE
    SYNTAX       Gauge32
    MAX-ACCESS   read-only
    STATUS       current
    DESCRIPTION
        "Cisco UCS sw:EthEstcEp:chassisId managed object property"
    ::= { cucsSwEthEstcEpEntry 7 }

cucsSwEthEstcEpCosValue OBJECT-TYPE
    SYNTAX       Gauge32
    MAX-ACCESS   read-only
    STATUS       current
    DESCRIPTION
        "Cisco UCS sw:EthEstcEp:cosValue managed object property"
    ::= { cucsSwEthEstcEpEntry 8 }

cucsSwEthEstcEpEpDn OBJECT-TYPE
    SYNTAX       SnmpAdminString
    MAX-ACCESS   read-only
    STATUS       current
    DESCRIPTION
        "Cisco UCS sw:EthEstcEp:epDn managed object property"
    ::= { cucsSwEthEstcEpEntry 9 }

cucsSwEthEstcEpIfRole OBJECT-TYPE
    SYNTAX       CucsNetworkPortRole
    MAX-ACCESS   read-only
    STATUS       current
    DESCRIPTION
        "Cisco UCS sw:EthEstcEp:ifRole managed object property"
    ::= { cucsSwEthEstcEpEntry 10 }

cucsSwEthEstcEpIfType OBJECT-TYPE
    SYNTAX       CucsSwPIoEpIfType
    MAX-ACCESS   read-only
    STATUS       current
    DESCRIPTION
        "Cisco UCS sw:EthEstcEp:ifType managed object property"
    ::= { cucsSwEthEstcEpEntry 11 }

cucsSwEthEstcEpLocale OBJECT-TYPE
    SYNTAX       CucsSwEstcEpLocale
    MAX-ACCESS   read-only
    STATUS       current
    DESCRIPTION
        "Cisco UCS sw:EthEstcEp:locale managed object property"
    ::= { cucsSwEthEstcEpEntry 12 }

cucsSwEthEstcEpName OBJECT-TYPE
    SYNTAX       SnmpAdminString
    MAX-ACCESS   read-only
    STATUS       current
    DESCRIPTION
        "Cisco UCS sw:EthEstcEp:name managed object property"
    ::= { cucsSwEthEstcEpEntry 13 }

cucsSwEthEstcEpPeerDn OBJECT-TYPE
    SYNTAX       SnmpAdminString
    MAX-ACCESS   read-only
    STATUS       current
    DESCRIPTION
        "Cisco UCS sw:EthEstcEp:peerDn managed object property"
    ::= { cucsSwEthEstcEpEntry 14 }

cucsSwEthEstcEpPeerPortId OBJECT-TYPE
    SYNTAX       Gauge32
    MAX-ACCESS   read-only
    STATUS       current
    DESCRIPTION
        "Cisco UCS sw:EthEstcEp:peerPortId managed object property"
    ::= { cucsSwEthEstcEpEntry 15 }

cucsSwEthEstcEpPeerSlotId OBJECT-TYPE
    SYNTAX       Gauge32
    MAX-ACCESS   read-only
    STATUS       current
    DESCRIPTION
        "Cisco UCS sw:EthEstcEp:peerSlotId managed object property"
    ::= { cucsSwEthEstcEpEntry 16 }

cucsSwEthEstcEpPinGroupName OBJECT-TYPE
    SYNTAX       SnmpAdminString
    MAX-ACCESS   read-only
    STATUS       current
    DESCRIPTION
        "Cisco UCS sw:EthEstcEp:pinGroupName managed object property"
    ::= { cucsSwEthEstcEpEntry 17 }

cucsSwEthEstcEpPortId OBJECT-TYPE
    SYNTAX       Gauge32
    MAX-ACCESS   read-only
    STATUS       current
    DESCRIPTION
        "Cisco UCS sw:EthEstcEp:portId managed object property"
    ::= { cucsSwEthEstcEpEntry 18 }

cucsSwEthEstcEpPortMode OBJECT-TYPE
    SYNTAX       CucsFabricEthEstcPortMode
    MAX-ACCESS   read-only
    STATUS       current
    DESCRIPTION
        "Cisco UCS sw:EthEstcEp:portMode managed object property"
    ::= { cucsSwEthEstcEpEntry 19 }

cucsSwEthEstcEpSlotId OBJECT-TYPE
    SYNTAX       Gauge32
    MAX-ACCESS   read-only
    STATUS       current
    DESCRIPTION
        "Cisco UCS sw:EthEstcEp:slotId managed object property"
    ::= { cucsSwEthEstcEpEntry 20 }

cucsSwEthEstcEpSwitchId OBJECT-TYPE
    SYNTAX       CucsNetworkSwitchId
    MAX-ACCESS   read-only
    STATUS       current
    DESCRIPTION
        "Cisco UCS sw:EthEstcEp:switchId managed object property"
    ::= { cucsSwEthEstcEpEntry 21 }

cucsSwEthEstcEpTransport OBJECT-TYPE
    SYNTAX       CucsSwEthEstcEpTransport
    MAX-ACCESS   read-only
    STATUS       current
    DESCRIPTION
        "Cisco UCS sw:EthEstcEp:transport managed object property"
    ::= { cucsSwEthEstcEpEntry 22 }

cucsSwEthEstcEpType OBJECT-TYPE
    SYNTAX       CucsNetworkConnectionType
    MAX-ACCESS   read-only
    STATUS       current
    DESCRIPTION
        "Cisco UCS sw:EthEstcEp:type managed object property"
    ::= { cucsSwEthEstcEpEntry 23 }

cucsSwEthEstcEpAdminSpeed OBJECT-TYPE
    SYNTAX       CucsPortEthSpeed
    MAX-ACCESS   read-only
    STATUS       current
    DESCRIPTION
        "Cisco UCS sw:EthEstcEp:adminSpeed managed object property"
    ::= { cucsSwEthEstcEpEntry 24 }

cucsSwEthEstcEpPcId OBJECT-TYPE
    SYNTAX       Gauge32
    MAX-ACCESS   read-only
    STATUS       current
    DESCRIPTION
        "Cisco UCS sw:EthEstcEp:pcId managed object property"
    ::= { cucsSwEthEstcEpEntry 25 }

cucsSwEthEstcEpPeerChassisId OBJECT-TYPE
    SYNTAX       Gauge32
    MAX-ACCESS   read-only
    STATUS       current
    DESCRIPTION
        "Cisco UCS sw:EthEstcEp:peerChassisId managed object property"
    ::= { cucsSwEthEstcEpEntry 26 }

cucsSwEthEstcEpCdp OBJECT-TYPE
    SYNTAX       CucsNwctrlAdminState
    MAX-ACCESS   read-only
    STATUS       current
    DESCRIPTION
        "Cisco UCS sw:EthEstcEp:cdp managed object property"
    ::= { cucsSwEthEstcEpEntry 27 }

cucsSwEthEstcEpForgeMac OBJECT-TYPE
    SYNTAX       CucsDpsecForgedTransmit
    MAX-ACCESS   read-only
    STATUS       current
    DESCRIPTION
        "Cisco UCS sw:EthEstcEp:forgeMac managed object property"
    ::= { cucsSwEthEstcEpEntry 28 }

cucsSwEthEstcEpUplinkFailAction OBJECT-TYPE
    SYNTAX       CucsNwctrlLinkFailAction
    MAX-ACCESS   read-only
    STATUS       current
    DESCRIPTION
        "Cisco UCS sw:EthEstcEp:uplinkFailAction managed object property"
    ::= { cucsSwEthEstcEpEntry 29 }

cucsSwEthEstcEpLc OBJECT-TYPE
    SYNTAX       CucsSwPIoEpLc
    MAX-ACCESS   read-only
    STATUS       current
    DESCRIPTION
        "Cisco UCS sw:EthEstcEp:lc managed object property"
    ::= { cucsSwEthEstcEpEntry 30 }

cucsSwEthEstcEpPriorityFlowCtrl OBJECT-TYPE
    SYNTAX       CucsFlowctrlPriorityPause
    MAX-ACCESS   read-only
    STATUS       current
    DESCRIPTION
        "Cisco UCS sw:EthEstcEp:priorityFlowCtrl managed object property"
    ::= { cucsSwEthEstcEpEntry 31 }

cucsSwEthEstcEpRecvFlowCtrl OBJECT-TYPE
    SYNTAX       CucsFlowctrlFlowControl
    MAX-ACCESS   read-only
    STATUS       current
    DESCRIPTION
        "Cisco UCS sw:EthEstcEp:recvFlowCtrl managed object property"
    ::= { cucsSwEthEstcEpEntry 32 }

cucsSwEthEstcEpSendFlowCtrl OBJECT-TYPE
    SYNTAX       CucsFlowctrlFlowControl
    MAX-ACCESS   read-only
    STATUS       current
    DESCRIPTION
        "Cisco UCS sw:EthEstcEp:sendFlowCtrl managed object property"
    ::= { cucsSwEthEstcEpEntry 33 }

cucsSwEthEstcEpAggrPortId OBJECT-TYPE
    SYNTAX       Gauge32
    MAX-ACCESS   read-only
    STATUS       current
    DESCRIPTION
        "Cisco UCS sw:EthEstcEp:aggrPortId managed object property"
    ::= { cucsSwEthEstcEpEntry 34 }

cucsSwEthEstcEpBorderAggrPortId OBJECT-TYPE
    SYNTAX       Gauge32
    MAX-ACCESS   read-only
    STATUS       current
    DESCRIPTION
        "Cisco UCS sw:EthEstcEp:borderAggrPortId managed object property"
    ::= { cucsSwEthEstcEpEntry 35 }

cucsSwEthEstcEpPeerAggrPortId OBJECT-TYPE
    SYNTAX       Gauge32
    MAX-ACCESS   read-only
    STATUS       current
    DESCRIPTION
        "Cisco UCS sw:EthEstcEp:peerAggrPortId managed object property"
    ::= { cucsSwEthEstcEpEntry 36 }

cucsSwEthEstcPcTable OBJECT-TYPE
    SYNTAX           SEQUENCE OF CucsSwEthEstcPcEntry
    MAX-ACCESS       not-accessible
    STATUS           current
    DESCRIPTION
        "Cisco UCS sw:EthEstcPc managed object table"
    ::= { cucsSwObjects 36 }

cucsSwEthEstcPcEntry OBJECT-TYPE
    SYNTAX           CucsSwEthEstcPcEntry
    MAX-ACCESS       not-accessible
    STATUS           current
    DESCRIPTION
        "Entry for the cucsSwEthEstcPcTable table."
    INDEX { cucsSwEthEstcPcInstanceId }
    ::= { cucsSwEthEstcPcTable 1 }

CucsSwEthEstcPcEntry ::= SEQUENCE {
    cucsSwEthEstcPcInstanceId                                        CucsManagedObjectId,
    cucsSwEthEstcPcDn                                                CucsManagedObjectDn,
    cucsSwEthEstcPcRn                                                SnmpAdminString,
    cucsSwEthEstcPcAdminSpeed                                        CucsPortEthSpeed,
    cucsSwEthEstcPcAdminState                                        CucsFabricAdminState,
    cucsSwEthEstcPcBorderPortId                                      Gauge32,
    cucsSwEthEstcPcBorderSlotId                                      Gauge32,
    cucsSwEthEstcPcCosValue                                          Gauge32,
    cucsSwEthEstcPcEpDn                                              SnmpAdminString,
    cucsSwEthEstcPcIfRole                                            CucsSwLanPcIfRole,
    cucsSwEthEstcPcIfType                                            CucsSwCIoEpIfType,
    cucsSwEthEstcPcLocale                                            CucsSwBorderPcLocale,
    cucsSwEthEstcPcMonTrafDir                                        CucsFabricTrafficDirection,
    cucsSwEthEstcPcName                                              SnmpAdminString,
    cucsSwEthEstcPcPeerDn                                            SnmpAdminString,
    cucsSwEthEstcPcPortId                                            Gauge32,
    cucsSwEthEstcPcPortMode                                          CucsFabricEthEstcPortMode,
    cucsSwEthEstcPcSwitchId                                          CucsNetworkSwitchId,
    cucsSwEthEstcPcTransport                                         CucsSwEthEstcPcTransport,
    cucsSwEthEstcPcType                                              CucsSwLanPcType,
    cucsSwEthEstcPcCdp                                               CucsNwctrlAdminState,
    cucsSwEthEstcPcForgeMac                                          CucsDpsecForgedTransmit,
    cucsSwEthEstcPcProtocol                                          CucsFabricEthPcProtocol,
    cucsSwEthEstcPcUplinkFailAction                                  CucsNwctrlLinkFailAction,
    cucsSwEthEstcPcPriorityFlowCtrl                                  CucsFlowctrlPriorityPause,
    cucsSwEthEstcPcRecvFlowCtrl                                      CucsFlowctrlFlowControl,
    cucsSwEthEstcPcSendFlowCtrl                                      CucsFlowctrlFlowControl,
    cucsSwEthEstcPcLacpFastTimer                                     TruthValue,
    cucsSwEthEstcPcLacpSuspendIndividual                             TruthValue,
    cucsSwEthEstcPcBorderAggrPortId                                  Gauge32
}

cucsSwEthEstcPcInstanceId OBJECT-TYPE
    SYNTAX       CucsManagedObjectId
    MAX-ACCESS   not-accessible
    STATUS       current
    DESCRIPTION
        "Instance identifier of the managed object."
    ::= { cucsSwEthEstcPcEntry 1 }

cucsSwEthEstcPcDn OBJECT-TYPE
    SYNTAX       CucsManagedObjectDn
    MAX-ACCESS   read-only
    STATUS       current
    DESCRIPTION
        "Cisco UCS sw:EthEstcPc:dn managed object property"
    ::= { cucsSwEthEstcPcEntry 2 }

cucsSwEthEstcPcRn OBJECT-TYPE
    SYNTAX       SnmpAdminString
    MAX-ACCESS   read-only
    STATUS       current
    DESCRIPTION
        "Cisco UCS sw:EthEstcPc:rn managed object property"
    ::= { cucsSwEthEstcPcEntry 3 }

cucsSwEthEstcPcAdminSpeed OBJECT-TYPE
    SYNTAX       CucsPortEthSpeed
    MAX-ACCESS   read-only
    STATUS       current
    DESCRIPTION
        "Cisco UCS sw:EthEstcPc:adminSpeed managed object property"
    ::= { cucsSwEthEstcPcEntry 4 }

cucsSwEthEstcPcAdminState OBJECT-TYPE
    SYNTAX       CucsFabricAdminState
    MAX-ACCESS   read-only
    STATUS       current
    DESCRIPTION
        "Cisco UCS sw:EthEstcPc:adminState managed object property"
    ::= { cucsSwEthEstcPcEntry 5 }

cucsSwEthEstcPcBorderPortId OBJECT-TYPE
    SYNTAX       Gauge32
    MAX-ACCESS   read-only
    STATUS       current
    DESCRIPTION
        "Cisco UCS sw:EthEstcPc:borderPortId managed object property"
    ::= { cucsSwEthEstcPcEntry 6 }

cucsSwEthEstcPcBorderSlotId OBJECT-TYPE
    SYNTAX       Gauge32
    MAX-ACCESS   read-only
    STATUS       current
    DESCRIPTION
        "Cisco UCS sw:EthEstcPc:borderSlotId managed object property"
    ::= { cucsSwEthEstcPcEntry 7 }

cucsSwEthEstcPcCosValue OBJECT-TYPE
    SYNTAX       Gauge32
    MAX-ACCESS   read-only
    STATUS       current
    DESCRIPTION
        "Cisco UCS sw:EthEstcPc:cosValue managed object property"
    ::= { cucsSwEthEstcPcEntry 8 }

cucsSwEthEstcPcEpDn OBJECT-TYPE
    SYNTAX       SnmpAdminString
    MAX-ACCESS   read-only
    STATUS       current
    DESCRIPTION
        "Cisco UCS sw:EthEstcPc:epDn managed object property"
    ::= { cucsSwEthEstcPcEntry 9 }

cucsSwEthEstcPcIfRole OBJECT-TYPE
    SYNTAX       CucsSwLanPcIfRole
    MAX-ACCESS   read-only
    STATUS       current
    DESCRIPTION
        "Cisco UCS sw:EthEstcPc:ifRole managed object property"
    ::= { cucsSwEthEstcPcEntry 10 }

cucsSwEthEstcPcIfType OBJECT-TYPE
    SYNTAX       CucsSwCIoEpIfType
    MAX-ACCESS   read-only
    STATUS       current
    DESCRIPTION
        "Cisco UCS sw:EthEstcPc:ifType managed object property"
    ::= { cucsSwEthEstcPcEntry 11 }

cucsSwEthEstcPcLocale OBJECT-TYPE
    SYNTAX       CucsSwBorderPcLocale
    MAX-ACCESS   read-only
    STATUS       current
    DESCRIPTION
        "Cisco UCS sw:EthEstcPc:locale managed object property"
    ::= { cucsSwEthEstcPcEntry 12 }

cucsSwEthEstcPcMonTrafDir OBJECT-TYPE
    SYNTAX       CucsFabricTrafficDirection
    MAX-ACCESS   read-only
    STATUS       current
    DESCRIPTION
        "Cisco UCS sw:EthEstcPc:monTrafDir managed object property"
    ::= { cucsSwEthEstcPcEntry 13 }

cucsSwEthEstcPcName OBJECT-TYPE
    SYNTAX       SnmpAdminString
    MAX-ACCESS   read-only
    STATUS       current
    DESCRIPTION
        "Cisco UCS sw:EthEstcPc:name managed object property"
    ::= { cucsSwEthEstcPcEntry 14 }

cucsSwEthEstcPcPeerDn OBJECT-TYPE
    SYNTAX       SnmpAdminString
    MAX-ACCESS   read-only
    STATUS       current
    DESCRIPTION
        "Cisco UCS sw:EthEstcPc:peerDn managed object property"
    ::= { cucsSwEthEstcPcEntry 15 }

cucsSwEthEstcPcPortId OBJECT-TYPE
    SYNTAX       Gauge32
    MAX-ACCESS   read-only
    STATUS       current
    DESCRIPTION
        "Cisco UCS sw:EthEstcPc:portId managed object property"
    ::= { cucsSwEthEstcPcEntry 16 }

cucsSwEthEstcPcPortMode OBJECT-TYPE
    SYNTAX       CucsFabricEthEstcPortMode
    MAX-ACCESS   read-only
    STATUS       current
    DESCRIPTION
        "Cisco UCS sw:EthEstcPc:portMode managed object property"
    ::= { cucsSwEthEstcPcEntry 17 }

cucsSwEthEstcPcSwitchId OBJECT-TYPE
    SYNTAX       CucsNetworkSwitchId
    MAX-ACCESS   read-only
    STATUS       current
    DESCRIPTION
        "Cisco UCS sw:EthEstcPc:switchId managed object property"
    ::= { cucsSwEthEstcPcEntry 18 }

cucsSwEthEstcPcTransport OBJECT-TYPE
    SYNTAX       CucsSwEthEstcPcTransport
    MAX-ACCESS   read-only
    STATUS       current
    DESCRIPTION
        "Cisco UCS sw:EthEstcPc:transport managed object property"
    ::= { cucsSwEthEstcPcEntry 19 }

cucsSwEthEstcPcType OBJECT-TYPE
    SYNTAX       CucsSwLanPcType
    MAX-ACCESS   read-only
    STATUS       current
    DESCRIPTION
        "Cisco UCS sw:EthEstcPc:type managed object property"
    ::= { cucsSwEthEstcPcEntry 20 }

cucsSwEthEstcPcCdp OBJECT-TYPE
    SYNTAX       CucsNwctrlAdminState
    MAX-ACCESS   read-only
    STATUS       current
    DESCRIPTION
        "Cisco UCS sw:EthEstcPc:cdp managed object property"
    ::= { cucsSwEthEstcPcEntry 21 }

cucsSwEthEstcPcForgeMac OBJECT-TYPE
    SYNTAX       CucsDpsecForgedTransmit
    MAX-ACCESS   read-only
    STATUS       current
    DESCRIPTION
        "Cisco UCS sw:EthEstcPc:forgeMac managed object property"
    ::= { cucsSwEthEstcPcEntry 22 }

cucsSwEthEstcPcProtocol OBJECT-TYPE
    SYNTAX       CucsFabricEthPcProtocol
    MAX-ACCESS   read-only
    STATUS       current
    DESCRIPTION
        "Cisco UCS sw:EthEstcPc:protocol managed object property"
    ::= { cucsSwEthEstcPcEntry 23 }

cucsSwEthEstcPcUplinkFailAction OBJECT-TYPE
    SYNTAX       CucsNwctrlLinkFailAction
    MAX-ACCESS   read-only
    STATUS       current
    DESCRIPTION
        "Cisco UCS sw:EthEstcPc:uplinkFailAction managed object property"
    ::= { cucsSwEthEstcPcEntry 24 }

cucsSwEthEstcPcPriorityFlowCtrl OBJECT-TYPE
    SYNTAX       CucsFlowctrlPriorityPause
    MAX-ACCESS   read-only
    STATUS       current
    DESCRIPTION
        "Cisco UCS sw:EthEstcPc:priorityFlowCtrl managed object property"
    ::= { cucsSwEthEstcPcEntry 25 }

cucsSwEthEstcPcRecvFlowCtrl OBJECT-TYPE
    SYNTAX       CucsFlowctrlFlowControl
    MAX-ACCESS   read-only
    STATUS       current
    DESCRIPTION
        "Cisco UCS sw:EthEstcPc:recvFlowCtrl managed object property"
    ::= { cucsSwEthEstcPcEntry 26 }

cucsSwEthEstcPcSendFlowCtrl OBJECT-TYPE
    SYNTAX       CucsFlowctrlFlowControl
    MAX-ACCESS   read-only
    STATUS       current
    DESCRIPTION
        "Cisco UCS sw:EthEstcPc:sendFlowCtrl managed object property"
    ::= { cucsSwEthEstcPcEntry 27 }

cucsSwEthEstcPcLacpFastTimer OBJECT-TYPE
    SYNTAX       TruthValue
    MAX-ACCESS   read-only
    STATUS       current
    DESCRIPTION
        "Cisco UCS sw:EthEstcPc:lacpFastTimer managed object property"
    ::= { cucsSwEthEstcPcEntry 28 }

cucsSwEthEstcPcLacpSuspendIndividual OBJECT-TYPE
    SYNTAX       TruthValue
    MAX-ACCESS   read-only
    STATUS       current
    DESCRIPTION
        "Cisco UCS sw:EthEstcPc:lacpSuspendIndividual managed
        object property"
    ::= { cucsSwEthEstcPcEntry 29 }

cucsSwEthEstcPcBorderAggrPortId OBJECT-TYPE
    SYNTAX       Gauge32
    MAX-ACCESS   read-only
    STATUS       current
    DESCRIPTION
        "Cisco UCS sw:EthEstcPc:borderAggrPortId managed object property"
    ::= { cucsSwEthEstcPcEntry 30 }

cucsSwEthLanBorderTable OBJECT-TYPE
    SYNTAX           SEQUENCE OF CucsSwEthLanBorderEntry
    MAX-ACCESS       not-accessible
    STATUS           current
    DESCRIPTION
        "Cisco UCS sw:EthLanBorder managed object table"
    ::= { cucsSwObjects 7 }

cucsSwEthLanBorderEntry OBJECT-TYPE
    SYNTAX           CucsSwEthLanBorderEntry
    MAX-ACCESS       not-accessible
    STATUS           current
    DESCRIPTION
        "Entry for the cucsSwEthLanBorderTable table."
    INDEX { cucsSwEthLanBorderInstanceId }
    ::= { cucsSwEthLanBorderTable 1 }

CucsSwEthLanBorderEntry ::= SEQUENCE {
    cucsSwEthLanBorderInstanceId                                     CucsManagedObjectId,
    cucsSwEthLanBorderDn                                             CucsManagedObjectDn,
    cucsSwEthLanBorderRn                                             SnmpAdminString,
    cucsSwEthLanBorderFsmDescr                                       SnmpAdminString,
    cucsSwEthLanBorderFsmPrev                                        SnmpAdminString,
    cucsSwEthLanBorderFsmProgr                                       Gauge32,
    cucsSwEthLanBorderFsmRmtInvErrCode                               Gauge32,
    cucsSwEthLanBorderFsmRmtInvErrDescr                              SnmpAdminString,
    cucsSwEthLanBorderFsmRmtInvRslt                                  CucsConditionRemoteInvRslt,
    cucsSwEthLanBorderFsmStageDescr                                  SnmpAdminString,
    cucsSwEthLanBorderFsmStamp                                       DateAndTime,
    cucsSwEthLanBorderFsmStatus                                      SnmpAdminString,
    cucsSwEthLanBorderFsmTry                                         Gauge32,
    cucsSwEthLanBorderLocale                                         CucsSwBorderDomainLocale,
    cucsSwEthLanBorderName                                           SnmpAdminString,
    cucsSwEthLanBorderSwitchId                                       CucsNetworkSwitchId,
    cucsSwEthLanBorderTransport                                      CucsSwEthLanBorderTransport,
    cucsSwEthLanBorderType                                           CucsSwLanBorderType,
    cucsSwEthLanBorderDeployFlag                                     BITS,
    cucsSwEthLanBorderFsmFlags                                       SnmpAdminString,
    cucsSwEthLanBorderUdldMsgInterval                                Gauge32,
    cucsSwEthLanBorderUdldRecoveryAction                             CucsFabricRecoveryAction,
    cucsSwEthLanBorderLastVlanGrpComputeTime                         DateAndTime,
    cucsSwEthLanBorderNumVlanLimit                                   CucsSwVlanLimitStatus
}

cucsSwEthLanBorderInstanceId OBJECT-TYPE
    SYNTAX       CucsManagedObjectId
    MAX-ACCESS   not-accessible
    STATUS       current
    DESCRIPTION
        "Instance identifier of the managed object."
    ::= { cucsSwEthLanBorderEntry 1 }

cucsSwEthLanBorderDn OBJECT-TYPE
    SYNTAX       CucsManagedObjectDn
    MAX-ACCESS   read-only
    STATUS       current
    DESCRIPTION
        "Cisco UCS sw:EthLanBorder:dn managed object property"
    ::= { cucsSwEthLanBorderEntry 2 }

cucsSwEthLanBorderRn OBJECT-TYPE
    SYNTAX       SnmpAdminString
    MAX-ACCESS   read-only
    STATUS       current
    DESCRIPTION
        "Cisco UCS sw:EthLanBorder:rn managed object property"
    ::= { cucsSwEthLanBorderEntry 3 }

cucsSwEthLanBorderFsmDescr OBJECT-TYPE
    SYNTAX       SnmpAdminString
    MAX-ACCESS   read-only
    STATUS       current
    DESCRIPTION
        "Cisco UCS sw:EthLanBorder:fsmDescr managed object property"
    ::= { cucsSwEthLanBorderEntry 4 }

cucsSwEthLanBorderFsmPrev OBJECT-TYPE
    SYNTAX       SnmpAdminString
    MAX-ACCESS   read-only
    STATUS       current
    DESCRIPTION
        "Cisco UCS sw:EthLanBorder:fsmPrev managed object property"
    ::= { cucsSwEthLanBorderEntry 5 }

cucsSwEthLanBorderFsmProgr OBJECT-TYPE
    SYNTAX       Gauge32
    MAX-ACCESS   read-only
    STATUS       current
    DESCRIPTION
        "Cisco UCS sw:EthLanBorder:fsmProgr managed object property"
    ::= { cucsSwEthLanBorderEntry 6 }

cucsSwEthLanBorderFsmRmtInvErrCode OBJECT-TYPE
    SYNTAX       Gauge32
    MAX-ACCESS   read-only
    STATUS       current
    DESCRIPTION
        "Cisco UCS sw:EthLanBorder:fsmRmtInvErrCode managed
        object property"
    ::= { cucsSwEthLanBorderEntry 7 }

cucsSwEthLanBorderFsmRmtInvErrDescr OBJECT-TYPE
    SYNTAX       SnmpAdminString
    MAX-ACCESS   read-only
    STATUS       current
    DESCRIPTION
        "Cisco UCS sw:EthLanBorder:fsmRmtInvErrDescr managed
        object property"
    ::= { cucsSwEthLanBorderEntry 8 }

cucsSwEthLanBorderFsmRmtInvRslt OBJECT-TYPE
    SYNTAX       CucsConditionRemoteInvRslt
    MAX-ACCESS   read-only
    STATUS       current
    DESCRIPTION
        "Cisco UCS sw:EthLanBorder:fsmRmtInvRslt managed object property"
    ::= { cucsSwEthLanBorderEntry 9 }

cucsSwEthLanBorderFsmStageDescr OBJECT-TYPE
    SYNTAX       SnmpAdminString
    MAX-ACCESS   read-only
    STATUS       current
    DESCRIPTION
        "Cisco UCS sw:EthLanBorder:fsmStageDescr managed object property"
    ::= { cucsSwEthLanBorderEntry 10 }

cucsSwEthLanBorderFsmStamp OBJECT-TYPE
    SYNTAX       DateAndTime
    MAX-ACCESS   read-only
    STATUS       current
    DESCRIPTION
        "Cisco UCS sw:EthLanBorder:fsmStamp managed object property"
    ::= { cucsSwEthLanBorderEntry 11 }

cucsSwEthLanBorderFsmStatus OBJECT-TYPE
    SYNTAX       SnmpAdminString
    MAX-ACCESS   read-only
    STATUS       current
    DESCRIPTION
        "Cisco UCS sw:EthLanBorder:fsmStatus managed object property"
    ::= { cucsSwEthLanBorderEntry 12 }

cucsSwEthLanBorderFsmTry OBJECT-TYPE
    SYNTAX       Gauge32
    MAX-ACCESS   read-only
    STATUS       current
    DESCRIPTION
        "Cisco UCS sw:EthLanBorder:fsmTry managed object property"
    ::= { cucsSwEthLanBorderEntry 13 }

cucsSwEthLanBorderLocale OBJECT-TYPE
    SYNTAX       CucsSwBorderDomainLocale
    MAX-ACCESS   read-only
    STATUS       current
    DESCRIPTION
        "Cisco UCS sw:EthLanBorder:locale managed object property"
    ::= { cucsSwEthLanBorderEntry 14 }

cucsSwEthLanBorderName OBJECT-TYPE
    SYNTAX       SnmpAdminString
    MAX-ACCESS   read-only
    STATUS       current
    DESCRIPTION
        "Cisco UCS sw:EthLanBorder:name managed object property"
    ::= { cucsSwEthLanBorderEntry 15 }

cucsSwEthLanBorderSwitchId OBJECT-TYPE
    SYNTAX       CucsNetworkSwitchId
    MAX-ACCESS   read-only
    STATUS       current
    DESCRIPTION
        "Cisco UCS sw:EthLanBorder:switchId managed object property"
    ::= { cucsSwEthLanBorderEntry 16 }

cucsSwEthLanBorderTransport OBJECT-TYPE
    SYNTAX       CucsSwEthLanBorderTransport
    MAX-ACCESS   read-only
    STATUS       current
    DESCRIPTION
        "Cisco UCS sw:EthLanBorder:transport managed object property"
    ::= { cucsSwEthLanBorderEntry 17 }

cucsSwEthLanBorderType OBJECT-TYPE
    SYNTAX       CucsSwLanBorderType
    MAX-ACCESS   read-only
    STATUS       current
    DESCRIPTION
        "Cisco UCS sw:EthLanBorder:type managed object property"
    ::= { cucsSwEthLanBorderEntry 18 }

cucsSwEthLanBorderDeployFlag OBJECT-TYPE
    SYNTAX       BITS
    MAX-ACCESS   read-only
    STATUS       current
    DESCRIPTION
        "Cisco UCS sw:EthLanBorder:deployFlag managed object property"
    ::= { cucsSwEthLanBorderEntry 19 }

cucsSwEthLanBorderFsmFlags OBJECT-TYPE
    SYNTAX       SnmpAdminString
    MAX-ACCESS   read-only
    STATUS       current
    DESCRIPTION
        "Cisco UCS sw:EthLanBorder:fsmFlags managed object property"
    ::= { cucsSwEthLanBorderEntry 20 }

cucsSwEthLanBorderUdldMsgInterval OBJECT-TYPE
    SYNTAX       Gauge32
    MAX-ACCESS   read-only
    STATUS       current
    DESCRIPTION
        "Cisco UCS sw:EthLanBorder:udldMsgInterval managed
        object property"
    ::= { cucsSwEthLanBorderEntry 21 }

cucsSwEthLanBorderUdldRecoveryAction OBJECT-TYPE
    SYNTAX       CucsFabricRecoveryAction
    MAX-ACCESS   read-only
    STATUS       current
    DESCRIPTION
        "Cisco UCS sw:EthLanBorder:udldRecoveryAction managed
        object property"
    ::= { cucsSwEthLanBorderEntry 22 }

cucsSwEthLanBorderLastVlanGrpComputeTime OBJECT-TYPE
    SYNTAX       DateAndTime
    MAX-ACCESS   read-only
    STATUS       current
    DESCRIPTION
        "Cisco UCS sw:EthLanBorder:lastVlanGrpComputeTime
        managed object property"
    ::= { cucsSwEthLanBorderEntry 23 }

cucsSwEthLanBorderNumVlanLimit OBJECT-TYPE
    SYNTAX       CucsSwVlanLimitStatus
    MAX-ACCESS   read-only
    STATUS       current
    DESCRIPTION
        "Cisco UCS sw:EthLanBorder:numVlanLimit managed object property"
    ::= { cucsSwEthLanBorderEntry 24 }

cucsSwEthLanBorderFsmTable OBJECT-TYPE
    SYNTAX           SEQUENCE OF CucsSwEthLanBorderFsmEntry
    MAX-ACCESS       not-accessible
    STATUS           current
    DESCRIPTION
        "Cisco UCS sw:EthLanBorderFsm managed object table"
    ::= { cucsSwObjects 46 }

cucsSwEthLanBorderFsmEntry OBJECT-TYPE
    SYNTAX           CucsSwEthLanBorderFsmEntry
    MAX-ACCESS       not-accessible
    STATUS           current
    DESCRIPTION
        "Entry for the cucsSwEthLanBorderFsmTable table."
    INDEX { cucsSwEthLanBorderFsmInstanceId }
    ::= { cucsSwEthLanBorderFsmTable 1 }

CucsSwEthLanBorderFsmEntry ::= SEQUENCE {
    cucsSwEthLanBorderFsmInstanceId                                  CucsManagedObjectId,
    cucsSwEthLanBorderFsmDn                                          CucsManagedObjectDn,
    cucsSwEthLanBorderFsmRn                                          SnmpAdminString,
    cucsSwEthLanBorderFsmCompletionTime                              DateAndTime,
    cucsSwEthLanBorderFsmCurrentFsm                                  CucsSwEthLanBorderFsmCurrentFsm,
    cucsSwEthLanBorderFsmDescrData                                   SnmpAdminString,
    cucsSwEthLanBorderFsmFsmStatus                                   CucsFsmFsmStageStatus,
    cucsSwEthLanBorderFsmProgress                                    Gauge32,
    cucsSwEthLanBorderFsmRmtErrCode                                  Gauge32,
    cucsSwEthLanBorderFsmRmtErrDescr                                 SnmpAdminString,
    cucsSwEthLanBorderFsmRmtRslt                                     CucsConditionRemoteInvRslt
}

cucsSwEthLanBorderFsmInstanceId OBJECT-TYPE
    SYNTAX       CucsManagedObjectId
    MAX-ACCESS   not-accessible
    STATUS       current
    DESCRIPTION
        "Instance identifier of the managed object."
    ::= { cucsSwEthLanBorderFsmEntry 1 }

cucsSwEthLanBorderFsmDn OBJECT-TYPE
    SYNTAX       CucsManagedObjectDn
    MAX-ACCESS   read-only
    STATUS       current
    DESCRIPTION
        "Cisco UCS sw:EthLanBorderFsm:dn managed object property"
    ::= { cucsSwEthLanBorderFsmEntry 2 }

cucsSwEthLanBorderFsmRn OBJECT-TYPE
    SYNTAX       SnmpAdminString
    MAX-ACCESS   read-only
    STATUS       current
    DESCRIPTION
        "Cisco UCS sw:EthLanBorderFsm:rn managed object property"
    ::= { cucsSwEthLanBorderFsmEntry 3 }

cucsSwEthLanBorderFsmCompletionTime OBJECT-TYPE
    SYNTAX       DateAndTime
    MAX-ACCESS   read-only
    STATUS       current
    DESCRIPTION
        "Cisco UCS sw:EthLanBorderFsm:completionTime managed
        object property"
    ::= { cucsSwEthLanBorderFsmEntry 4 }

cucsSwEthLanBorderFsmCurrentFsm OBJECT-TYPE
    SYNTAX       CucsSwEthLanBorderFsmCurrentFsm
    MAX-ACCESS   read-only
    STATUS       current
    DESCRIPTION
        "Cisco UCS sw:EthLanBorderFsm:currentFsm managed object property"
    ::= { cucsSwEthLanBorderFsmEntry 5 }

cucsSwEthLanBorderFsmDescrData OBJECT-TYPE
    SYNTAX       SnmpAdminString
    MAX-ACCESS   read-only
    STATUS       current
    DESCRIPTION
        "Cisco UCS sw:EthLanBorderFsm:descr managed object property"
    ::= { cucsSwEthLanBorderFsmEntry 6 }

cucsSwEthLanBorderFsmFsmStatus OBJECT-TYPE
    SYNTAX       CucsFsmFsmStageStatus
    MAX-ACCESS   read-only
    STATUS       current
    DESCRIPTION
        "Cisco UCS sw:EthLanBorderFsm:fsmStatus managed object property"
    ::= { cucsSwEthLanBorderFsmEntry 7 }

cucsSwEthLanBorderFsmProgress OBJECT-TYPE
    SYNTAX       Gauge32
    MAX-ACCESS   read-only
    STATUS       current
    DESCRIPTION
        "Cisco UCS sw:EthLanBorderFsm:progress managed object property"
    ::= { cucsSwEthLanBorderFsmEntry 8 }

cucsSwEthLanBorderFsmRmtErrCode OBJECT-TYPE
    SYNTAX       Gauge32
    MAX-ACCESS   read-only
    STATUS       current
    DESCRIPTION
        "Cisco UCS sw:EthLanBorderFsm:rmtErrCode managed object property"
    ::= { cucsSwEthLanBorderFsmEntry 9 }

cucsSwEthLanBorderFsmRmtErrDescr OBJECT-TYPE
    SYNTAX       SnmpAdminString
    MAX-ACCESS   read-only
    STATUS       current
    DESCRIPTION
        "Cisco UCS sw:EthLanBorderFsm:rmtErrDescr managed object property"
    ::= { cucsSwEthLanBorderFsmEntry 10 }

cucsSwEthLanBorderFsmRmtRslt OBJECT-TYPE
    SYNTAX       CucsConditionRemoteInvRslt
    MAX-ACCESS   read-only
    STATUS       current
    DESCRIPTION
        "Cisco UCS sw:EthLanBorderFsm:rmtRslt managed object property"
    ::= { cucsSwEthLanBorderFsmEntry 11 }

cucsSwEthLanBorderFsmStageTable OBJECT-TYPE
    SYNTAX           SEQUENCE OF CucsSwEthLanBorderFsmStageEntry
    MAX-ACCESS       not-accessible
    STATUS           current
    DESCRIPTION
        "Cisco UCS sw:EthLanBorderFsmStage managed object table"
    ::= { cucsSwObjects 47 }

cucsSwEthLanBorderFsmStageEntry OBJECT-TYPE
    SYNTAX           CucsSwEthLanBorderFsmStageEntry
    MAX-ACCESS       not-accessible
    STATUS           current
    DESCRIPTION
        "Entry for the cucsSwEthLanBorderFsmStageTable table."
    INDEX { cucsSwEthLanBorderFsmStageInstanceId }
    ::= { cucsSwEthLanBorderFsmStageTable 1 }

CucsSwEthLanBorderFsmStageEntry ::= SEQUENCE {
    cucsSwEthLanBorderFsmStageInstanceId                             CucsManagedObjectId,
    cucsSwEthLanBorderFsmStageDn                                     CucsManagedObjectDn,
    cucsSwEthLanBorderFsmStageRn                                     SnmpAdminString,
    cucsSwEthLanBorderFsmStageDescrData                              SnmpAdminString,
    cucsSwEthLanBorderFsmStageLastUpdateTime                         DateAndTime,
    cucsSwEthLanBorderFsmStageName                                   CucsSwEthLanBorderFsmStageName,
    cucsSwEthLanBorderFsmStageOrder                                  Gauge32,
    cucsSwEthLanBorderFsmStageRetry                                  Gauge32,
    cucsSwEthLanBorderFsmStageStageStatus                            CucsFsmFsmStageStatus
}

cucsSwEthLanBorderFsmStageInstanceId OBJECT-TYPE
    SYNTAX       CucsManagedObjectId
    MAX-ACCESS   not-accessible
    STATUS       current
    DESCRIPTION
        "Instance identifier of the managed object."
    ::= { cucsSwEthLanBorderFsmStageEntry 1 }

cucsSwEthLanBorderFsmStageDn OBJECT-TYPE
    SYNTAX       CucsManagedObjectDn
    MAX-ACCESS   read-only
    STATUS       current
    DESCRIPTION
        "Cisco UCS sw:EthLanBorderFsmStage:dn managed object property"
    ::= { cucsSwEthLanBorderFsmStageEntry 2 }

cucsSwEthLanBorderFsmStageRn OBJECT-TYPE
    SYNTAX       SnmpAdminString
    MAX-ACCESS   read-only
    STATUS       current
    DESCRIPTION
        "Cisco UCS sw:EthLanBorderFsmStage:rn managed object property"
    ::= { cucsSwEthLanBorderFsmStageEntry 3 }

cucsSwEthLanBorderFsmStageDescrData OBJECT-TYPE
    SYNTAX       SnmpAdminString
    MAX-ACCESS   read-only
    STATUS       current
    DESCRIPTION
        "Cisco UCS sw:EthLanBorderFsmStage:descr managed object property"
    ::= { cucsSwEthLanBorderFsmStageEntry 4 }

cucsSwEthLanBorderFsmStageLastUpdateTime OBJECT-TYPE
    SYNTAX       DateAndTime
    MAX-ACCESS   read-only
    STATUS       current
    DESCRIPTION
        "Cisco UCS sw:EthLanBorderFsmStage:lastUpdateTime
        managed object property"
    ::= { cucsSwEthLanBorderFsmStageEntry 5 }

cucsSwEthLanBorderFsmStageName OBJECT-TYPE
    SYNTAX       CucsSwEthLanBorderFsmStageName
    MAX-ACCESS   read-only
    STATUS       current
    DESCRIPTION
        "Cisco UCS sw:EthLanBorderFsmStage:name managed object property"
    ::= { cucsSwEthLanBorderFsmStageEntry 6 }

cucsSwEthLanBorderFsmStageOrder OBJECT-TYPE
    SYNTAX       Gauge32
    MAX-ACCESS   read-only
    STATUS       current
    DESCRIPTION
        "Cisco UCS sw:EthLanBorderFsmStage:order managed object property"
    ::= { cucsSwEthLanBorderFsmStageEntry 7 }

cucsSwEthLanBorderFsmStageRetry OBJECT-TYPE
    SYNTAX       Gauge32
    MAX-ACCESS   read-only
    STATUS       current
    DESCRIPTION
        "Cisco UCS sw:EthLanBorderFsmStage:retry managed object property"
    ::= { cucsSwEthLanBorderFsmStageEntry 8 }

cucsSwEthLanBorderFsmStageStageStatus OBJECT-TYPE
    SYNTAX       CucsFsmFsmStageStatus
    MAX-ACCESS   read-only
    STATUS       current
    DESCRIPTION
        "Cisco UCS sw:EthLanBorderFsmStage:stageStatus
        managed object property"
    ::= { cucsSwEthLanBorderFsmStageEntry 9 }

cucsSwEthLanBorderFsmTaskTable OBJECT-TYPE
    SYNTAX           SEQUENCE OF CucsSwEthLanBorderFsmTaskEntry
    MAX-ACCESS       not-accessible
    STATUS           current
    DESCRIPTION
        "Cisco UCS sw:EthLanBorderFsmTask managed object table"
    ::= { cucsSwObjects 8 }

cucsSwEthLanBorderFsmTaskEntry OBJECT-TYPE
    SYNTAX           CucsSwEthLanBorderFsmTaskEntry
    MAX-ACCESS       not-accessible
    STATUS           current
    DESCRIPTION
        "Entry for the cucsSwEthLanBorderFsmTaskTable table."
    INDEX { cucsSwEthLanBorderFsmTaskInstanceId }
    ::= { cucsSwEthLanBorderFsmTaskTable 1 }

CucsSwEthLanBorderFsmTaskEntry ::= SEQUENCE {
    cucsSwEthLanBorderFsmTaskInstanceId                              CucsManagedObjectId,
    cucsSwEthLanBorderFsmTaskDn                                      CucsManagedObjectDn,
    cucsSwEthLanBorderFsmTaskRn                                      SnmpAdminString,
    cucsSwEthLanBorderFsmTaskCompletion                              CucsFsmCompletion,
    cucsSwEthLanBorderFsmTaskFlags                                   CucsSwEthLanBorderFsmTaskFlags,
    cucsSwEthLanBorderFsmTaskItem                                    CucsSwEthLanBorderFsmTaskItem,
    cucsSwEthLanBorderFsmTaskSeqId                                   Gauge32
}

cucsSwEthLanBorderFsmTaskInstanceId OBJECT-TYPE
    SYNTAX       CucsManagedObjectId
    MAX-ACCESS   not-accessible
    STATUS       current
    DESCRIPTION
        "Instance identifier of the managed object."
    ::= { cucsSwEthLanBorderFsmTaskEntry 1 }

cucsSwEthLanBorderFsmTaskDn OBJECT-TYPE
    SYNTAX       CucsManagedObjectDn
    MAX-ACCESS   read-only
    STATUS       current
    DESCRIPTION
        "Cisco UCS sw:EthLanBorderFsmTask:dn managed object property"
    ::= { cucsSwEthLanBorderFsmTaskEntry 2 }

cucsSwEthLanBorderFsmTaskRn OBJECT-TYPE
    SYNTAX       SnmpAdminString
    MAX-ACCESS   read-only
    STATUS       current
    DESCRIPTION
        "Cisco UCS sw:EthLanBorderFsmTask:rn managed object property"
    ::= { cucsSwEthLanBorderFsmTaskEntry 3 }

cucsSwEthLanBorderFsmTaskCompletion OBJECT-TYPE
    SYNTAX       CucsFsmCompletion
    MAX-ACCESS   read-only
    STATUS       current
    DESCRIPTION
        "Cisco UCS sw:EthLanBorderFsmTask:completion managed
        object property"
    ::= { cucsSwEthLanBorderFsmTaskEntry 4 }

cucsSwEthLanBorderFsmTaskFlags OBJECT-TYPE
    SYNTAX       CucsSwEthLanBorderFsmTaskFlags
    MAX-ACCESS   read-only
    STATUS       current
    DESCRIPTION
        "Cisco UCS sw:EthLanBorderFsmTask:flags managed object property"
    ::= { cucsSwEthLanBorderFsmTaskEntry 5 }

cucsSwEthLanBorderFsmTaskItem OBJECT-TYPE
    SYNTAX       CucsSwEthLanBorderFsmTaskItem
    MAX-ACCESS   read-only
    STATUS       current
    DESCRIPTION
        "Cisco UCS sw:EthLanBorderFsmTask:item managed object property"
    ::= { cucsSwEthLanBorderFsmTaskEntry 6 }

cucsSwEthLanBorderFsmTaskSeqId OBJECT-TYPE
    SYNTAX       Gauge32
    MAX-ACCESS   read-only
    STATUS       current
    DESCRIPTION
        "Cisco UCS sw:EthLanBorderFsmTask:seqId managed object property"
    ::= { cucsSwEthLanBorderFsmTaskEntry 7 }

cucsSwEthLanEpTable OBJECT-TYPE
    SYNTAX           SEQUENCE OF CucsSwEthLanEpEntry
    MAX-ACCESS       not-accessible
    STATUS           current
    DESCRIPTION
        "Cisco UCS sw:EthLanEp managed object table"
    ::= { cucsSwObjects 9 }

cucsSwEthLanEpEntry OBJECT-TYPE
    SYNTAX           CucsSwEthLanEpEntry
    MAX-ACCESS       not-accessible
    STATUS           current
    DESCRIPTION
        "Entry for the cucsSwEthLanEpTable table."
    INDEX { cucsSwEthLanEpInstanceId }
    ::= { cucsSwEthLanEpTable 1 }

CucsSwEthLanEpEntry ::= SEQUENCE {
    cucsSwEthLanEpInstanceId                                         CucsManagedObjectId,
    cucsSwEthLanEpDn                                                 CucsManagedObjectDn,
    cucsSwEthLanEpRn                                                 SnmpAdminString,
    cucsSwEthLanEpAdminSpeed                                         CucsPortEthSpeed,
    cucsSwEthLanEpAdminState                                         CucsFabricAdminState,
    cucsSwEthLanEpChassisId                                          Gauge32,
    cucsSwEthLanEpEpDn                                               SnmpAdminString,
    cucsSwEthLanEpIfRole                                             CucsSwLanEpIfRole,
    cucsSwEthLanEpIfType                                             CucsSwPIoEpIfType,
    cucsSwEthLanEpLocale                                             CucsSwBorderEpLocale,
    cucsSwEthLanEpName                                               SnmpAdminString,
    cucsSwEthLanEpPcId                                               Gauge32,
    cucsSwEthLanEpPeerDn                                             SnmpAdminString,
    cucsSwEthLanEpPeerPortId                                         Gauge32,
    cucsSwEthLanEpPeerSlotId                                         Gauge32,
    cucsSwEthLanEpPortId                                             Gauge32,
    cucsSwEthLanEpPriorityFlowCtrl                                   CucsFlowctrlPriorityPause,
    cucsSwEthLanEpRecvFlowCtrl                                       CucsFlowctrlFlowControl,
    cucsSwEthLanEpSendFlowCtrl                                       CucsFlowctrlFlowControl,
    cucsSwEthLanEpSlotId                                             Gauge32,
    cucsSwEthLanEpSwitchId                                           CucsNetworkSwitchId,
    cucsSwEthLanEpTransport                                          CucsSwEthLanEpTransport,
    cucsSwEthLanEpType                                               CucsSwLanEpType,
    cucsSwEthLanEpPeerChassisId                                      Gauge32,
    cucsSwEthLanEpLc                                                 CucsSwPIoEpLc,
    cucsSwEthLanEpUdldAdminState                                     CucsSwEthLanEpUdldAdminState,
    cucsSwEthLanEpUdldMode                                           CucsSwEthLanEpUdldMode,
    cucsSwEthLanEpAggrPortId                                         Gauge32,
    cucsSwEthLanEpPeerAggrPortId                                     Gauge32
}

cucsSwEthLanEpInstanceId OBJECT-TYPE
    SYNTAX       CucsManagedObjectId
    MAX-ACCESS   not-accessible
    STATUS       current
    DESCRIPTION
        "Instance identifier of the managed object."
    ::= { cucsSwEthLanEpEntry 1 }

cucsSwEthLanEpDn OBJECT-TYPE
    SYNTAX       CucsManagedObjectDn
    MAX-ACCESS   read-only
    STATUS       current
    DESCRIPTION
        "Cisco UCS sw:EthLanEp:dn managed object property"
    ::= { cucsSwEthLanEpEntry 2 }

cucsSwEthLanEpRn OBJECT-TYPE
    SYNTAX       SnmpAdminString
    MAX-ACCESS   read-only
    STATUS       current
    DESCRIPTION
        "Cisco UCS sw:EthLanEp:rn managed object property"
    ::= { cucsSwEthLanEpEntry 3 }

cucsSwEthLanEpAdminSpeed OBJECT-TYPE
    SYNTAX       CucsPortEthSpeed
    MAX-ACCESS   read-only
    STATUS       current
    DESCRIPTION
        "Cisco UCS sw:EthLanEp:adminSpeed managed object property"
    ::= { cucsSwEthLanEpEntry 4 }

cucsSwEthLanEpAdminState OBJECT-TYPE
    SYNTAX       CucsFabricAdminState
    MAX-ACCESS   read-only
    STATUS       current
    DESCRIPTION
        "Cisco UCS sw:EthLanEp:adminState managed object property"
    ::= { cucsSwEthLanEpEntry 5 }

cucsSwEthLanEpChassisId OBJECT-TYPE
    SYNTAX       Gauge32
    MAX-ACCESS   read-only
    STATUS       current
    DESCRIPTION
        "Cisco UCS sw:EthLanEp:chassisId managed object property"
    ::= { cucsSwEthLanEpEntry 6 }

cucsSwEthLanEpEpDn OBJECT-TYPE
    SYNTAX       SnmpAdminString
    MAX-ACCESS   read-only
    STATUS       current
    DESCRIPTION
        "Cisco UCS sw:EthLanEp:epDn managed object property"
    ::= { cucsSwEthLanEpEntry 7 }

cucsSwEthLanEpIfRole OBJECT-TYPE
    SYNTAX       CucsSwLanEpIfRole
    MAX-ACCESS   read-only
    STATUS       current
    DESCRIPTION
        "Cisco UCS sw:EthLanEp:ifRole managed object property"
    ::= { cucsSwEthLanEpEntry 8 }

cucsSwEthLanEpIfType OBJECT-TYPE
    SYNTAX       CucsSwPIoEpIfType
    MAX-ACCESS   read-only
    STATUS       current
    DESCRIPTION
        "Cisco UCS sw:EthLanEp:ifType managed object property"
    ::= { cucsSwEthLanEpEntry 9 }

cucsSwEthLanEpLocale OBJECT-TYPE
    SYNTAX       CucsSwBorderEpLocale
    MAX-ACCESS   read-only
    STATUS       current
    DESCRIPTION
        "Cisco UCS sw:EthLanEp:locale managed object property"
    ::= { cucsSwEthLanEpEntry 10 }

cucsSwEthLanEpName OBJECT-TYPE
    SYNTAX       SnmpAdminString
    MAX-ACCESS   read-only
    STATUS       current
    DESCRIPTION
        "Cisco UCS sw:EthLanEp:name managed object property"
    ::= { cucsSwEthLanEpEntry 11 }

cucsSwEthLanEpPcId OBJECT-TYPE
    SYNTAX       Gauge32
    MAX-ACCESS   read-only
    STATUS       current
    DESCRIPTION
        "Cisco UCS sw:EthLanEp:pcId managed object property"
    ::= { cucsSwEthLanEpEntry 12 }

cucsSwEthLanEpPeerDn OBJECT-TYPE
    SYNTAX       SnmpAdminString
    MAX-ACCESS   read-only
    STATUS       current
    DESCRIPTION
        "Cisco UCS sw:EthLanEp:peerDn managed object property"
    ::= { cucsSwEthLanEpEntry 13 }

cucsSwEthLanEpPeerPortId OBJECT-TYPE
    SYNTAX       Gauge32
    MAX-ACCESS   read-only
    STATUS       current
    DESCRIPTION
        "Cisco UCS sw:EthLanEp:peerPortId managed object property"
    ::= { cucsSwEthLanEpEntry 14 }

cucsSwEthLanEpPeerSlotId OBJECT-TYPE
    SYNTAX       Gauge32
    MAX-ACCESS   read-only
    STATUS       current
    DESCRIPTION
        "Cisco UCS sw:EthLanEp:peerSlotId managed object property"
    ::= { cucsSwEthLanEpEntry 15 }

cucsSwEthLanEpPortId OBJECT-TYPE
    SYNTAX       Gauge32
    MAX-ACCESS   read-only
    STATUS       current
    DESCRIPTION
        "Cisco UCS sw:EthLanEp:portId managed object property"
    ::= { cucsSwEthLanEpEntry 16 }

cucsSwEthLanEpPriorityFlowCtrl OBJECT-TYPE
    SYNTAX       CucsFlowctrlPriorityPause
    MAX-ACCESS   read-only
    STATUS       current
    DESCRIPTION
        "Cisco UCS sw:EthLanEp:priorityFlowCtrl managed object property"
    ::= { cucsSwEthLanEpEntry 17 }

cucsSwEthLanEpRecvFlowCtrl OBJECT-TYPE
    SYNTAX       CucsFlowctrlFlowControl
    MAX-ACCESS   read-only
    STATUS       current
    DESCRIPTION
        "Cisco UCS sw:EthLanEp:recvFlowCtrl managed object property"
    ::= { cucsSwEthLanEpEntry 18 }

cucsSwEthLanEpSendFlowCtrl OBJECT-TYPE
    SYNTAX       CucsFlowctrlFlowControl
    MAX-ACCESS   read-only
    STATUS       current
    DESCRIPTION
        "Cisco UCS sw:EthLanEp:sendFlowCtrl managed object property"
    ::= { cucsSwEthLanEpEntry 19 }

cucsSwEthLanEpSlotId OBJECT-TYPE
    SYNTAX       Gauge32
    MAX-ACCESS   read-only
    STATUS       current
    DESCRIPTION
        "Cisco UCS sw:EthLanEp:slotId managed object property"
    ::= { cucsSwEthLanEpEntry 20 }

cucsSwEthLanEpSwitchId OBJECT-TYPE
    SYNTAX       CucsNetworkSwitchId
    MAX-ACCESS   read-only
    STATUS       current
    DESCRIPTION
        "Cisco UCS sw:EthLanEp:switchId managed object property"
    ::= { cucsSwEthLanEpEntry 21 }

cucsSwEthLanEpTransport OBJECT-TYPE
    SYNTAX       CucsSwEthLanEpTransport
    MAX-ACCESS   read-only
    STATUS       current
    DESCRIPTION
        "Cisco UCS sw:EthLanEp:transport managed object property"
    ::= { cucsSwEthLanEpEntry 22 }

cucsSwEthLanEpType OBJECT-TYPE
    SYNTAX       CucsSwLanEpType
    MAX-ACCESS   read-only
    STATUS       current
    DESCRIPTION
        "Cisco UCS sw:EthLanEp:type managed object property"
    ::= { cucsSwEthLanEpEntry 23 }

cucsSwEthLanEpPeerChassisId OBJECT-TYPE
    SYNTAX       Gauge32
    MAX-ACCESS   read-only
    STATUS       current
    DESCRIPTION
        "Cisco UCS sw:EthLanEp:peerChassisId managed object property"
    ::= { cucsSwEthLanEpEntry 24 }

cucsSwEthLanEpLc OBJECT-TYPE
    SYNTAX       CucsSwPIoEpLc
    MAX-ACCESS   read-only
    STATUS       current
    DESCRIPTION
        "Cisco UCS sw:EthLanEp:lc managed object property"
    ::= { cucsSwEthLanEpEntry 25 }

cucsSwEthLanEpUdldAdminState OBJECT-TYPE
    SYNTAX       CucsSwEthLanEpUdldAdminState
    MAX-ACCESS   read-only
    STATUS       current
    DESCRIPTION
        "Cisco UCS sw:EthLanEp:udldAdminState managed object property"
    ::= { cucsSwEthLanEpEntry 27 }

cucsSwEthLanEpUdldMode OBJECT-TYPE
    SYNTAX       CucsSwEthLanEpUdldMode
    MAX-ACCESS   read-only
    STATUS       current
    DESCRIPTION
        "Cisco UCS sw:EthLanEp:udldMode managed object property"
    ::= { cucsSwEthLanEpEntry 28 }

cucsSwEthLanEpAggrPortId OBJECT-TYPE
    SYNTAX       Gauge32
    MAX-ACCESS   read-only
    STATUS       current
    DESCRIPTION
        "Cisco UCS sw:EthLanEp:aggrPortId managed object property"
    ::= { cucsSwEthLanEpEntry 29 }

cucsSwEthLanEpPeerAggrPortId OBJECT-TYPE
    SYNTAX       Gauge32
    MAX-ACCESS   read-only
    STATUS       current
    DESCRIPTION
        "Cisco UCS sw:EthLanEp:peerAggrPortId managed object property"
    ::= { cucsSwEthLanEpEntry 30 }

cucsSwEthLanFlowMonTable OBJECT-TYPE
    SYNTAX           SEQUENCE OF CucsSwEthLanFlowMonEntry
    MAX-ACCESS       not-accessible
    STATUS           current
    DESCRIPTION
        "Cisco UCS sw:EthLanFlowMon managed object table"
    ::= { cucsSwObjects 70 }

cucsSwEthLanFlowMonEntry OBJECT-TYPE
    SYNTAX           CucsSwEthLanFlowMonEntry
    MAX-ACCESS       not-accessible
    STATUS           current
    DESCRIPTION
        "Entry for the cucsSwEthLanFlowMonTable table."
    INDEX { cucsSwEthLanFlowMonInstanceId }
    ::= { cucsSwEthLanFlowMonTable 1 }

CucsSwEthLanFlowMonEntry ::= SEQUENCE {
    cucsSwEthLanFlowMonInstanceId                                    CucsManagedObjectId,
    cucsSwEthLanFlowMonDn                                            CucsManagedObjectDn,
    cucsSwEthLanFlowMonRn                                            SnmpAdminString,
    cucsSwEthLanFlowMonFsmDescr                                      SnmpAdminString,
    cucsSwEthLanFlowMonFsmPrev                                       SnmpAdminString,
    cucsSwEthLanFlowMonFsmProgr                                      Gauge32,
    cucsSwEthLanFlowMonFsmRmtInvErrCode                              Gauge32,
    cucsSwEthLanFlowMonFsmRmtInvErrDescr                             SnmpAdminString,
    cucsSwEthLanFlowMonFsmRmtInvRslt                                 CucsConditionRemoteInvRslt,
    cucsSwEthLanFlowMonFsmStageDescr                                 SnmpAdminString,
    cucsSwEthLanFlowMonFsmStamp                                      DateAndTime,
    cucsSwEthLanFlowMonFsmStatus                                     SnmpAdminString,
    cucsSwEthLanFlowMonFsmTry                                        Gauge32,
    cucsSwEthLanFlowMonLocale                                        CucsSwMonDomainLocale,
    cucsSwEthLanFlowMonName                                          SnmpAdminString,
    cucsSwEthLanFlowMonNetflowActiveTimeout                          Gauge32,
    cucsSwEthLanFlowMonNetflowInactiveTimeout                        Gauge32,
    cucsSwEthLanFlowMonSwitchId                                      CucsNetworkSwitchId,
    cucsSwEthLanFlowMonTransport                                     CucsSwEthLanFlowMonTransport,
    cucsSwEthLanFlowMonType                                          CucsSwLanMonType
}

cucsSwEthLanFlowMonInstanceId OBJECT-TYPE
    SYNTAX       CucsManagedObjectId
    MAX-ACCESS   not-accessible
    STATUS       current
    DESCRIPTION
        "Instance identifier of the managed object."
    ::= { cucsSwEthLanFlowMonEntry 1 }

cucsSwEthLanFlowMonDn OBJECT-TYPE
    SYNTAX       CucsManagedObjectDn
    MAX-ACCESS   read-only
    STATUS       current
    DESCRIPTION
        "Cisco UCS sw:EthLanFlowMon:dn managed object property"
    ::= { cucsSwEthLanFlowMonEntry 2 }

cucsSwEthLanFlowMonRn OBJECT-TYPE
    SYNTAX       SnmpAdminString
    MAX-ACCESS   read-only
    STATUS       current
    DESCRIPTION
        "Cisco UCS sw:EthLanFlowMon:rn managed object property"
    ::= { cucsSwEthLanFlowMonEntry 3 }

cucsSwEthLanFlowMonFsmDescr OBJECT-TYPE
    SYNTAX       SnmpAdminString
    MAX-ACCESS   read-only
    STATUS       current
    DESCRIPTION
        "Cisco UCS sw:EthLanFlowMon:fsmDescr managed object property"
    ::= { cucsSwEthLanFlowMonEntry 4 }

cucsSwEthLanFlowMonFsmPrev OBJECT-TYPE
    SYNTAX       SnmpAdminString
    MAX-ACCESS   read-only
    STATUS       current
    DESCRIPTION
        "Cisco UCS sw:EthLanFlowMon:fsmPrev managed object property"
    ::= { cucsSwEthLanFlowMonEntry 5 }

cucsSwEthLanFlowMonFsmProgr OBJECT-TYPE
    SYNTAX       Gauge32
    MAX-ACCESS   read-only
    STATUS       current
    DESCRIPTION
        "Cisco UCS sw:EthLanFlowMon:fsmProgr managed object property"
    ::= { cucsSwEthLanFlowMonEntry 6 }

cucsSwEthLanFlowMonFsmRmtInvErrCode OBJECT-TYPE
    SYNTAX       Gauge32
    MAX-ACCESS   read-only
    STATUS       current
    DESCRIPTION
        "Cisco UCS sw:EthLanFlowMon:fsmRmtInvErrCode managed
        object property"
    ::= { cucsSwEthLanFlowMonEntry 7 }

cucsSwEthLanFlowMonFsmRmtInvErrDescr OBJECT-TYPE
    SYNTAX       SnmpAdminString
    MAX-ACCESS   read-only
    STATUS       current
    DESCRIPTION
        "Cisco UCS sw:EthLanFlowMon:fsmRmtInvErrDescr managed
        object property"
    ::= { cucsSwEthLanFlowMonEntry 8 }

cucsSwEthLanFlowMonFsmRmtInvRslt OBJECT-TYPE
    SYNTAX       CucsConditionRemoteInvRslt
    MAX-ACCESS   read-only
    STATUS       current
    DESCRIPTION
        "Cisco UCS sw:EthLanFlowMon:fsmRmtInvRslt managed object property"
    ::= { cucsSwEthLanFlowMonEntry 9 }

cucsSwEthLanFlowMonFsmStageDescr OBJECT-TYPE
    SYNTAX       SnmpAdminString
    MAX-ACCESS   read-only
    STATUS       current
    DESCRIPTION
        "Cisco UCS sw:EthLanFlowMon:fsmStageDescr managed object property"
    ::= { cucsSwEthLanFlowMonEntry 10 }

cucsSwEthLanFlowMonFsmStamp OBJECT-TYPE
    SYNTAX       DateAndTime
    MAX-ACCESS   read-only
    STATUS       current
    DESCRIPTION
        "Cisco UCS sw:EthLanFlowMon:fsmStamp managed object property"
    ::= { cucsSwEthLanFlowMonEntry 11 }

cucsSwEthLanFlowMonFsmStatus OBJECT-TYPE
    SYNTAX       SnmpAdminString
    MAX-ACCESS   read-only
    STATUS       current
    DESCRIPTION
        "Cisco UCS sw:EthLanFlowMon:fsmStatus managed object property"
    ::= { cucsSwEthLanFlowMonEntry 12 }

cucsSwEthLanFlowMonFsmTry OBJECT-TYPE
    SYNTAX       Gauge32
    MAX-ACCESS   read-only
    STATUS       current
    DESCRIPTION
        "Cisco UCS sw:EthLanFlowMon:fsmTry managed object property"
    ::= { cucsSwEthLanFlowMonEntry 13 }

cucsSwEthLanFlowMonLocale OBJECT-TYPE
    SYNTAX       CucsSwMonDomainLocale
    MAX-ACCESS   read-only
    STATUS       current
    DESCRIPTION
        "Cisco UCS sw:EthLanFlowMon:locale managed object property"
    ::= { cucsSwEthLanFlowMonEntry 14 }

cucsSwEthLanFlowMonName OBJECT-TYPE
    SYNTAX       SnmpAdminString
    MAX-ACCESS   read-only
    STATUS       current
    DESCRIPTION
        "Cisco UCS sw:EthLanFlowMon:name managed object property"
    ::= { cucsSwEthLanFlowMonEntry 15 }

cucsSwEthLanFlowMonNetflowActiveTimeout OBJECT-TYPE
    SYNTAX       Gauge32
    MAX-ACCESS   read-only
    STATUS       current
    DESCRIPTION
        "Cisco UCS sw:EthLanFlowMon:netflowActiveTimeout
        managed object property"
    ::= { cucsSwEthLanFlowMonEntry 16 }

cucsSwEthLanFlowMonNetflowInactiveTimeout OBJECT-TYPE
    SYNTAX       Gauge32
    MAX-ACCESS   read-only
    STATUS       current
    DESCRIPTION
        "Cisco UCS sw:EthLanFlowMon:netflowInactiveTimeout
        managed object property"
    ::= { cucsSwEthLanFlowMonEntry 17 }

cucsSwEthLanFlowMonSwitchId OBJECT-TYPE
    SYNTAX       CucsNetworkSwitchId
    MAX-ACCESS   read-only
    STATUS       current
    DESCRIPTION
        "Cisco UCS sw:EthLanFlowMon:switchId managed object property"
    ::= { cucsSwEthLanFlowMonEntry 18 }

cucsSwEthLanFlowMonTransport OBJECT-TYPE
    SYNTAX       CucsSwEthLanFlowMonTransport
    MAX-ACCESS   read-only
    STATUS       current
    DESCRIPTION
        "Cisco UCS sw:EthLanFlowMon:transport managed object property"
    ::= { cucsSwEthLanFlowMonEntry 19 }

cucsSwEthLanFlowMonType OBJECT-TYPE
    SYNTAX       CucsSwLanMonType
    MAX-ACCESS   read-only
    STATUS       current
    DESCRIPTION
        "Cisco UCS sw:EthLanFlowMon:type managed object property"
    ::= { cucsSwEthLanFlowMonEntry 20 }

cucsSwEthLanFlowMonFsmTable OBJECT-TYPE
    SYNTAX           SEQUENCE OF CucsSwEthLanFlowMonFsmEntry
    MAX-ACCESS       not-accessible
    STATUS           current
    DESCRIPTION
        "Cisco UCS sw:EthLanFlowMonFsm managed object table"
    ::= { cucsSwObjects 71 }

cucsSwEthLanFlowMonFsmEntry OBJECT-TYPE
    SYNTAX           CucsSwEthLanFlowMonFsmEntry
    MAX-ACCESS       not-accessible
    STATUS           current
    DESCRIPTION
        "Entry for the cucsSwEthLanFlowMonFsmTable table."
    INDEX { cucsSwEthLanFlowMonFsmInstanceId }
    ::= { cucsSwEthLanFlowMonFsmTable 1 }

CucsSwEthLanFlowMonFsmEntry ::= SEQUENCE {
    cucsSwEthLanFlowMonFsmInstanceId                                 CucsManagedObjectId,
    cucsSwEthLanFlowMonFsmDn                                         CucsManagedObjectDn,
    cucsSwEthLanFlowMonFsmRn                                         SnmpAdminString,
    cucsSwEthLanFlowMonFsmCompletionTime                             DateAndTime,
    cucsSwEthLanFlowMonFsmCurrentFsm                                 CucsSwEthLanFlowMonFsmCurrentFsm,
    cucsSwEthLanFlowMonFsmDescrData                                  SnmpAdminString,
    cucsSwEthLanFlowMonFsmFsmStatus                                  CucsFsmFsmStageStatus,
    cucsSwEthLanFlowMonFsmProgress                                   Gauge32,
    cucsSwEthLanFlowMonFsmRmtErrCode                                 Gauge32,
    cucsSwEthLanFlowMonFsmRmtErrDescr                                SnmpAdminString,
    cucsSwEthLanFlowMonFsmRmtRslt                                    CucsConditionRemoteInvRslt
}

cucsSwEthLanFlowMonFsmInstanceId OBJECT-TYPE
    SYNTAX       CucsManagedObjectId
    MAX-ACCESS   not-accessible
    STATUS       current
    DESCRIPTION
        "Instance identifier of the managed object."
    ::= { cucsSwEthLanFlowMonFsmEntry 1 }

cucsSwEthLanFlowMonFsmDn OBJECT-TYPE
    SYNTAX       CucsManagedObjectDn
    MAX-ACCESS   read-only
    STATUS       current
    DESCRIPTION
        "Cisco UCS sw:EthLanFlowMonFsm:dn managed object property"
    ::= { cucsSwEthLanFlowMonFsmEntry 2 }

cucsSwEthLanFlowMonFsmRn OBJECT-TYPE
    SYNTAX       SnmpAdminString
    MAX-ACCESS   read-only
    STATUS       current
    DESCRIPTION
        "Cisco UCS sw:EthLanFlowMonFsm:rn managed object property"
    ::= { cucsSwEthLanFlowMonFsmEntry 3 }

cucsSwEthLanFlowMonFsmCompletionTime OBJECT-TYPE
    SYNTAX       DateAndTime
    MAX-ACCESS   read-only
    STATUS       current
    DESCRIPTION
        "Cisco UCS sw:EthLanFlowMonFsm:completionTime managed
        object property"
    ::= { cucsSwEthLanFlowMonFsmEntry 4 }

cucsSwEthLanFlowMonFsmCurrentFsm OBJECT-TYPE
    SYNTAX       CucsSwEthLanFlowMonFsmCurrentFsm
    MAX-ACCESS   read-only
    STATUS       current
    DESCRIPTION
        "Cisco UCS sw:EthLanFlowMonFsm:currentFsm managed object property"
    ::= { cucsSwEthLanFlowMonFsmEntry 5 }

cucsSwEthLanFlowMonFsmDescrData OBJECT-TYPE
    SYNTAX       SnmpAdminString
    MAX-ACCESS   read-only
    STATUS       current
    DESCRIPTION
        "Cisco UCS sw:EthLanFlowMonFsm:descr managed object property"
    ::= { cucsSwEthLanFlowMonFsmEntry 6 }

cucsSwEthLanFlowMonFsmFsmStatus OBJECT-TYPE
    SYNTAX       CucsFsmFsmStageStatus
    MAX-ACCESS   read-only
    STATUS       current
    DESCRIPTION
        "Cisco UCS sw:EthLanFlowMonFsm:fsmStatus managed object property"
    ::= { cucsSwEthLanFlowMonFsmEntry 7 }

cucsSwEthLanFlowMonFsmProgress OBJECT-TYPE
    SYNTAX       Gauge32
    MAX-ACCESS   read-only
    STATUS       current
    DESCRIPTION
        "Cisco UCS sw:EthLanFlowMonFsm:progress managed object property"
    ::= { cucsSwEthLanFlowMonFsmEntry 8 }

cucsSwEthLanFlowMonFsmRmtErrCode OBJECT-TYPE
    SYNTAX       Gauge32
    MAX-ACCESS   read-only
    STATUS       current
    DESCRIPTION
        "Cisco UCS sw:EthLanFlowMonFsm:rmtErrCode managed object property"
    ::= { cucsSwEthLanFlowMonFsmEntry 9 }

cucsSwEthLanFlowMonFsmRmtErrDescr OBJECT-TYPE
    SYNTAX       SnmpAdminString
    MAX-ACCESS   read-only
    STATUS       current
    DESCRIPTION
        "Cisco UCS sw:EthLanFlowMonFsm:rmtErrDescr managed
        object property"
    ::= { cucsSwEthLanFlowMonFsmEntry 10 }

cucsSwEthLanFlowMonFsmRmtRslt OBJECT-TYPE
    SYNTAX       CucsConditionRemoteInvRslt
    MAX-ACCESS   read-only
    STATUS       current
    DESCRIPTION
        "Cisco UCS sw:EthLanFlowMonFsm:rmtRslt managed object property"
    ::= { cucsSwEthLanFlowMonFsmEntry 11 }

cucsSwEthLanFlowMonFsmStageTable OBJECT-TYPE
    SYNTAX           SEQUENCE OF CucsSwEthLanFlowMonFsmStageEntry
    MAX-ACCESS       not-accessible
    STATUS           current
    DESCRIPTION
        "Cisco UCS sw:EthLanFlowMonFsmStage managed object table"
    ::= { cucsSwObjects 72 }

cucsSwEthLanFlowMonFsmStageEntry OBJECT-TYPE
    SYNTAX           CucsSwEthLanFlowMonFsmStageEntry
    MAX-ACCESS       not-accessible
    STATUS           current
    DESCRIPTION
        "Entry for the cucsSwEthLanFlowMonFsmStageTable table."
    INDEX { cucsSwEthLanFlowMonFsmStageInstanceId }
    ::= { cucsSwEthLanFlowMonFsmStageTable 1 }

CucsSwEthLanFlowMonFsmStageEntry ::= SEQUENCE {
    cucsSwEthLanFlowMonFsmStageInstanceId                            CucsManagedObjectId,
    cucsSwEthLanFlowMonFsmStageDn                                    CucsManagedObjectDn,
    cucsSwEthLanFlowMonFsmStageRn                                    SnmpAdminString,
    cucsSwEthLanFlowMonFsmStageDescrData                             SnmpAdminString,
    cucsSwEthLanFlowMonFsmStageLastUpdateTime                        DateAndTime,
    cucsSwEthLanFlowMonFsmStageName                                  CucsSwEthLanFlowMonFsmStageName,
    cucsSwEthLanFlowMonFsmStageOrder                                 Gauge32,
    cucsSwEthLanFlowMonFsmStageRetry                                 Gauge32,
    cucsSwEthLanFlowMonFsmStageStageStatus                           CucsFsmFsmStageStatus
}

cucsSwEthLanFlowMonFsmStageInstanceId OBJECT-TYPE
    SYNTAX       CucsManagedObjectId
    MAX-ACCESS   not-accessible
    STATUS       current
    DESCRIPTION
        "Instance identifier of the managed object."
    ::= { cucsSwEthLanFlowMonFsmStageEntry 1 }

cucsSwEthLanFlowMonFsmStageDn OBJECT-TYPE
    SYNTAX       CucsManagedObjectDn
    MAX-ACCESS   read-only
    STATUS       current
    DESCRIPTION
        "Cisco UCS sw:EthLanFlowMonFsmStage:dn managed object property"
    ::= { cucsSwEthLanFlowMonFsmStageEntry 2 }

cucsSwEthLanFlowMonFsmStageRn OBJECT-TYPE
    SYNTAX       SnmpAdminString
    MAX-ACCESS   read-only
    STATUS       current
    DESCRIPTION
        "Cisco UCS sw:EthLanFlowMonFsmStage:rn managed object property"
    ::= { cucsSwEthLanFlowMonFsmStageEntry 3 }

cucsSwEthLanFlowMonFsmStageDescrData OBJECT-TYPE
    SYNTAX       SnmpAdminString
    MAX-ACCESS   read-only
    STATUS       current
    DESCRIPTION
        "Cisco UCS sw:EthLanFlowMonFsmStage:descr managed object property"
    ::= { cucsSwEthLanFlowMonFsmStageEntry 4 }

cucsSwEthLanFlowMonFsmStageLastUpdateTime OBJECT-TYPE
    SYNTAX       DateAndTime
    MAX-ACCESS   read-only
    STATUS       current
    DESCRIPTION
        "Cisco UCS sw:EthLanFlowMonFsmStage:lastUpdateTime
        managed object property"
    ::= { cucsSwEthLanFlowMonFsmStageEntry 5 }

cucsSwEthLanFlowMonFsmStageName OBJECT-TYPE
    SYNTAX       CucsSwEthLanFlowMonFsmStageName
    MAX-ACCESS   read-only
    STATUS       current
    DESCRIPTION
        "Cisco UCS sw:EthLanFlowMonFsmStage:name managed object property"
    ::= { cucsSwEthLanFlowMonFsmStageEntry 6 }

cucsSwEthLanFlowMonFsmStageOrder OBJECT-TYPE
    SYNTAX       Gauge32
    MAX-ACCESS   read-only
    STATUS       current
    DESCRIPTION
        "Cisco UCS sw:EthLanFlowMonFsmStage:order managed object property"
    ::= { cucsSwEthLanFlowMonFsmStageEntry 7 }

cucsSwEthLanFlowMonFsmStageRetry OBJECT-TYPE
    SYNTAX       Gauge32
    MAX-ACCESS   read-only
    STATUS       current
    DESCRIPTION
        "Cisco UCS sw:EthLanFlowMonFsmStage:retry managed object property"
    ::= { cucsSwEthLanFlowMonFsmStageEntry 8 }

cucsSwEthLanFlowMonFsmStageStageStatus OBJECT-TYPE
    SYNTAX       CucsFsmFsmStageStatus
    MAX-ACCESS   read-only
    STATUS       current
    DESCRIPTION
        "Cisco UCS sw:EthLanFlowMonFsmStage:stageStatus
        managed object property"
    ::= { cucsSwEthLanFlowMonFsmStageEntry 9 }

cucsSwEthLanFlowMonFsmTaskTable OBJECT-TYPE
    SYNTAX           SEQUENCE OF CucsSwEthLanFlowMonFsmTaskEntry
    MAX-ACCESS       not-accessible
    STATUS           current
    DESCRIPTION
        "Cisco UCS sw:EthLanFlowMonFsmTask managed object table"
    ::= { cucsSwObjects 73 }

cucsSwEthLanFlowMonFsmTaskEntry OBJECT-TYPE
    SYNTAX           CucsSwEthLanFlowMonFsmTaskEntry
    MAX-ACCESS       not-accessible
    STATUS           current
    DESCRIPTION
        "Entry for the cucsSwEthLanFlowMonFsmTaskTable table."
    INDEX { cucsSwEthLanFlowMonFsmTaskInstanceId }
    ::= { cucsSwEthLanFlowMonFsmTaskTable 1 }

CucsSwEthLanFlowMonFsmTaskEntry ::= SEQUENCE {
    cucsSwEthLanFlowMonFsmTaskInstanceId                             CucsManagedObjectId,
    cucsSwEthLanFlowMonFsmTaskDn                                     CucsManagedObjectDn,
    cucsSwEthLanFlowMonFsmTaskRn                                     SnmpAdminString,
    cucsSwEthLanFlowMonFsmTaskCompletion                             CucsFsmCompletion,
    cucsSwEthLanFlowMonFsmTaskFlags                                  CucsFsmFlags,
    cucsSwEthLanFlowMonFsmTaskItem                                   CucsSwEthLanFlowMonFsmTaskItem,
    cucsSwEthLanFlowMonFsmTaskSeqId                                  Gauge32
}

cucsSwEthLanFlowMonFsmTaskInstanceId OBJECT-TYPE
    SYNTAX       CucsManagedObjectId
    MAX-ACCESS   not-accessible
    STATUS       current
    DESCRIPTION
        "Instance identifier of the managed object."
    ::= { cucsSwEthLanFlowMonFsmTaskEntry 1 }

cucsSwEthLanFlowMonFsmTaskDn OBJECT-TYPE
    SYNTAX       CucsManagedObjectDn
    MAX-ACCESS   read-only
    STATUS       current
    DESCRIPTION
        "Cisco UCS sw:EthLanFlowMonFsmTask:dn managed object property"
    ::= { cucsSwEthLanFlowMonFsmTaskEntry 2 }

cucsSwEthLanFlowMonFsmTaskRn OBJECT-TYPE
    SYNTAX       SnmpAdminString
    MAX-ACCESS   read-only
    STATUS       current
    DESCRIPTION
        "Cisco UCS sw:EthLanFlowMonFsmTask:rn managed object property"
    ::= { cucsSwEthLanFlowMonFsmTaskEntry 3 }

cucsSwEthLanFlowMonFsmTaskCompletion OBJECT-TYPE
    SYNTAX       CucsFsmCompletion
    MAX-ACCESS   read-only
    STATUS       current
    DESCRIPTION
        "Cisco UCS sw:EthLanFlowMonFsmTask:completion managed
        object property"
    ::= { cucsSwEthLanFlowMonFsmTaskEntry 4 }

cucsSwEthLanFlowMonFsmTaskFlags OBJECT-TYPE
    SYNTAX       CucsFsmFlags
    MAX-ACCESS   read-only
    STATUS       current
    DESCRIPTION
        "Cisco UCS sw:EthLanFlowMonFsmTask:flags managed object property"
    ::= { cucsSwEthLanFlowMonFsmTaskEntry 5 }

cucsSwEthLanFlowMonFsmTaskItem OBJECT-TYPE
    SYNTAX       CucsSwEthLanFlowMonFsmTaskItem
    MAX-ACCESS   read-only
    STATUS       current
    DESCRIPTION
        "Cisco UCS sw:EthLanFlowMonFsmTask:item managed object property"
    ::= { cucsSwEthLanFlowMonFsmTaskEntry 6 }

cucsSwEthLanFlowMonFsmTaskSeqId OBJECT-TYPE
    SYNTAX       Gauge32
    MAX-ACCESS   read-only
    STATUS       current
    DESCRIPTION
        "Cisco UCS sw:EthLanFlowMonFsmTask:seqId managed object property"
    ::= { cucsSwEthLanFlowMonFsmTaskEntry 7 }

cucsSwEthLanMonTable OBJECT-TYPE
    SYNTAX           SEQUENCE OF CucsSwEthLanMonEntry
    MAX-ACCESS       not-accessible
    STATUS           current
    DESCRIPTION
        "Cisco UCS sw:EthLanMon managed object table"
    ::= { cucsSwObjects 10 }

cucsSwEthLanMonEntry OBJECT-TYPE
    SYNTAX           CucsSwEthLanMonEntry
    MAX-ACCESS       not-accessible
    STATUS           current
    DESCRIPTION
        "Entry for the cucsSwEthLanMonTable table."
    INDEX { cucsSwEthLanMonInstanceId }
    ::= { cucsSwEthLanMonTable 1 }

CucsSwEthLanMonEntry ::= SEQUENCE {
    cucsSwEthLanMonInstanceId                                        CucsManagedObjectId,
    cucsSwEthLanMonDn                                                CucsManagedObjectDn,
    cucsSwEthLanMonRn                                                SnmpAdminString,
    cucsSwEthLanMonLocale                                            CucsSwMonDomainLocale,
    cucsSwEthLanMonName                                              SnmpAdminString,
    cucsSwEthLanMonSwitchId                                          CucsNetworkSwitchId,
    cucsSwEthLanMonTransport                                         CucsSwEthLanMonTransport,
    cucsSwEthLanMonType                                              CucsSwLanMonType
}

cucsSwEthLanMonInstanceId OBJECT-TYPE
    SYNTAX       CucsManagedObjectId
    MAX-ACCESS   not-accessible
    STATUS       current
    DESCRIPTION
        "Instance identifier of the managed object."
    ::= { cucsSwEthLanMonEntry 1 }

cucsSwEthLanMonDn OBJECT-TYPE
    SYNTAX       CucsManagedObjectDn
    MAX-ACCESS   read-only
    STATUS       current
    DESCRIPTION
        "Cisco UCS sw:EthLanMon:dn managed object property"
    ::= { cucsSwEthLanMonEntry 2 }

cucsSwEthLanMonRn OBJECT-TYPE
    SYNTAX       SnmpAdminString
    MAX-ACCESS   read-only
    STATUS       current
    DESCRIPTION
        "Cisco UCS sw:EthLanMon:rn managed object property"
    ::= { cucsSwEthLanMonEntry 3 }

cucsSwEthLanMonLocale OBJECT-TYPE
    SYNTAX       CucsSwMonDomainLocale
    MAX-ACCESS   read-only
    STATUS       current
    DESCRIPTION
        "Cisco UCS sw:EthLanMon:locale managed object property"
    ::= { cucsSwEthLanMonEntry 4 }

cucsSwEthLanMonName OBJECT-TYPE
    SYNTAX       SnmpAdminString
    MAX-ACCESS   read-only
    STATUS       current
    DESCRIPTION
        "Cisco UCS sw:EthLanMon:name managed object property"
    ::= { cucsSwEthLanMonEntry 5 }

cucsSwEthLanMonSwitchId OBJECT-TYPE
    SYNTAX       CucsNetworkSwitchId
    MAX-ACCESS   read-only
    STATUS       current
    DESCRIPTION
        "Cisco UCS sw:EthLanMon:switchId managed object property"
    ::= { cucsSwEthLanMonEntry 6 }

cucsSwEthLanMonTransport OBJECT-TYPE
    SYNTAX       CucsSwEthLanMonTransport
    MAX-ACCESS   read-only
    STATUS       current
    DESCRIPTION
        "Cisco UCS sw:EthLanMon:transport managed object property"
    ::= { cucsSwEthLanMonEntry 7 }

cucsSwEthLanMonType OBJECT-TYPE
    SYNTAX       CucsSwLanMonType
    MAX-ACCESS   read-only
    STATUS       current
    DESCRIPTION
        "Cisco UCS sw:EthLanMon:type managed object property"
    ::= { cucsSwEthLanMonEntry 8 }

cucsSwEthLanPcTable OBJECT-TYPE
    SYNTAX           SEQUENCE OF CucsSwEthLanPcEntry
    MAX-ACCESS       not-accessible
    STATUS           current
    DESCRIPTION
        "Cisco UCS sw:EthLanPc managed object table"
    ::= { cucsSwObjects 11 }

cucsSwEthLanPcEntry OBJECT-TYPE
    SYNTAX           CucsSwEthLanPcEntry
    MAX-ACCESS       not-accessible
    STATUS           current
    DESCRIPTION
        "Entry for the cucsSwEthLanPcTable table."
    INDEX { cucsSwEthLanPcInstanceId }
    ::= { cucsSwEthLanPcTable 1 }

CucsSwEthLanPcEntry ::= SEQUENCE {
    cucsSwEthLanPcInstanceId                                         CucsManagedObjectId,
    cucsSwEthLanPcDn                                                 CucsManagedObjectDn,
    cucsSwEthLanPcRn                                                 SnmpAdminString,
    cucsSwEthLanPcAdminSpeed                                         CucsPortEthSpeed,
    cucsSwEthLanPcAdminState                                         CucsFabricAdminState,
    cucsSwEthLanPcEpDn                                               SnmpAdminString,
    cucsSwEthLanPcIfRole                                             CucsSwLanPcIfRole,
    cucsSwEthLanPcIfType                                             CucsSwCIoEpIfType,
    cucsSwEthLanPcLocale                                             CucsSwBorderPcLocale,
    cucsSwEthLanPcName                                               SnmpAdminString,
    cucsSwEthLanPcPeerDn                                             SnmpAdminString,
    cucsSwEthLanPcPortId                                             Gauge32,
    cucsSwEthLanPcPriorityFlowCtrl                                   CucsFlowctrlPriorityPause,
    cucsSwEthLanPcRecvFlowCtrl                                       CucsFlowctrlFlowControl,
    cucsSwEthLanPcSendFlowCtrl                                       CucsFlowctrlFlowControl,
    cucsSwEthLanPcSwitchId                                           CucsNetworkSwitchId,
    cucsSwEthLanPcTransport                                          CucsSwEthLanPcTransport,
    cucsSwEthLanPcType                                               CucsSwLanPcType,
    cucsSwEthLanPcMonTrafDir                                         CucsFabricTrafficDirection,
    cucsSwEthLanPcLacpFastTimer                                      TruthValue,
    cucsSwEthLanPcLacpSuspendIndividual                              TruthValue
}

cucsSwEthLanPcInstanceId OBJECT-TYPE
    SYNTAX       CucsManagedObjectId
    MAX-ACCESS   not-accessible
    STATUS       current
    DESCRIPTION
        "Instance identifier of the managed object."
    ::= { cucsSwEthLanPcEntry 1 }

cucsSwEthLanPcDn OBJECT-TYPE
    SYNTAX       CucsManagedObjectDn
    MAX-ACCESS   read-only
    STATUS       current
    DESCRIPTION
        "Cisco UCS sw:EthLanPc:dn managed object property"
    ::= { cucsSwEthLanPcEntry 2 }

cucsSwEthLanPcRn OBJECT-TYPE
    SYNTAX       SnmpAdminString
    MAX-ACCESS   read-only
    STATUS       current
    DESCRIPTION
        "Cisco UCS sw:EthLanPc:rn managed object property"
    ::= { cucsSwEthLanPcEntry 3 }

cucsSwEthLanPcAdminSpeed OBJECT-TYPE
    SYNTAX       CucsPortEthSpeed
    MAX-ACCESS   read-only
    STATUS       current
    DESCRIPTION
        "Cisco UCS sw:EthLanPc:adminSpeed managed object property"
    ::= { cucsSwEthLanPcEntry 4 }

cucsSwEthLanPcAdminState OBJECT-TYPE
    SYNTAX       CucsFabricAdminState
    MAX-ACCESS   read-only
    STATUS       current
    DESCRIPTION
        "Cisco UCS sw:EthLanPc:adminState managed object property"
    ::= { cucsSwEthLanPcEntry 5 }

cucsSwEthLanPcEpDn OBJECT-TYPE
    SYNTAX       SnmpAdminString
    MAX-ACCESS   read-only
    STATUS       current
    DESCRIPTION
        "Cisco UCS sw:EthLanPc:epDn managed object property"
    ::= { cucsSwEthLanPcEntry 6 }

cucsSwEthLanPcIfRole OBJECT-TYPE
    SYNTAX       CucsSwLanPcIfRole
    MAX-ACCESS   read-only
    STATUS       current
    DESCRIPTION
        "Cisco UCS sw:EthLanPc:ifRole managed object property"
    ::= { cucsSwEthLanPcEntry 7 }

cucsSwEthLanPcIfType OBJECT-TYPE
    SYNTAX       CucsSwCIoEpIfType
    MAX-ACCESS   read-only
    STATUS       current
    DESCRIPTION
        "Cisco UCS sw:EthLanPc:ifType managed object property"
    ::= { cucsSwEthLanPcEntry 8 }

cucsSwEthLanPcLocale OBJECT-TYPE
    SYNTAX       CucsSwBorderPcLocale
    MAX-ACCESS   read-only
    STATUS       current
    DESCRIPTION
        "Cisco UCS sw:EthLanPc:locale managed object property"
    ::= { cucsSwEthLanPcEntry 9 }

cucsSwEthLanPcName OBJECT-TYPE
    SYNTAX       SnmpAdminString
    MAX-ACCESS   read-only
    STATUS       current
    DESCRIPTION
        "Cisco UCS sw:EthLanPc:name managed object property"
    ::= { cucsSwEthLanPcEntry 10 }

cucsSwEthLanPcPeerDn OBJECT-TYPE
    SYNTAX       SnmpAdminString
    MAX-ACCESS   read-only
    STATUS       current
    DESCRIPTION
        "Cisco UCS sw:EthLanPc:peerDn managed object property"
    ::= { cucsSwEthLanPcEntry 11 }

cucsSwEthLanPcPortId OBJECT-TYPE
    SYNTAX       Gauge32
    MAX-ACCESS   read-only
    STATUS       current
    DESCRIPTION
        "Cisco UCS sw:EthLanPc:portId managed object property"
    ::= { cucsSwEthLanPcEntry 12 }

cucsSwEthLanPcPriorityFlowCtrl OBJECT-TYPE
    SYNTAX       CucsFlowctrlPriorityPause
    MAX-ACCESS   read-only
    STATUS       current
    DESCRIPTION
        "Cisco UCS sw:EthLanPc:priorityFlowCtrl managed object property"
    ::= { cucsSwEthLanPcEntry 13 }

cucsSwEthLanPcRecvFlowCtrl OBJECT-TYPE
    SYNTAX       CucsFlowctrlFlowControl
    MAX-ACCESS   read-only
    STATUS       current
    DESCRIPTION
        "Cisco UCS sw:EthLanPc:recvFlowCtrl managed object property"
    ::= { cucsSwEthLanPcEntry 14 }

cucsSwEthLanPcSendFlowCtrl OBJECT-TYPE
    SYNTAX       CucsFlowctrlFlowControl
    MAX-ACCESS   read-only
    STATUS       current
    DESCRIPTION
        "Cisco UCS sw:EthLanPc:sendFlowCtrl managed object property"
    ::= { cucsSwEthLanPcEntry 15 }

cucsSwEthLanPcSwitchId OBJECT-TYPE
    SYNTAX       CucsNetworkSwitchId
    MAX-ACCESS   read-only
    STATUS       current
    DESCRIPTION
        "Cisco UCS sw:EthLanPc:switchId managed object property"
    ::= { cucsSwEthLanPcEntry 16 }

cucsSwEthLanPcTransport OBJECT-TYPE
    SYNTAX       CucsSwEthLanPcTransport
    MAX-ACCESS   read-only
    STATUS       current
    DESCRIPTION
        "Cisco UCS sw:EthLanPc:transport managed object property"
    ::= { cucsSwEthLanPcEntry 17 }

cucsSwEthLanPcType OBJECT-TYPE
    SYNTAX       CucsSwLanPcType
    MAX-ACCESS   read-only
    STATUS       current
    DESCRIPTION
        "Cisco UCS sw:EthLanPc:type managed object property"
    ::= { cucsSwEthLanPcEntry 18 }

cucsSwEthLanPcMonTrafDir OBJECT-TYPE
    SYNTAX       CucsFabricTrafficDirection
    MAX-ACCESS   read-only
    STATUS       current
    DESCRIPTION
        "Cisco UCS sw:EthLanPc:monTrafDir managed object property"
    ::= { cucsSwEthLanPcEntry 19 }

cucsSwEthLanPcLacpFastTimer OBJECT-TYPE
    SYNTAX       TruthValue
    MAX-ACCESS   read-only
    STATUS       current
    DESCRIPTION
        "Cisco UCS sw:EthLanPc:lacpFastTimer managed object property"
    ::= { cucsSwEthLanPcEntry 21 }

cucsSwEthLanPcLacpSuspendIndividual OBJECT-TYPE
    SYNTAX       TruthValue
    MAX-ACCESS   read-only
    STATUS       current
    DESCRIPTION
        "Cisco UCS sw:EthLanPc:lacpSuspendIndividual managed
        object property"
    ::= { cucsSwEthLanPcEntry 22 }

cucsSwEthMonTable OBJECT-TYPE
    SYNTAX           SEQUENCE OF CucsSwEthMonEntry
    MAX-ACCESS       not-accessible
    STATUS           current
    DESCRIPTION
        "Cisco UCS sw:EthMon managed object table"
    ::= { cucsSwObjects 12 }

cucsSwEthMonEntry OBJECT-TYPE
    SYNTAX           CucsSwEthMonEntry
    MAX-ACCESS       not-accessible
    STATUS           current
    DESCRIPTION
        "Entry for the cucsSwEthMonTable table."
    INDEX { cucsSwEthMonInstanceId }
    ::= { cucsSwEthMonTable 1 }

CucsSwEthMonEntry ::= SEQUENCE {
    cucsSwEthMonInstanceId                                           CucsManagedObjectId,
    cucsSwEthMonDn                                                   CucsManagedObjectDn,
    cucsSwEthMonRn                                                   SnmpAdminString,
    cucsSwEthMonAdminState                                           CucsSwMonAdminState,
    cucsSwEthMonFsmDescr                                             SnmpAdminString,
    cucsSwEthMonFsmPrev                                              SnmpAdminString,
    cucsSwEthMonFsmProgr                                             Gauge32,
    cucsSwEthMonFsmRmtInvErrCode                                     Gauge32,
    cucsSwEthMonFsmRmtInvErrDescr                                    SnmpAdminString,
    cucsSwEthMonFsmRmtInvRslt                                        CucsConditionRemoteInvRslt,
    cucsSwEthMonFsmStageDescr                                        SnmpAdminString,
    cucsSwEthMonFsmStamp                                             DateAndTime,
    cucsSwEthMonFsmStatus                                            SnmpAdminString,
    cucsSwEthMonFsmTry                                               Gauge32,
    cucsSwEthMonLifeCycle                                            CucsSwMonLifeCycle,
    cucsSwEthMonName                                                 SnmpAdminString,
    cucsSwEthMonSession                                              Gauge32,
    cucsSwEthMonSwitchId                                             CucsNetworkSwitchId,
    cucsSwEthMonTransport                                            CucsSwEthMonTransport,
    cucsSwEthMonType                                                 CucsSwEthMonType,
    cucsSwEthMonHasLastDest                                          TruthValue,
    cucsSwEthMonPeerDn                                               SnmpAdminString
}

cucsSwEthMonInstanceId OBJECT-TYPE
    SYNTAX       CucsManagedObjectId
    MAX-ACCESS   not-accessible
    STATUS       current
    DESCRIPTION
        "Instance identifier of the managed object."
    ::= { cucsSwEthMonEntry 1 }

cucsSwEthMonDn OBJECT-TYPE
    SYNTAX       CucsManagedObjectDn
    MAX-ACCESS   read-only
    STATUS       current
    DESCRIPTION
        "Cisco UCS sw:EthMon:dn managed object property"
    ::= { cucsSwEthMonEntry 2 }

cucsSwEthMonRn OBJECT-TYPE
    SYNTAX       SnmpAdminString
    MAX-ACCESS   read-only
    STATUS       current
    DESCRIPTION
        "Cisco UCS sw:EthMon:rn managed object property"
    ::= { cucsSwEthMonEntry 3 }

cucsSwEthMonAdminState OBJECT-TYPE
    SYNTAX       CucsSwMonAdminState
    MAX-ACCESS   read-only
    STATUS       current
    DESCRIPTION
        "Cisco UCS sw:EthMon:adminState managed object property"
    ::= { cucsSwEthMonEntry 4 }

cucsSwEthMonFsmDescr OBJECT-TYPE
    SYNTAX       SnmpAdminString
    MAX-ACCESS   read-only
    STATUS       current
    DESCRIPTION
        "Cisco UCS sw:EthMon:fsmDescr managed object property"
    ::= { cucsSwEthMonEntry 5 }

cucsSwEthMonFsmPrev OBJECT-TYPE
    SYNTAX       SnmpAdminString
    MAX-ACCESS   read-only
    STATUS       current
    DESCRIPTION
        "Cisco UCS sw:EthMon:fsmPrev managed object property"
    ::= { cucsSwEthMonEntry 6 }

cucsSwEthMonFsmProgr OBJECT-TYPE
    SYNTAX       Gauge32
    MAX-ACCESS   read-only
    STATUS       current
    DESCRIPTION
        "Cisco UCS sw:EthMon:fsmProgr managed object property"
    ::= { cucsSwEthMonEntry 7 }

cucsSwEthMonFsmRmtInvErrCode OBJECT-TYPE
    SYNTAX       Gauge32
    MAX-ACCESS   read-only
    STATUS       current
    DESCRIPTION
        "Cisco UCS sw:EthMon:fsmRmtInvErrCode managed object property"
    ::= { cucsSwEthMonEntry 8 }

cucsSwEthMonFsmRmtInvErrDescr OBJECT-TYPE
    SYNTAX       SnmpAdminString
    MAX-ACCESS   read-only
    STATUS       current
    DESCRIPTION
        "Cisco UCS sw:EthMon:fsmRmtInvErrDescr managed object property"
    ::= { cucsSwEthMonEntry 9 }

cucsSwEthMonFsmRmtInvRslt OBJECT-TYPE
    SYNTAX       CucsConditionRemoteInvRslt
    MAX-ACCESS   read-only
    STATUS       current
    DESCRIPTION
        "Cisco UCS sw:EthMon:fsmRmtInvRslt managed object property"
    ::= { cucsSwEthMonEntry 10 }

cucsSwEthMonFsmStageDescr OBJECT-TYPE
    SYNTAX       SnmpAdminString
    MAX-ACCESS   read-only
    STATUS       current
    DESCRIPTION
        "Cisco UCS sw:EthMon:fsmStageDescr managed object property"
    ::= { cucsSwEthMonEntry 11 }

cucsSwEthMonFsmStamp OBJECT-TYPE
    SYNTAX       DateAndTime
    MAX-ACCESS   read-only
    STATUS       current
    DESCRIPTION
        "Cisco UCS sw:EthMon:fsmStamp managed object property"
    ::= { cucsSwEthMonEntry 12 }

cucsSwEthMonFsmStatus OBJECT-TYPE
    SYNTAX       SnmpAdminString
    MAX-ACCESS   read-only
    STATUS       current
    DESCRIPTION
        "Cisco UCS sw:EthMon:fsmStatus managed object property"
    ::= { cucsSwEthMonEntry 13 }

cucsSwEthMonFsmTry OBJECT-TYPE
    SYNTAX       Gauge32
    MAX-ACCESS   read-only
    STATUS       current
    DESCRIPTION
        "Cisco UCS sw:EthMon:fsmTry managed object property"
    ::= { cucsSwEthMonEntry 14 }

cucsSwEthMonLifeCycle OBJECT-TYPE
    SYNTAX       CucsSwMonLifeCycle
    MAX-ACCESS   read-only
    STATUS       current
    DESCRIPTION
        "Cisco UCS sw:EthMon:lifeCycle managed object property"
    ::= { cucsSwEthMonEntry 15 }

cucsSwEthMonName OBJECT-TYPE
    SYNTAX       SnmpAdminString
    MAX-ACCESS   read-only
    STATUS       current
    DESCRIPTION
        "Cisco UCS sw:EthMon:name managed object property"
    ::= { cucsSwEthMonEntry 16 }

cucsSwEthMonSession OBJECT-TYPE
    SYNTAX       Gauge32
    MAX-ACCESS   read-only
    STATUS       current
    DESCRIPTION
        "Cisco UCS sw:EthMon:session managed object property"
    ::= { cucsSwEthMonEntry 17 }

cucsSwEthMonSwitchId OBJECT-TYPE
    SYNTAX       CucsNetworkSwitchId
    MAX-ACCESS   read-only
    STATUS       current
    DESCRIPTION
        "Cisco UCS sw:EthMon:switchId managed object property"
    ::= { cucsSwEthMonEntry 18 }

cucsSwEthMonTransport OBJECT-TYPE
    SYNTAX       CucsSwEthMonTransport
    MAX-ACCESS   read-only
    STATUS       current
    DESCRIPTION
        "Cisco UCS sw:EthMon:transport managed object property"
    ::= { cucsSwEthMonEntry 19 }

cucsSwEthMonType OBJECT-TYPE
    SYNTAX       CucsSwEthMonType
    MAX-ACCESS   read-only
    STATUS       current
    DESCRIPTION
        "Cisco UCS sw:EthMon:type managed object property"
    ::= { cucsSwEthMonEntry 20 }

cucsSwEthMonHasLastDest OBJECT-TYPE
    SYNTAX       TruthValue
    MAX-ACCESS   read-only
    STATUS       current
    DESCRIPTION
        "Cisco UCS sw:EthMon:hasLastDest managed object property"
    ::= { cucsSwEthMonEntry 21 }

cucsSwEthMonPeerDn OBJECT-TYPE
    SYNTAX       SnmpAdminString
    MAX-ACCESS   read-only
    STATUS       current
    DESCRIPTION
        "Cisco UCS sw:EthMon:peerDn managed object property"
    ::= { cucsSwEthMonEntry 22 }

cucsSwEthMonDestEpTable OBJECT-TYPE
    SYNTAX           SEQUENCE OF CucsSwEthMonDestEpEntry
    MAX-ACCESS       not-accessible
    STATUS           current
    DESCRIPTION
        "Cisco UCS sw:EthMonDestEp managed object table"
    ::= { cucsSwObjects 13 }

cucsSwEthMonDestEpEntry OBJECT-TYPE
    SYNTAX           CucsSwEthMonDestEpEntry
    MAX-ACCESS       not-accessible
    STATUS           current
    DESCRIPTION
        "Entry for the cucsSwEthMonDestEpTable table."
    INDEX { cucsSwEthMonDestEpInstanceId }
    ::= { cucsSwEthMonDestEpTable 1 }

CucsSwEthMonDestEpEntry ::= SEQUENCE {
    cucsSwEthMonDestEpInstanceId                                     CucsManagedObjectId,
    cucsSwEthMonDestEpDn                                             CucsManagedObjectDn,
    cucsSwEthMonDestEpRn                                             SnmpAdminString,
    cucsSwEthMonDestEpAdminState                                     CucsFabricAdminState,
    cucsSwEthMonDestEpChassisId                                      Gauge32,
    cucsSwEthMonDestEpEpDn                                           SnmpAdminString,
    cucsSwEthMonDestEpIfRole                                         CucsNetworkPortRole,
    cucsSwEthMonDestEpIfType                                         CucsSwPIoEpIfType,
    cucsSwEthMonDestEpLocale                                         CucsNetworkLocale,
    cucsSwEthMonDestEpName                                           SnmpAdminString,
    cucsSwEthMonDestEpPeerDn                                         SnmpAdminString,
    cucsSwEthMonDestEpPeerPortId                                     Gauge32,
    cucsSwEthMonDestEpPeerSlotId                                     Gauge32,
    cucsSwEthMonDestEpPortId                                         Gauge32,
    cucsSwEthMonDestEpSlotId                                         Gauge32,
    cucsSwEthMonDestEpSwitchId                                       CucsNetworkSwitchId,
    cucsSwEthMonDestEpTransport                                      CucsSwEthMonDestEpTransport,
    cucsSwEthMonDestEpType                                           CucsNetworkConnectionType,
    cucsSwEthMonDestEpPeerChassisId                                  Gauge32,
    cucsSwEthMonDestEpLc                                             CucsSwPIoEpLc,
    cucsSwEthMonDestEpAdminSpeed                                     CucsPortEthSpeed,
    cucsSwEthMonDestEpAggrPortId                                     Gauge32,
    cucsSwEthMonDestEpPeerAggrPortId                                 Gauge32
}

cucsSwEthMonDestEpInstanceId OBJECT-TYPE
    SYNTAX       CucsManagedObjectId
    MAX-ACCESS   not-accessible
    STATUS       current
    DESCRIPTION
        "Instance identifier of the managed object."
    ::= { cucsSwEthMonDestEpEntry 1 }

cucsSwEthMonDestEpDn OBJECT-TYPE
    SYNTAX       CucsManagedObjectDn
    MAX-ACCESS   read-only
    STATUS       current
    DESCRIPTION
        "Cisco UCS sw:EthMonDestEp:dn managed object property"
    ::= { cucsSwEthMonDestEpEntry 2 }

cucsSwEthMonDestEpRn OBJECT-TYPE
    SYNTAX       SnmpAdminString
    MAX-ACCESS   read-only
    STATUS       current
    DESCRIPTION
        "Cisco UCS sw:EthMonDestEp:rn managed object property"
    ::= { cucsSwEthMonDestEpEntry 3 }

cucsSwEthMonDestEpAdminState OBJECT-TYPE
    SYNTAX       CucsFabricAdminState
    MAX-ACCESS   read-only
    STATUS       current
    DESCRIPTION
        "Cisco UCS sw:EthMonDestEp:adminState managed object property"
    ::= { cucsSwEthMonDestEpEntry 4 }

cucsSwEthMonDestEpChassisId OBJECT-TYPE
    SYNTAX       Gauge32
    MAX-ACCESS   read-only
    STATUS       current
    DESCRIPTION
        "Cisco UCS sw:EthMonDestEp:chassisId managed object property"
    ::= { cucsSwEthMonDestEpEntry 5 }

cucsSwEthMonDestEpEpDn OBJECT-TYPE
    SYNTAX       SnmpAdminString
    MAX-ACCESS   read-only
    STATUS       current
    DESCRIPTION
        "Cisco UCS sw:EthMonDestEp:epDn managed object property"
    ::= { cucsSwEthMonDestEpEntry 6 }

cucsSwEthMonDestEpIfRole OBJECT-TYPE
    SYNTAX       CucsNetworkPortRole
    MAX-ACCESS   read-only
    STATUS       current
    DESCRIPTION
        "Cisco UCS sw:EthMonDestEp:ifRole managed object property"
    ::= { cucsSwEthMonDestEpEntry 7 }

cucsSwEthMonDestEpIfType OBJECT-TYPE
    SYNTAX       CucsSwPIoEpIfType
    MAX-ACCESS   read-only
    STATUS       current
    DESCRIPTION
        "Cisco UCS sw:EthMonDestEp:ifType managed object property"
    ::= { cucsSwEthMonDestEpEntry 8 }

cucsSwEthMonDestEpLocale OBJECT-TYPE
    SYNTAX       CucsNetworkLocale
    MAX-ACCESS   read-only
    STATUS       current
    DESCRIPTION
        "Cisco UCS sw:EthMonDestEp:locale managed object property"
    ::= { cucsSwEthMonDestEpEntry 9 }

cucsSwEthMonDestEpName OBJECT-TYPE
    SYNTAX       SnmpAdminString
    MAX-ACCESS   read-only
    STATUS       current
    DESCRIPTION
        "Cisco UCS sw:EthMonDestEp:name managed object property"
    ::= { cucsSwEthMonDestEpEntry 10 }

cucsSwEthMonDestEpPeerDn OBJECT-TYPE
    SYNTAX       SnmpAdminString
    MAX-ACCESS   read-only
    STATUS       current
    DESCRIPTION
        "Cisco UCS sw:EthMonDestEp:peerDn managed object property"
    ::= { cucsSwEthMonDestEpEntry 11 }

cucsSwEthMonDestEpPeerPortId OBJECT-TYPE
    SYNTAX       Gauge32
    MAX-ACCESS   read-only
    STATUS       current
    DESCRIPTION
        "Cisco UCS sw:EthMonDestEp:peerPortId managed object property"
    ::= { cucsSwEthMonDestEpEntry 12 }

cucsSwEthMonDestEpPeerSlotId OBJECT-TYPE
    SYNTAX       Gauge32
    MAX-ACCESS   read-only
    STATUS       current
    DESCRIPTION
        "Cisco UCS sw:EthMonDestEp:peerSlotId managed object property"
    ::= { cucsSwEthMonDestEpEntry 13 }

cucsSwEthMonDestEpPortId OBJECT-TYPE
    SYNTAX       Gauge32
    MAX-ACCESS   read-only
    STATUS       current
    DESCRIPTION
        "Cisco UCS sw:EthMonDestEp:portId managed object property"
    ::= { cucsSwEthMonDestEpEntry 14 }

cucsSwEthMonDestEpSlotId OBJECT-TYPE
    SYNTAX       Gauge32
    MAX-ACCESS   read-only
    STATUS       current
    DESCRIPTION
        "Cisco UCS sw:EthMonDestEp:slotId managed object property"
    ::= { cucsSwEthMonDestEpEntry 15 }

cucsSwEthMonDestEpSwitchId OBJECT-TYPE
    SYNTAX       CucsNetworkSwitchId
    MAX-ACCESS   read-only
    STATUS       current
    DESCRIPTION
        "Cisco UCS sw:EthMonDestEp:switchId managed object property"
    ::= { cucsSwEthMonDestEpEntry 16 }

cucsSwEthMonDestEpTransport OBJECT-TYPE
    SYNTAX       CucsSwEthMonDestEpTransport
    MAX-ACCESS   read-only
    STATUS       current
    DESCRIPTION
        "Cisco UCS sw:EthMonDestEp:transport managed object property"
    ::= { cucsSwEthMonDestEpEntry 17 }

cucsSwEthMonDestEpType OBJECT-TYPE
    SYNTAX       CucsNetworkConnectionType
    MAX-ACCESS   read-only
    STATUS       current
    DESCRIPTION
        "Cisco UCS sw:EthMonDestEp:type managed object property"
    ::= { cucsSwEthMonDestEpEntry 18 }

cucsSwEthMonDestEpPeerChassisId OBJECT-TYPE
    SYNTAX       Gauge32
    MAX-ACCESS   read-only
    STATUS       current
    DESCRIPTION
        "Cisco UCS sw:EthMonDestEp:peerChassisId managed object property"
    ::= { cucsSwEthMonDestEpEntry 19 }

cucsSwEthMonDestEpLc OBJECT-TYPE
    SYNTAX       CucsSwPIoEpLc
    MAX-ACCESS   read-only
    STATUS       current
    DESCRIPTION
        "Cisco UCS sw:EthMonDestEp:lc managed object property"
    ::= { cucsSwEthMonDestEpEntry 20 }

cucsSwEthMonDestEpAdminSpeed OBJECT-TYPE
    SYNTAX       CucsPortEthSpeed
    MAX-ACCESS   read-only
    STATUS       current
    DESCRIPTION
        "Cisco UCS sw:EthMonDestEp:adminSpeed managed object property"
    ::= { cucsSwEthMonDestEpEntry 21 }

cucsSwEthMonDestEpAggrPortId OBJECT-TYPE
    SYNTAX       Gauge32
    MAX-ACCESS   read-only
    STATUS       current
    DESCRIPTION
        "Cisco UCS sw:EthMonDestEp:aggrPortId managed object property"
    ::= { cucsSwEthMonDestEpEntry 22 }

cucsSwEthMonDestEpPeerAggrPortId OBJECT-TYPE
    SYNTAX       Gauge32
    MAX-ACCESS   read-only
    STATUS       current
    DESCRIPTION
        "Cisco UCS sw:EthMonDestEp:peerAggrPortId managed object property"
    ::= { cucsSwEthMonDestEpEntry 23 }

cucsSwEthMonFsmTable OBJECT-TYPE
    SYNTAX           SEQUENCE OF CucsSwEthMonFsmEntry
    MAX-ACCESS       not-accessible
    STATUS           current
    DESCRIPTION
        "Cisco UCS sw:EthMonFsm managed object table"
    ::= { cucsSwObjects 48 }

cucsSwEthMonFsmEntry OBJECT-TYPE
    SYNTAX           CucsSwEthMonFsmEntry
    MAX-ACCESS       not-accessible
    STATUS           current
    DESCRIPTION
        "Entry for the cucsSwEthMonFsmTable table."
    INDEX { cucsSwEthMonFsmInstanceId }
    ::= { cucsSwEthMonFsmTable 1 }

CucsSwEthMonFsmEntry ::= SEQUENCE {
    cucsSwEthMonFsmInstanceId                                        CucsManagedObjectId,
    cucsSwEthMonFsmDn                                                CucsManagedObjectDn,
    cucsSwEthMonFsmRn                                                SnmpAdminString,
    cucsSwEthMonFsmCompletionTime                                    DateAndTime,
    cucsSwEthMonFsmCurrentFsm                                        CucsSwEthMonFsmCurrentFsm,
    cucsSwEthMonFsmDescrData                                         SnmpAdminString,
    cucsSwEthMonFsmFsmStatus                                         CucsFsmFsmStageStatus,
    cucsSwEthMonFsmProgress                                          Gauge32,
    cucsSwEthMonFsmRmtErrCode                                        Gauge32,
    cucsSwEthMonFsmRmtErrDescr                                       SnmpAdminString,
    cucsSwEthMonFsmRmtRslt                                           CucsConditionRemoteInvRslt
}

cucsSwEthMonFsmInstanceId OBJECT-TYPE
    SYNTAX       CucsManagedObjectId
    MAX-ACCESS   not-accessible
    STATUS       current
    DESCRIPTION
        "Instance identifier of the managed object."
    ::= { cucsSwEthMonFsmEntry 1 }

cucsSwEthMonFsmDn OBJECT-TYPE
    SYNTAX       CucsManagedObjectDn
    MAX-ACCESS   read-only
    STATUS       current
    DESCRIPTION
        "Cisco UCS sw:EthMonFsm:dn managed object property"
    ::= { cucsSwEthMonFsmEntry 2 }

cucsSwEthMonFsmRn OBJECT-TYPE
    SYNTAX       SnmpAdminString
    MAX-ACCESS   read-only
    STATUS       current
    DESCRIPTION
        "Cisco UCS sw:EthMonFsm:rn managed object property"
    ::= { cucsSwEthMonFsmEntry 3 }

cucsSwEthMonFsmCompletionTime OBJECT-TYPE
    SYNTAX       DateAndTime
    MAX-ACCESS   read-only
    STATUS       current
    DESCRIPTION
        "Cisco UCS sw:EthMonFsm:completionTime managed object property"
    ::= { cucsSwEthMonFsmEntry 4 }

cucsSwEthMonFsmCurrentFsm OBJECT-TYPE
    SYNTAX       CucsSwEthMonFsmCurrentFsm
    MAX-ACCESS   read-only
    STATUS       current
    DESCRIPTION
        "Cisco UCS sw:EthMonFsm:currentFsm managed object property"
    ::= { cucsSwEthMonFsmEntry 5 }

cucsSwEthMonFsmDescrData OBJECT-TYPE
    SYNTAX       SnmpAdminString
    MAX-ACCESS   read-only
    STATUS       current
    DESCRIPTION
        "Cisco UCS sw:EthMonFsm:descr managed object property"
    ::= { cucsSwEthMonFsmEntry 6 }

cucsSwEthMonFsmFsmStatus OBJECT-TYPE
    SYNTAX       CucsFsmFsmStageStatus
    MAX-ACCESS   read-only
    STATUS       current
    DESCRIPTION
        "Cisco UCS sw:EthMonFsm:fsmStatus managed object property"
    ::= { cucsSwEthMonFsmEntry 7 }

cucsSwEthMonFsmProgress OBJECT-TYPE
    SYNTAX       Gauge32
    MAX-ACCESS   read-only
    STATUS       current
    DESCRIPTION
        "Cisco UCS sw:EthMonFsm:progress managed object property"
    ::= { cucsSwEthMonFsmEntry 8 }

cucsSwEthMonFsmRmtErrCode OBJECT-TYPE
    SYNTAX       Gauge32
    MAX-ACCESS   read-only
    STATUS       current
    DESCRIPTION
        "Cisco UCS sw:EthMonFsm:rmtErrCode managed object property"
    ::= { cucsSwEthMonFsmEntry 9 }

cucsSwEthMonFsmRmtErrDescr OBJECT-TYPE
    SYNTAX       SnmpAdminString
    MAX-ACCESS   read-only
    STATUS       current
    DESCRIPTION
        "Cisco UCS sw:EthMonFsm:rmtErrDescr managed object property"
    ::= { cucsSwEthMonFsmEntry 10 }

cucsSwEthMonFsmRmtRslt OBJECT-TYPE
    SYNTAX       CucsConditionRemoteInvRslt
    MAX-ACCESS   read-only
    STATUS       current
    DESCRIPTION
        "Cisco UCS sw:EthMonFsm:rmtRslt managed object property"
    ::= { cucsSwEthMonFsmEntry 11 }

cucsSwEthMonFsmStageTable OBJECT-TYPE
    SYNTAX           SEQUENCE OF CucsSwEthMonFsmStageEntry
    MAX-ACCESS       not-accessible
    STATUS           current
    DESCRIPTION
        "Cisco UCS sw:EthMonFsmStage managed object table"
    ::= { cucsSwObjects 49 }

cucsSwEthMonFsmStageEntry OBJECT-TYPE
    SYNTAX           CucsSwEthMonFsmStageEntry
    MAX-ACCESS       not-accessible
    STATUS           current
    DESCRIPTION
        "Entry for the cucsSwEthMonFsmStageTable table."
    INDEX { cucsSwEthMonFsmStageInstanceId }
    ::= { cucsSwEthMonFsmStageTable 1 }

CucsSwEthMonFsmStageEntry ::= SEQUENCE {
    cucsSwEthMonFsmStageInstanceId                                   CucsManagedObjectId,
    cucsSwEthMonFsmStageDn                                           CucsManagedObjectDn,
    cucsSwEthMonFsmStageRn                                           SnmpAdminString,
    cucsSwEthMonFsmStageDescrData                                    SnmpAdminString,
    cucsSwEthMonFsmStageLastUpdateTime                               DateAndTime,
    cucsSwEthMonFsmStageName                                         CucsSwEthMonFsmStageName,
    cucsSwEthMonFsmStageOrder                                        Gauge32,
    cucsSwEthMonFsmStageRetry                                        Gauge32,
    cucsSwEthMonFsmStageStageStatus                                  CucsFsmFsmStageStatus
}

cucsSwEthMonFsmStageInstanceId OBJECT-TYPE
    SYNTAX       CucsManagedObjectId
    MAX-ACCESS   not-accessible
    STATUS       current
    DESCRIPTION
        "Instance identifier of the managed object."
    ::= { cucsSwEthMonFsmStageEntry 1 }

cucsSwEthMonFsmStageDn OBJECT-TYPE
    SYNTAX       CucsManagedObjectDn
    MAX-ACCESS   read-only
    STATUS       current
    DESCRIPTION
        "Cisco UCS sw:EthMonFsmStage:dn managed object property"
    ::= { cucsSwEthMonFsmStageEntry 2 }

cucsSwEthMonFsmStageRn OBJECT-TYPE
    SYNTAX       SnmpAdminString
    MAX-ACCESS   read-only
    STATUS       current
    DESCRIPTION
        "Cisco UCS sw:EthMonFsmStage:rn managed object property"
    ::= { cucsSwEthMonFsmStageEntry 3 }

cucsSwEthMonFsmStageDescrData OBJECT-TYPE
    SYNTAX       SnmpAdminString
    MAX-ACCESS   read-only
    STATUS       current
    DESCRIPTION
        "Cisco UCS sw:EthMonFsmStage:descr managed object property"
    ::= { cucsSwEthMonFsmStageEntry 4 }

cucsSwEthMonFsmStageLastUpdateTime OBJECT-TYPE
    SYNTAX       DateAndTime
    MAX-ACCESS   read-only
    STATUS       current
    DESCRIPTION
        "Cisco UCS sw:EthMonFsmStage:lastUpdateTime managed
        object property"
    ::= { cucsSwEthMonFsmStageEntry 5 }

cucsSwEthMonFsmStageName OBJECT-TYPE
    SYNTAX       CucsSwEthMonFsmStageName
    MAX-ACCESS   read-only
    STATUS       current
    DESCRIPTION
        "Cisco UCS sw:EthMonFsmStage:name managed object property"
    ::= { cucsSwEthMonFsmStageEntry 6 }

cucsSwEthMonFsmStageOrder OBJECT-TYPE
    SYNTAX       Gauge32
    MAX-ACCESS   read-only
    STATUS       current
    DESCRIPTION
        "Cisco UCS sw:EthMonFsmStage:order managed object property"
    ::= { cucsSwEthMonFsmStageEntry 7 }

cucsSwEthMonFsmStageRetry OBJECT-TYPE
    SYNTAX       Gauge32
    MAX-ACCESS   read-only
    STATUS       current
    DESCRIPTION
        "Cisco UCS sw:EthMonFsmStage:retry managed object property"
    ::= { cucsSwEthMonFsmStageEntry 8 }

cucsSwEthMonFsmStageStageStatus OBJECT-TYPE
    SYNTAX       CucsFsmFsmStageStatus
    MAX-ACCESS   read-only
    STATUS       current
    DESCRIPTION
        "Cisco UCS sw:EthMonFsmStage:stageStatus managed object property"
    ::= { cucsSwEthMonFsmStageEntry 9 }

cucsSwEthMonFsmTaskTable OBJECT-TYPE
    SYNTAX           SEQUENCE OF CucsSwEthMonFsmTaskEntry
    MAX-ACCESS       not-accessible
    STATUS           current
    DESCRIPTION
        "Cisco UCS sw:EthMonFsmTask managed object table"
    ::= { cucsSwObjects 14 }

cucsSwEthMonFsmTaskEntry OBJECT-TYPE
    SYNTAX           CucsSwEthMonFsmTaskEntry
    MAX-ACCESS       not-accessible
    STATUS           current
    DESCRIPTION
        "Entry for the cucsSwEthMonFsmTaskTable table."
    INDEX { cucsSwEthMonFsmTaskInstanceId }
    ::= { cucsSwEthMonFsmTaskTable 1 }

CucsSwEthMonFsmTaskEntry ::= SEQUENCE {
    cucsSwEthMonFsmTaskInstanceId                                    CucsManagedObjectId,
    cucsSwEthMonFsmTaskDn                                            CucsManagedObjectDn,
    cucsSwEthMonFsmTaskRn                                            SnmpAdminString,
    cucsSwEthMonFsmTaskCompletion                                    CucsFsmCompletion,
    cucsSwEthMonFsmTaskFlags                                         CucsFsmFlags,
    cucsSwEthMonFsmTaskItem                                          CucsSwEthMonFsmTaskItem,
    cucsSwEthMonFsmTaskSeqId                                         Gauge32
}

cucsSwEthMonFsmTaskInstanceId OBJECT-TYPE
    SYNTAX       CucsManagedObjectId
    MAX-ACCESS   not-accessible
    STATUS       current
    DESCRIPTION
        "Instance identifier of the managed object."
    ::= { cucsSwEthMonFsmTaskEntry 1 }

cucsSwEthMonFsmTaskDn OBJECT-TYPE
    SYNTAX       CucsManagedObjectDn
    MAX-ACCESS   read-only
    STATUS       current
    DESCRIPTION
        "Cisco UCS sw:EthMonFsmTask:dn managed object property"
    ::= { cucsSwEthMonFsmTaskEntry 2 }

cucsSwEthMonFsmTaskRn OBJECT-TYPE
    SYNTAX       SnmpAdminString
    MAX-ACCESS   read-only
    STATUS       current
    DESCRIPTION
        "Cisco UCS sw:EthMonFsmTask:rn managed object property"
    ::= { cucsSwEthMonFsmTaskEntry 3 }

cucsSwEthMonFsmTaskCompletion OBJECT-TYPE
    SYNTAX       CucsFsmCompletion
    MAX-ACCESS   read-only
    STATUS       current
    DESCRIPTION
        "Cisco UCS sw:EthMonFsmTask:completion managed object property"
    ::= { cucsSwEthMonFsmTaskEntry 4 }

cucsSwEthMonFsmTaskFlags OBJECT-TYPE
    SYNTAX       CucsFsmFlags
    MAX-ACCESS   read-only
    STATUS       current
    DESCRIPTION
        "Cisco UCS sw:EthMonFsmTask:flags managed object property"
    ::= { cucsSwEthMonFsmTaskEntry 5 }

cucsSwEthMonFsmTaskItem OBJECT-TYPE
    SYNTAX       CucsSwEthMonFsmTaskItem
    MAX-ACCESS   read-only
    STATUS       current
    DESCRIPTION
        "Cisco UCS sw:EthMonFsmTask:item managed object property"
    ::= { cucsSwEthMonFsmTaskEntry 6 }

cucsSwEthMonFsmTaskSeqId OBJECT-TYPE
    SYNTAX       Gauge32
    MAX-ACCESS   read-only
    STATUS       current
    DESCRIPTION
        "Cisco UCS sw:EthMonFsmTask:seqId managed object property"
    ::= { cucsSwEthMonFsmTaskEntry 7 }

cucsSwEthMonSrcEpTable OBJECT-TYPE
    SYNTAX           SEQUENCE OF CucsSwEthMonSrcEpEntry
    MAX-ACCESS       not-accessible
    STATUS           current
    DESCRIPTION
        "Cisco UCS sw:EthMonSrcEp managed object table"
    ::= { cucsSwObjects 15 }

cucsSwEthMonSrcEpEntry OBJECT-TYPE
    SYNTAX           CucsSwEthMonSrcEpEntry
    MAX-ACCESS       not-accessible
    STATUS           current
    DESCRIPTION
        "Entry for the cucsSwEthMonSrcEpTable table."
    INDEX { cucsSwEthMonSrcEpInstanceId }
    ::= { cucsSwEthMonSrcEpTable 1 }

CucsSwEthMonSrcEpEntry ::= SEQUENCE {
    cucsSwEthMonSrcEpInstanceId                                      CucsManagedObjectId,
    cucsSwEthMonSrcEpDn                                              CucsManagedObjectDn,
    cucsSwEthMonSrcEpRn                                              SnmpAdminString,
    cucsSwEthMonSrcEpAdminState                                      CucsFabricAdminState,
    cucsSwEthMonSrcEpChassisId                                       Gauge32,
    cucsSwEthMonSrcEpEpDn                                            SnmpAdminString,
    cucsSwEthMonSrcEpIfRole                                          CucsNetworkPortRole,
    cucsSwEthMonSrcEpIfType                                          CucsSwPIoEpIfType,
    cucsSwEthMonSrcEpLocale                                          CucsSwMonSrcEpLocale,
    cucsSwEthMonSrcEpMonTrafDir                                      CucsFabricTrafficDirection,
    cucsSwEthMonSrcEpName                                            SnmpAdminString,
    cucsSwEthMonSrcEpPeerDn                                          SnmpAdminString,
    cucsSwEthMonSrcEpPeerPortId                                      Gauge32,
    cucsSwEthMonSrcEpPeerSlotId                                      Gauge32,
    cucsSwEthMonSrcEpPortId                                          Gauge32,
    cucsSwEthMonSrcEpSlotId                                          Gauge32,
    cucsSwEthMonSrcEpSwitchId                                        CucsNetworkSwitchId,
    cucsSwEthMonSrcEpTransport                                       CucsSwEthMonSrcEpTransport,
    cucsSwEthMonSrcEpType                                            CucsNetworkConnectionType,
    cucsSwEthMonSrcEpPeerChassisId                                   Gauge32,
    cucsSwEthMonSrcEpLc                                              CucsSwPIoEpLc,
    cucsSwEthMonSrcEpAggrPortId                                      Gauge32,
    cucsSwEthMonSrcEpPeerAggrPortId                                  Gauge32
}

cucsSwEthMonSrcEpInstanceId OBJECT-TYPE
    SYNTAX       CucsManagedObjectId
    MAX-ACCESS   not-accessible
    STATUS       current
    DESCRIPTION
        "Instance identifier of the managed object."
    ::= { cucsSwEthMonSrcEpEntry 1 }

cucsSwEthMonSrcEpDn OBJECT-TYPE
    SYNTAX       CucsManagedObjectDn
    MAX-ACCESS   read-only
    STATUS       current
    DESCRIPTION
        "Cisco UCS sw:EthMonSrcEp:dn managed object property"
    ::= { cucsSwEthMonSrcEpEntry 2 }

cucsSwEthMonSrcEpRn OBJECT-TYPE
    SYNTAX       SnmpAdminString
    MAX-ACCESS   read-only
    STATUS       current
    DESCRIPTION
        "Cisco UCS sw:EthMonSrcEp:rn managed object property"
    ::= { cucsSwEthMonSrcEpEntry 3 }

cucsSwEthMonSrcEpAdminState OBJECT-TYPE
    SYNTAX       CucsFabricAdminState
    MAX-ACCESS   read-only
    STATUS       current
    DESCRIPTION
        "Cisco UCS sw:EthMonSrcEp:adminState managed object property"
    ::= { cucsSwEthMonSrcEpEntry 4 }

cucsSwEthMonSrcEpChassisId OBJECT-TYPE
    SYNTAX       Gauge32
    MAX-ACCESS   read-only
    STATUS       current
    DESCRIPTION
        "Cisco UCS sw:EthMonSrcEp:chassisId managed object property"
    ::= { cucsSwEthMonSrcEpEntry 5 }

cucsSwEthMonSrcEpEpDn OBJECT-TYPE
    SYNTAX       SnmpAdminString
    MAX-ACCESS   read-only
    STATUS       current
    DESCRIPTION
        "Cisco UCS sw:EthMonSrcEp:epDn managed object property"
    ::= { cucsSwEthMonSrcEpEntry 6 }

cucsSwEthMonSrcEpIfRole OBJECT-TYPE
    SYNTAX       CucsNetworkPortRole
    MAX-ACCESS   read-only
    STATUS       current
    DESCRIPTION
        "Cisco UCS sw:EthMonSrcEp:ifRole managed object property"
    ::= { cucsSwEthMonSrcEpEntry 7 }

cucsSwEthMonSrcEpIfType OBJECT-TYPE
    SYNTAX       CucsSwPIoEpIfType
    MAX-ACCESS   read-only
    STATUS       current
    DESCRIPTION
        "Cisco UCS sw:EthMonSrcEp:ifType managed object property"
    ::= { cucsSwEthMonSrcEpEntry 8 }

cucsSwEthMonSrcEpLocale OBJECT-TYPE
    SYNTAX       CucsSwMonSrcEpLocale
    MAX-ACCESS   read-only
    STATUS       current
    DESCRIPTION
        "Cisco UCS sw:EthMonSrcEp:locale managed object property"
    ::= { cucsSwEthMonSrcEpEntry 9 }

cucsSwEthMonSrcEpMonTrafDir OBJECT-TYPE
    SYNTAX       CucsFabricTrafficDirection
    MAX-ACCESS   read-only
    STATUS       current
    DESCRIPTION
        "Cisco UCS sw:EthMonSrcEp:monTrafDir managed object property"
    ::= { cucsSwEthMonSrcEpEntry 10 }

cucsSwEthMonSrcEpName OBJECT-TYPE
    SYNTAX       SnmpAdminString
    MAX-ACCESS   read-only
    STATUS       current
    DESCRIPTION
        "Cisco UCS sw:EthMonSrcEp:name managed object property"
    ::= { cucsSwEthMonSrcEpEntry 11 }

cucsSwEthMonSrcEpPeerDn OBJECT-TYPE
    SYNTAX       SnmpAdminString
    MAX-ACCESS   read-only
    STATUS       current
    DESCRIPTION
        "Cisco UCS sw:EthMonSrcEp:peerDn managed object property"
    ::= { cucsSwEthMonSrcEpEntry 12 }

cucsSwEthMonSrcEpPeerPortId OBJECT-TYPE
    SYNTAX       Gauge32
    MAX-ACCESS   read-only
    STATUS       current
    DESCRIPTION
        "Cisco UCS sw:EthMonSrcEp:peerPortId managed object property"
    ::= { cucsSwEthMonSrcEpEntry 13 }

cucsSwEthMonSrcEpPeerSlotId OBJECT-TYPE
    SYNTAX       Gauge32
    MAX-ACCESS   read-only
    STATUS       current
    DESCRIPTION
        "Cisco UCS sw:EthMonSrcEp:peerSlotId managed object property"
    ::= { cucsSwEthMonSrcEpEntry 14 }

cucsSwEthMonSrcEpPortId OBJECT-TYPE
    SYNTAX       Gauge32
    MAX-ACCESS   read-only
    STATUS       current
    DESCRIPTION
        "Cisco UCS sw:EthMonSrcEp:portId managed object property"
    ::= { cucsSwEthMonSrcEpEntry 15 }

cucsSwEthMonSrcEpSlotId OBJECT-TYPE
    SYNTAX       Gauge32
    MAX-ACCESS   read-only
    STATUS       current
    DESCRIPTION
        "Cisco UCS sw:EthMonSrcEp:slotId managed object property"
    ::= { cucsSwEthMonSrcEpEntry 16 }

cucsSwEthMonSrcEpSwitchId OBJECT-TYPE
    SYNTAX       CucsNetworkSwitchId
    MAX-ACCESS   read-only
    STATUS       current
    DESCRIPTION
        "Cisco UCS sw:EthMonSrcEp:switchId managed object property"
    ::= { cucsSwEthMonSrcEpEntry 17 }

cucsSwEthMonSrcEpTransport OBJECT-TYPE
    SYNTAX       CucsSwEthMonSrcEpTransport
    MAX-ACCESS   read-only
    STATUS       current
    DESCRIPTION
        "Cisco UCS sw:EthMonSrcEp:transport managed object property"
    ::= { cucsSwEthMonSrcEpEntry 18 }

cucsSwEthMonSrcEpType OBJECT-TYPE
    SYNTAX       CucsNetworkConnectionType
    MAX-ACCESS   read-only
    STATUS       current
    DESCRIPTION
        "Cisco UCS sw:EthMonSrcEp:type managed object property"
    ::= { cucsSwEthMonSrcEpEntry 19 }

cucsSwEthMonSrcEpPeerChassisId OBJECT-TYPE
    SYNTAX       Gauge32
    MAX-ACCESS   read-only
    STATUS       current
    DESCRIPTION
        "Cisco UCS sw:EthMonSrcEp:peerChassisId managed object property"
    ::= { cucsSwEthMonSrcEpEntry 20 }

cucsSwEthMonSrcEpLc OBJECT-TYPE
    SYNTAX       CucsSwPIoEpLc
    MAX-ACCESS   read-only
    STATUS       current
    DESCRIPTION
        "Cisco UCS sw:EthMonSrcEp:lc managed object property"
    ::= { cucsSwEthMonSrcEpEntry 21 }

cucsSwEthMonSrcEpAggrPortId OBJECT-TYPE
    SYNTAX       Gauge32
    MAX-ACCESS   read-only
    STATUS       current
    DESCRIPTION
        "Cisco UCS sw:EthMonSrcEp:aggrPortId managed object property"
    ::= { cucsSwEthMonSrcEpEntry 22 }

cucsSwEthMonSrcEpPeerAggrPortId OBJECT-TYPE
    SYNTAX       Gauge32
    MAX-ACCESS   read-only
    STATUS       current
    DESCRIPTION
        "Cisco UCS sw:EthMonSrcEp:peerAggrPortId managed object property"
    ::= { cucsSwEthMonSrcEpEntry 23 }

cucsSwEthTargetEpTable OBJECT-TYPE
    SYNTAX           SEQUENCE OF CucsSwEthTargetEpEntry
    MAX-ACCESS       not-accessible
    STATUS           current
    DESCRIPTION
        "Cisco UCS sw:EthTargetEp managed object table"
    ::= { cucsSwObjects 16 }

cucsSwEthTargetEpEntry OBJECT-TYPE
    SYNTAX           CucsSwEthTargetEpEntry
    MAX-ACCESS       not-accessible
    STATUS           current
    DESCRIPTION
        "Entry for the cucsSwEthTargetEpTable table."
    INDEX { cucsSwEthTargetEpInstanceId }
    ::= { cucsSwEthTargetEpTable 1 }

CucsSwEthTargetEpEntry ::= SEQUENCE {
    cucsSwEthTargetEpInstanceId                                      CucsManagedObjectId,
    cucsSwEthTargetEpDn                                              CucsManagedObjectDn,
    cucsSwEthTargetEpRn                                              SnmpAdminString,
    cucsSwEthTargetEpAdminState                                      CucsSwEthTargetEpAdminState,
    cucsSwEthTargetEpChassisId                                       Gauge32,
    cucsSwEthTargetEpEpDn                                            SnmpAdminString,
    cucsSwEthTargetEpIfRole                                          CucsNetworkPortRole,
    cucsSwEthTargetEpIfType                                          CucsFabricPIoEpIfType,
    cucsSwEthTargetEpLicGP                                           Unsigned64,
    cucsSwEthTargetEpLicState                                        CucsLicenseState,
    cucsSwEthTargetEpLocale                                          CucsFabricExternalEpLocale,
    cucsSwEthTargetEpMacAddress                                      MacAddress,
    cucsSwEthTargetEpName                                            SnmpAdminString,
    cucsSwEthTargetEpPeerDn                                          SnmpAdminString,
    cucsSwEthTargetEpPeerPortId                                      Gauge32,
    cucsSwEthTargetEpPeerSlotId                                      Gauge32,
    cucsSwEthTargetEpPortId                                          CucsFabricPIoEpPortId,
    cucsSwEthTargetEpSlotId                                          CucsFabricPIoEpSlotId,
    cucsSwEthTargetEpSwitchId                                        CucsNetworkSwitchId,
    cucsSwEthTargetEpTransport                                       CucsSwEthTargetEpTransport,
    cucsSwEthTargetEpType                                            CucsSwTargetEpType,
    cucsSwEthTargetEpPeerChassisId                                   Gauge32,
    cucsSwEthTargetEpFltAggr                                         Unsigned64,
    cucsSwEthTargetEpOperState                                       CucsFabricPIoEpOperState,
    cucsSwEthTargetEpOperStateReason                                 SnmpAdminString,
    cucsSwEthTargetEpWarnings                                        CucsFabricWarnings,
    cucsSwEthTargetEpAggrPortId                                      Gauge32,
    cucsSwEthTargetEpPeerAggrPortId                                  Gauge32,
    cucsSwEthTargetEpAutoNegotiate                                   TruthValue,
    cucsSwEthTargetEpUsrLbl                                          SnmpAdminString
}

cucsSwEthTargetEpInstanceId OBJECT-TYPE
    SYNTAX       CucsManagedObjectId
    MAX-ACCESS   not-accessible
    STATUS       current
    DESCRIPTION
        "Instance identifier of the managed object."
    ::= { cucsSwEthTargetEpEntry 1 }

cucsSwEthTargetEpDn OBJECT-TYPE
    SYNTAX       CucsManagedObjectDn
    MAX-ACCESS   read-only
    STATUS       current
    DESCRIPTION
        "Cisco UCS sw:EthTargetEp:dn managed object property"
    ::= { cucsSwEthTargetEpEntry 2 }

cucsSwEthTargetEpRn OBJECT-TYPE
    SYNTAX       SnmpAdminString
    MAX-ACCESS   read-only
    STATUS       current
    DESCRIPTION
        "Cisco UCS sw:EthTargetEp:rn managed object property"
    ::= { cucsSwEthTargetEpEntry 3 }

cucsSwEthTargetEpAdminState OBJECT-TYPE
    SYNTAX       CucsSwEthTargetEpAdminState
    MAX-ACCESS   read-only
    STATUS       current
    DESCRIPTION
        "Cisco UCS sw:EthTargetEp:adminState managed object property"
    ::= { cucsSwEthTargetEpEntry 4 }

cucsSwEthTargetEpChassisId OBJECT-TYPE
    SYNTAX       Gauge32
    MAX-ACCESS   read-only
    STATUS       current
    DESCRIPTION
        "Cisco UCS sw:EthTargetEp:chassisId managed object property"
    ::= { cucsSwEthTargetEpEntry 5 }

cucsSwEthTargetEpEpDn OBJECT-TYPE
    SYNTAX       SnmpAdminString
    MAX-ACCESS   read-only
    STATUS       current
    DESCRIPTION
        "Cisco UCS sw:EthTargetEp:epDn managed object property"
    ::= { cucsSwEthTargetEpEntry 6 }

cucsSwEthTargetEpIfRole OBJECT-TYPE
    SYNTAX       CucsNetworkPortRole
    MAX-ACCESS   read-only
    STATUS       current
    DESCRIPTION
        "Cisco UCS sw:EthTargetEp:ifRole managed object property"
    ::= { cucsSwEthTargetEpEntry 7 }

cucsSwEthTargetEpIfType OBJECT-TYPE
    SYNTAX       CucsFabricPIoEpIfType
    MAX-ACCESS   read-only
    STATUS       current
    DESCRIPTION
        "Cisco UCS sw:EthTargetEp:ifType managed object property"
    ::= { cucsSwEthTargetEpEntry 8 }

cucsSwEthTargetEpLicGP OBJECT-TYPE
    SYNTAX       Unsigned64
    MAX-ACCESS   read-only
    STATUS       current
    DESCRIPTION
        "Cisco UCS sw:EthTargetEp:licGP managed object property"
    ::= { cucsSwEthTargetEpEntry 9 }

cucsSwEthTargetEpLicState OBJECT-TYPE
    SYNTAX       CucsLicenseState
    MAX-ACCESS   read-only
    STATUS       current
    DESCRIPTION
        "Cisco UCS sw:EthTargetEp:licState managed object property"
    ::= { cucsSwEthTargetEpEntry 10 }

cucsSwEthTargetEpLocale OBJECT-TYPE
    SYNTAX       CucsFabricExternalEpLocale
    MAX-ACCESS   read-only
    STATUS       current
    DESCRIPTION
        "Cisco UCS sw:EthTargetEp:locale managed object property"
    ::= { cucsSwEthTargetEpEntry 11 }

cucsSwEthTargetEpMacAddress OBJECT-TYPE
    SYNTAX       MacAddress
    MAX-ACCESS   read-only
    STATUS       current
    DESCRIPTION
        "Cisco UCS sw:EthTargetEp:macAddress managed object property"
    ::= { cucsSwEthTargetEpEntry 12 }

cucsSwEthTargetEpName OBJECT-TYPE
    SYNTAX       SnmpAdminString
    MAX-ACCESS   read-only
    STATUS       current
    DESCRIPTION
        "Cisco UCS sw:EthTargetEp:name managed object property"
    ::= { cucsSwEthTargetEpEntry 13 }

cucsSwEthTargetEpPeerDn OBJECT-TYPE
    SYNTAX       SnmpAdminString
    MAX-ACCESS   read-only
    STATUS       current
    DESCRIPTION
        "Cisco UCS sw:EthTargetEp:peerDn managed object property"
    ::= { cucsSwEthTargetEpEntry 14 }

cucsSwEthTargetEpPeerPortId OBJECT-TYPE
    SYNTAX       Gauge32
    MAX-ACCESS   read-only
    STATUS       current
    DESCRIPTION
        "Cisco UCS sw:EthTargetEp:peerPortId managed object property"
    ::= { cucsSwEthTargetEpEntry 15 }

cucsSwEthTargetEpPeerSlotId OBJECT-TYPE
    SYNTAX       Gauge32
    MAX-ACCESS   read-only
    STATUS       current
    DESCRIPTION
        "Cisco UCS sw:EthTargetEp:peerSlotId managed object property"
    ::= { cucsSwEthTargetEpEntry 16 }

cucsSwEthTargetEpPortId OBJECT-TYPE
    SYNTAX       CucsFabricPIoEpPortId
    MAX-ACCESS   read-only
    STATUS       current
    DESCRIPTION
        "Cisco UCS sw:EthTargetEp:portId managed object property"
    ::= { cucsSwEthTargetEpEntry 17 }

cucsSwEthTargetEpSlotId OBJECT-TYPE
    SYNTAX       CucsFabricPIoEpSlotId
    MAX-ACCESS   read-only
    STATUS       current
    DESCRIPTION
        "Cisco UCS sw:EthTargetEp:slotId managed object property"
    ::= { cucsSwEthTargetEpEntry 18 }

cucsSwEthTargetEpSwitchId OBJECT-TYPE
    SYNTAX       CucsNetworkSwitchId
    MAX-ACCESS   read-only
    STATUS       current
    DESCRIPTION
        "Cisco UCS sw:EthTargetEp:switchId managed object property"
    ::= { cucsSwEthTargetEpEntry 19 }

cucsSwEthTargetEpTransport OBJECT-TYPE
    SYNTAX       CucsSwEthTargetEpTransport
    MAX-ACCESS   read-only
    STATUS       current
    DESCRIPTION
        "Cisco UCS sw:EthTargetEp:transport managed object property"
    ::= { cucsSwEthTargetEpEntry 20 }

cucsSwEthTargetEpType OBJECT-TYPE
    SYNTAX       CucsSwTargetEpType
    MAX-ACCESS   read-only
    STATUS       current
    DESCRIPTION
        "Cisco UCS sw:EthTargetEp:type managed object property"
    ::= { cucsSwEthTargetEpEntry 21 }

cucsSwEthTargetEpPeerChassisId OBJECT-TYPE
    SYNTAX       Gauge32
    MAX-ACCESS   read-only
    STATUS       current
    DESCRIPTION
        "Cisco UCS sw:EthTargetEp:peerChassisId managed object property"
    ::= { cucsSwEthTargetEpEntry 22 }

cucsSwEthTargetEpFltAggr OBJECT-TYPE
    SYNTAX       Unsigned64
    MAX-ACCESS   read-only
    STATUS       current
    DESCRIPTION
        "Cisco UCS sw:EthTargetEp:fltAggr managed object property"
    ::= { cucsSwEthTargetEpEntry 23 }

cucsSwEthTargetEpOperState OBJECT-TYPE
    SYNTAX       CucsFabricPIoEpOperState
    MAX-ACCESS   read-only
    STATUS       current
    DESCRIPTION
        "Cisco UCS sw:EthTargetEp:operState managed object property"
    ::= { cucsSwEthTargetEpEntry 24 }

cucsSwEthTargetEpOperStateReason OBJECT-TYPE
    SYNTAX       SnmpAdminString
    MAX-ACCESS   read-only
    STATUS       current
    DESCRIPTION
        "Cisco UCS sw:EthTargetEp:operStateReason managed object property"
    ::= { cucsSwEthTargetEpEntry 25 }

cucsSwEthTargetEpWarnings OBJECT-TYPE
    SYNTAX       CucsFabricWarnings
    MAX-ACCESS   read-only
    STATUS       current
    DESCRIPTION
        "Cisco UCS sw:EthTargetEp:warnings managed object property"
    ::= { cucsSwEthTargetEpEntry 26 }

cucsSwEthTargetEpAggrPortId OBJECT-TYPE
    SYNTAX       Gauge32
    MAX-ACCESS   read-only
    STATUS       current
    DESCRIPTION
        "Cisco UCS sw:EthTargetEp:aggrPortId managed object property"
    ::= { cucsSwEthTargetEpEntry 27 }

cucsSwEthTargetEpPeerAggrPortId OBJECT-TYPE
    SYNTAX       Gauge32
    MAX-ACCESS   read-only
    STATUS       current
    DESCRIPTION
        "Cisco UCS sw:EthTargetEp:peerAggrPortId managed object property"
    ::= { cucsSwEthTargetEpEntry 28 }

cucsSwEthTargetEpAutoNegotiate OBJECT-TYPE
    SYNTAX       TruthValue
    MAX-ACCESS   read-only
    STATUS       current
    DESCRIPTION
        "Cisco UCS sw:EthTargetEp:autoNegotiate managed object property"
    ::= { cucsSwEthTargetEpEntry 29 }

cucsSwEthTargetEpUsrLbl OBJECT-TYPE
    SYNTAX       SnmpAdminString
    MAX-ACCESS   read-only
    STATUS       current
    DESCRIPTION
        "Cisco UCS sw:EthTargetEp:usrLbl managed object property"
    ::= { cucsSwEthTargetEpEntry 30 }

cucsSwEtherPortTable OBJECT-TYPE
    SYNTAX           SEQUENCE OF CucsSwEtherPortEntry
    MAX-ACCESS       not-accessible
    STATUS           current
    DESCRIPTION
        "Cisco UCS sw:EtherPort managed object table"
    ::= { cucsSwObjects 92 }

cucsSwEtherPortEntry OBJECT-TYPE
    SYNTAX           CucsSwEtherPortEntry
    MAX-ACCESS       not-accessible
    STATUS           current
    DESCRIPTION
        "Entry for the cucsSwEtherPortTable table."
    INDEX { cucsSwEtherPortInstanceId }
    ::= { cucsSwEtherPortTable 1 }

CucsSwEtherPortEntry ::= SEQUENCE {
    cucsSwEtherPortInstanceId                                        CucsManagedObjectId,
    cucsSwEtherPortDn                                                CucsManagedObjectDn,
    cucsSwEtherPortRn                                                SnmpAdminString,
    cucsSwEtherPortAggrPortId                                        CucsSwEtherPortAggrPortId,
    cucsSwEtherPortPortId                                            CucsSwEtherPortPortId,
    cucsSwEtherPortSlotId                                            CucsSwEtherPortSlotId
}

cucsSwEtherPortInstanceId OBJECT-TYPE
    SYNTAX       CucsManagedObjectId
    MAX-ACCESS   not-accessible
    STATUS       current
    DESCRIPTION
        "Instance identifier of the managed object."
    ::= { cucsSwEtherPortEntry 1 }

cucsSwEtherPortDn OBJECT-TYPE
    SYNTAX       CucsManagedObjectDn
    MAX-ACCESS   read-only
    STATUS       current
    DESCRIPTION
        "Cisco UCS sw:EtherPort:dn managed object property"
    ::= { cucsSwEtherPortEntry 2 }

cucsSwEtherPortRn OBJECT-TYPE
    SYNTAX       SnmpAdminString
    MAX-ACCESS   read-only
    STATUS       current
    DESCRIPTION
        "Cisco UCS sw:EtherPort:rn managed object property"
    ::= { cucsSwEtherPortEntry 3 }

cucsSwEtherPortAggrPortId OBJECT-TYPE
    SYNTAX       CucsSwEtherPortAggrPortId
    MAX-ACCESS   read-only
    STATUS       current
    DESCRIPTION
        "Cisco UCS sw:EtherPort:aggrPortId managed object property"
    ::= { cucsSwEtherPortEntry 4 }

cucsSwEtherPortPortId OBJECT-TYPE
    SYNTAX       CucsSwEtherPortPortId
    MAX-ACCESS   read-only
    STATUS       current
    DESCRIPTION
        "Cisco UCS sw:EtherPort:portId managed object property"
    ::= { cucsSwEtherPortEntry 5 }

cucsSwEtherPortSlotId OBJECT-TYPE
    SYNTAX       CucsSwEtherPortSlotId
    MAX-ACCESS   read-only
    STATUS       current
    DESCRIPTION
        "Cisco UCS sw:EtherPort:slotId managed object property"
    ::= { cucsSwEtherPortEntry 6 }

cucsSwExtUtilityTable OBJECT-TYPE
    SYNTAX           SEQUENCE OF CucsSwExtUtilityEntry
    MAX-ACCESS       not-accessible
    STATUS           current
    DESCRIPTION
        "Cisco UCS sw:ExtUtility managed object table"
    ::= { cucsSwObjects 83 }

cucsSwExtUtilityEntry OBJECT-TYPE
    SYNTAX           CucsSwExtUtilityEntry
    MAX-ACCESS       not-accessible
    STATUS           current
    DESCRIPTION
        "Entry for the cucsSwExtUtilityTable table."
    INDEX { cucsSwExtUtilityInstanceId }
    ::= { cucsSwExtUtilityTable 1 }

CucsSwExtUtilityEntry ::= SEQUENCE {
    cucsSwExtUtilityInstanceId                                       CucsManagedObjectId,
    cucsSwExtUtilityDn                                               CucsManagedObjectDn,
    cucsSwExtUtilityRn                                               SnmpAdminString,
    cucsSwExtUtilityConfMode                                         CucsSwConfMode,
    cucsSwExtUtilityFsmDescr                                         SnmpAdminString,
    cucsSwExtUtilityFsmPrev                                          SnmpAdminString,
    cucsSwExtUtilityFsmProgr                                         Gauge32,
    cucsSwExtUtilityFsmRmtInvErrCode                                 Gauge32,
    cucsSwExtUtilityFsmRmtInvErrDescr                                SnmpAdminString,
    cucsSwExtUtilityFsmRmtInvRslt                                    CucsConditionRemoteInvRslt,
    cucsSwExtUtilityFsmStageDescr                                    SnmpAdminString,
    cucsSwExtUtilityFsmStamp                                         DateAndTime,
    cucsSwExtUtilityFsmStatus                                        SnmpAdminString,
    cucsSwExtUtilityFsmTry                                           Gauge32,
    cucsSwExtUtilitySwitchId                                         CucsNetworkSwitchId
}

cucsSwExtUtilityInstanceId OBJECT-TYPE
    SYNTAX       CucsManagedObjectId
    MAX-ACCESS   not-accessible
    STATUS       current
    DESCRIPTION
        "Instance identifier of the managed object."
    ::= { cucsSwExtUtilityEntry 1 }

cucsSwExtUtilityDn OBJECT-TYPE
    SYNTAX       CucsManagedObjectDn
    MAX-ACCESS   read-only
    STATUS       current
    DESCRIPTION
        "Cisco UCS sw:ExtUtility:dn managed object property"
    ::= { cucsSwExtUtilityEntry 2 }

cucsSwExtUtilityRn OBJECT-TYPE
    SYNTAX       SnmpAdminString
    MAX-ACCESS   read-only
    STATUS       current
    DESCRIPTION
        "Cisco UCS sw:ExtUtility:rn managed object property"
    ::= { cucsSwExtUtilityEntry 3 }

cucsSwExtUtilityConfMode OBJECT-TYPE
    SYNTAX       CucsSwConfMode
    MAX-ACCESS   read-only
    STATUS       current
    DESCRIPTION
        "Cisco UCS sw:ExtUtility:confMode managed object property"
    ::= { cucsSwExtUtilityEntry 4 }

cucsSwExtUtilityFsmDescr OBJECT-TYPE
    SYNTAX       SnmpAdminString
    MAX-ACCESS   read-only
    STATUS       current
    DESCRIPTION
        "Cisco UCS sw:ExtUtility:fsmDescr managed object property"
    ::= { cucsSwExtUtilityEntry 5 }

cucsSwExtUtilityFsmPrev OBJECT-TYPE
    SYNTAX       SnmpAdminString
    MAX-ACCESS   read-only
    STATUS       current
    DESCRIPTION
        "Cisco UCS sw:ExtUtility:fsmPrev managed object property"
    ::= { cucsSwExtUtilityEntry 6 }

cucsSwExtUtilityFsmProgr OBJECT-TYPE
    SYNTAX       Gauge32
    MAX-ACCESS   read-only
    STATUS       current
    DESCRIPTION
        "Cisco UCS sw:ExtUtility:fsmProgr managed object property"
    ::= { cucsSwExtUtilityEntry 7 }

cucsSwExtUtilityFsmRmtInvErrCode OBJECT-TYPE
    SYNTAX       Gauge32
    MAX-ACCESS   read-only
    STATUS       current
    DESCRIPTION
        "Cisco UCS sw:ExtUtility:fsmRmtInvErrCode managed object property"
    ::= { cucsSwExtUtilityEntry 8 }

cucsSwExtUtilityFsmRmtInvErrDescr OBJECT-TYPE
    SYNTAX       SnmpAdminString
    MAX-ACCESS   read-only
    STATUS       current
    DESCRIPTION
        "Cisco UCS sw:ExtUtility:fsmRmtInvErrDescr managed
        object property"
    ::= { cucsSwExtUtilityEntry 9 }

cucsSwExtUtilityFsmRmtInvRslt OBJECT-TYPE
    SYNTAX       CucsConditionRemoteInvRslt
    MAX-ACCESS   read-only
    STATUS       current
    DESCRIPTION
        "Cisco UCS sw:ExtUtility:fsmRmtInvRslt managed object property"
    ::= { cucsSwExtUtilityEntry 10 }

cucsSwExtUtilityFsmStageDescr OBJECT-TYPE
    SYNTAX       SnmpAdminString
    MAX-ACCESS   read-only
    STATUS       current
    DESCRIPTION
        "Cisco UCS sw:ExtUtility:fsmStageDescr managed object property"
    ::= { cucsSwExtUtilityEntry 11 }

cucsSwExtUtilityFsmStamp OBJECT-TYPE
    SYNTAX       DateAndTime
    MAX-ACCESS   read-only
    STATUS       current
    DESCRIPTION
        "Cisco UCS sw:ExtUtility:fsmStamp managed object property"
    ::= { cucsSwExtUtilityEntry 12 }

cucsSwExtUtilityFsmStatus OBJECT-TYPE
    SYNTAX       SnmpAdminString
    MAX-ACCESS   read-only
    STATUS       current
    DESCRIPTION
        "Cisco UCS sw:ExtUtility:fsmStatus managed object property"
    ::= { cucsSwExtUtilityEntry 13 }

cucsSwExtUtilityFsmTry OBJECT-TYPE
    SYNTAX       Gauge32
    MAX-ACCESS   read-only
    STATUS       current
    DESCRIPTION
        "Cisco UCS sw:ExtUtility:fsmTry managed object property"
    ::= { cucsSwExtUtilityEntry 14 }

cucsSwExtUtilitySwitchId OBJECT-TYPE
    SYNTAX       CucsNetworkSwitchId
    MAX-ACCESS   read-only
    STATUS       current
    DESCRIPTION
        "Cisco UCS sw:ExtUtility:switchId managed object property"
    ::= { cucsSwExtUtilityEntry 15 }

cucsSwExtUtilityFsmTable OBJECT-TYPE
    SYNTAX           SEQUENCE OF CucsSwExtUtilityFsmEntry
    MAX-ACCESS       not-accessible
    STATUS           current
    DESCRIPTION
        "Cisco UCS sw:ExtUtilityFsm managed object table"
    ::= { cucsSwObjects 84 }

cucsSwExtUtilityFsmEntry OBJECT-TYPE
    SYNTAX           CucsSwExtUtilityFsmEntry
    MAX-ACCESS       not-accessible
    STATUS           current
    DESCRIPTION
        "Entry for the cucsSwExtUtilityFsmTable table."
    INDEX { cucsSwExtUtilityFsmInstanceId }
    ::= { cucsSwExtUtilityFsmTable 1 }

CucsSwExtUtilityFsmEntry ::= SEQUENCE {
    cucsSwExtUtilityFsmInstanceId                                    CucsManagedObjectId,
    cucsSwExtUtilityFsmDn                                            CucsManagedObjectDn,
    cucsSwExtUtilityFsmRn                                            SnmpAdminString,
    cucsSwExtUtilityFsmCompletionTime                                DateAndTime,
    cucsSwExtUtilityFsmCurrentFsm                                    CucsSwExtUtilityFsmCurrentFsm,
    cucsSwExtUtilityFsmDescrData                                     SnmpAdminString,
    cucsSwExtUtilityFsmFsmStatus                                     CucsFsmFsmStageStatus,
    cucsSwExtUtilityFsmProgress                                      Gauge32,
    cucsSwExtUtilityFsmRmtErrCode                                    Gauge32,
    cucsSwExtUtilityFsmRmtErrDescr                                   SnmpAdminString,
    cucsSwExtUtilityFsmRmtRslt                                       CucsConditionRemoteInvRslt
}

cucsSwExtUtilityFsmInstanceId OBJECT-TYPE
    SYNTAX       CucsManagedObjectId
    MAX-ACCESS   not-accessible
    STATUS       current
    DESCRIPTION
        "Instance identifier of the managed object."
    ::= { cucsSwExtUtilityFsmEntry 1 }

cucsSwExtUtilityFsmDn OBJECT-TYPE
    SYNTAX       CucsManagedObjectDn
    MAX-ACCESS   read-only
    STATUS       current
    DESCRIPTION
        "Cisco UCS sw:ExtUtilityFsm:dn managed object property"
    ::= { cucsSwExtUtilityFsmEntry 2 }

cucsSwExtUtilityFsmRn OBJECT-TYPE
    SYNTAX       SnmpAdminString
    MAX-ACCESS   read-only
    STATUS       current
    DESCRIPTION
        "Cisco UCS sw:ExtUtilityFsm:rn managed object property"
    ::= { cucsSwExtUtilityFsmEntry 3 }

cucsSwExtUtilityFsmCompletionTime OBJECT-TYPE
    SYNTAX       DateAndTime
    MAX-ACCESS   read-only
    STATUS       current
    DESCRIPTION
        "Cisco UCS sw:ExtUtilityFsm:completionTime managed
        object property"
    ::= { cucsSwExtUtilityFsmEntry 4 }

cucsSwExtUtilityFsmCurrentFsm OBJECT-TYPE
    SYNTAX       CucsSwExtUtilityFsmCurrentFsm
    MAX-ACCESS   read-only
    STATUS       current
    DESCRIPTION
        "Cisco UCS sw:ExtUtilityFsm:currentFsm managed object property"
    ::= { cucsSwExtUtilityFsmEntry 5 }

cucsSwExtUtilityFsmDescrData OBJECT-TYPE
    SYNTAX       SnmpAdminString
    MAX-ACCESS   read-only
    STATUS       current
    DESCRIPTION
        "Cisco UCS sw:ExtUtilityFsm:descr managed object property"
    ::= { cucsSwExtUtilityFsmEntry 6 }

cucsSwExtUtilityFsmFsmStatus OBJECT-TYPE
    SYNTAX       CucsFsmFsmStageStatus
    MAX-ACCESS   read-only
    STATUS       current
    DESCRIPTION
        "Cisco UCS sw:ExtUtilityFsm:fsmStatus managed object property"
    ::= { cucsSwExtUtilityFsmEntry 7 }

cucsSwExtUtilityFsmProgress OBJECT-TYPE
    SYNTAX       Gauge32
    MAX-ACCESS   read-only
    STATUS       current
    DESCRIPTION
        "Cisco UCS sw:ExtUtilityFsm:progress managed object property"
    ::= { cucsSwExtUtilityFsmEntry 8 }

cucsSwExtUtilityFsmRmtErrCode OBJECT-TYPE
    SYNTAX       Gauge32
    MAX-ACCESS   read-only
    STATUS       current
    DESCRIPTION
        "Cisco UCS sw:ExtUtilityFsm:rmtErrCode managed object property"
    ::= { cucsSwExtUtilityFsmEntry 9 }

cucsSwExtUtilityFsmRmtErrDescr OBJECT-TYPE
    SYNTAX       SnmpAdminString
    MAX-ACCESS   read-only
    STATUS       current
    DESCRIPTION
        "Cisco UCS sw:ExtUtilityFsm:rmtErrDescr managed object property"
    ::= { cucsSwExtUtilityFsmEntry 10 }

cucsSwExtUtilityFsmRmtRslt OBJECT-TYPE
    SYNTAX       CucsConditionRemoteInvRslt
    MAX-ACCESS   read-only
    STATUS       current
    DESCRIPTION
        "Cisco UCS sw:ExtUtilityFsm:rmtRslt managed object property"
    ::= { cucsSwExtUtilityFsmEntry 11 }

cucsSwExtUtilityFsmStageTable OBJECT-TYPE
    SYNTAX           SEQUENCE OF CucsSwExtUtilityFsmStageEntry
    MAX-ACCESS       not-accessible
    STATUS           current
    DESCRIPTION
        "Cisco UCS sw:ExtUtilityFsmStage managed object table"
    ::= { cucsSwObjects 85 }

cucsSwExtUtilityFsmStageEntry OBJECT-TYPE
    SYNTAX           CucsSwExtUtilityFsmStageEntry
    MAX-ACCESS       not-accessible
    STATUS           current
    DESCRIPTION
        "Entry for the cucsSwExtUtilityFsmStageTable table."
    INDEX { cucsSwExtUtilityFsmStageInstanceId }
    ::= { cucsSwExtUtilityFsmStageTable 1 }

CucsSwExtUtilityFsmStageEntry ::= SEQUENCE {
    cucsSwExtUtilityFsmStageInstanceId                               CucsManagedObjectId,
    cucsSwExtUtilityFsmStageDn                                       CucsManagedObjectDn,
    cucsSwExtUtilityFsmStageRn                                       SnmpAdminString,
    cucsSwExtUtilityFsmStageDescrData                                SnmpAdminString,
    cucsSwExtUtilityFsmStageLastUpdateTime                           DateAndTime,
    cucsSwExtUtilityFsmStageName                                     CucsSwExtUtilityFsmStageName,
    cucsSwExtUtilityFsmStageOrder                                    Gauge32,
    cucsSwExtUtilityFsmStageRetry                                    Gauge32,
    cucsSwExtUtilityFsmStageStageStatus                              CucsFsmFsmStageStatus
}

cucsSwExtUtilityFsmStageInstanceId OBJECT-TYPE
    SYNTAX       CucsManagedObjectId
    MAX-ACCESS   not-accessible
    STATUS       current
    DESCRIPTION
        "Instance identifier of the managed object."
    ::= { cucsSwExtUtilityFsmStageEntry 1 }

cucsSwExtUtilityFsmStageDn OBJECT-TYPE
    SYNTAX       CucsManagedObjectDn
    MAX-ACCESS   read-only
    STATUS       current
    DESCRIPTION
        "Cisco UCS sw:ExtUtilityFsmStage:dn managed object property"
    ::= { cucsSwExtUtilityFsmStageEntry 2 }

cucsSwExtUtilityFsmStageRn OBJECT-TYPE
    SYNTAX       SnmpAdminString
    MAX-ACCESS   read-only
    STATUS       current
    DESCRIPTION
        "Cisco UCS sw:ExtUtilityFsmStage:rn managed object property"
    ::= { cucsSwExtUtilityFsmStageEntry 3 }

cucsSwExtUtilityFsmStageDescrData OBJECT-TYPE
    SYNTAX       SnmpAdminString
    MAX-ACCESS   read-only
    STATUS       current
    DESCRIPTION
        "Cisco UCS sw:ExtUtilityFsmStage:descr managed object property"
    ::= { cucsSwExtUtilityFsmStageEntry 4 }

cucsSwExtUtilityFsmStageLastUpdateTime OBJECT-TYPE
    SYNTAX       DateAndTime
    MAX-ACCESS   read-only
    STATUS       current
    DESCRIPTION
        "Cisco UCS sw:ExtUtilityFsmStage:lastUpdateTime
        managed object property"
    ::= { cucsSwExtUtilityFsmStageEntry 5 }

cucsSwExtUtilityFsmStageName OBJECT-TYPE
    SYNTAX       CucsSwExtUtilityFsmStageName
    MAX-ACCESS   read-only
    STATUS       current
    DESCRIPTION
        "Cisco UCS sw:ExtUtilityFsmStage:name managed object property"
    ::= { cucsSwExtUtilityFsmStageEntry 6 }

cucsSwExtUtilityFsmStageOrder OBJECT-TYPE
    SYNTAX       Gauge32
    MAX-ACCESS   read-only
    STATUS       current
    DESCRIPTION
        "Cisco UCS sw:ExtUtilityFsmStage:order managed object property"
    ::= { cucsSwExtUtilityFsmStageEntry 7 }

cucsSwExtUtilityFsmStageRetry OBJECT-TYPE
    SYNTAX       Gauge32
    MAX-ACCESS   read-only
    STATUS       current
    DESCRIPTION
        "Cisco UCS sw:ExtUtilityFsmStage:retry managed object property"
    ::= { cucsSwExtUtilityFsmStageEntry 8 }

cucsSwExtUtilityFsmStageStageStatus OBJECT-TYPE
    SYNTAX       CucsFsmFsmStageStatus
    MAX-ACCESS   read-only
    STATUS       current
    DESCRIPTION
        "Cisco UCS sw:ExtUtilityFsmStage:stageStatus managed
        object property"
    ::= { cucsSwExtUtilityFsmStageEntry 9 }

cucsSwExtUtilityFsmTaskTable OBJECT-TYPE
    SYNTAX           SEQUENCE OF CucsSwExtUtilityFsmTaskEntry
    MAX-ACCESS       not-accessible
    STATUS           current
    DESCRIPTION
        "Cisco UCS sw:ExtUtilityFsmTask managed object table"
    ::= { cucsSwObjects 86 }

cucsSwExtUtilityFsmTaskEntry OBJECT-TYPE
    SYNTAX           CucsSwExtUtilityFsmTaskEntry
    MAX-ACCESS       not-accessible
    STATUS           current
    DESCRIPTION
        "Entry for the cucsSwExtUtilityFsmTaskTable table."
    INDEX { cucsSwExtUtilityFsmTaskInstanceId }
    ::= { cucsSwExtUtilityFsmTaskTable 1 }

CucsSwExtUtilityFsmTaskEntry ::= SEQUENCE {
    cucsSwExtUtilityFsmTaskInstanceId                                CucsManagedObjectId,
    cucsSwExtUtilityFsmTaskDn                                        CucsManagedObjectDn,
    cucsSwExtUtilityFsmTaskRn                                        SnmpAdminString,
    cucsSwExtUtilityFsmTaskCompletion                                CucsFsmCompletion,
    cucsSwExtUtilityFsmTaskFlags                                     CucsFsmFlags,
    cucsSwExtUtilityFsmTaskItem                                      CucsSwExtUtilityFsmTaskItem,
    cucsSwExtUtilityFsmTaskSeqId                                     Gauge32
}

cucsSwExtUtilityFsmTaskInstanceId OBJECT-TYPE
    SYNTAX       CucsManagedObjectId
    MAX-ACCESS   not-accessible
    STATUS       current
    DESCRIPTION
        "Instance identifier of the managed object."
    ::= { cucsSwExtUtilityFsmTaskEntry 1 }

cucsSwExtUtilityFsmTaskDn OBJECT-TYPE
    SYNTAX       CucsManagedObjectDn
    MAX-ACCESS   read-only
    STATUS       current
    DESCRIPTION
        "Cisco UCS sw:ExtUtilityFsmTask:dn managed object property"
    ::= { cucsSwExtUtilityFsmTaskEntry 2 }

cucsSwExtUtilityFsmTaskRn OBJECT-TYPE
    SYNTAX       SnmpAdminString
    MAX-ACCESS   read-only
    STATUS       current
    DESCRIPTION
        "Cisco UCS sw:ExtUtilityFsmTask:rn managed object property"
    ::= { cucsSwExtUtilityFsmTaskEntry 3 }

cucsSwExtUtilityFsmTaskCompletion OBJECT-TYPE
    SYNTAX       CucsFsmCompletion
    MAX-ACCESS   read-only
    STATUS       current
    DESCRIPTION
        "Cisco UCS sw:ExtUtilityFsmTask:completion managed
        object property"
    ::= { cucsSwExtUtilityFsmTaskEntry 4 }

cucsSwExtUtilityFsmTaskFlags OBJECT-TYPE
    SYNTAX       CucsFsmFlags
    MAX-ACCESS   read-only
    STATUS       current
    DESCRIPTION
        "Cisco UCS sw:ExtUtilityFsmTask:flags managed object property"
    ::= { cucsSwExtUtilityFsmTaskEntry 5 }

cucsSwExtUtilityFsmTaskItem OBJECT-TYPE
    SYNTAX       CucsSwExtUtilityFsmTaskItem
    MAX-ACCESS   read-only
    STATUS       current
    DESCRIPTION
        "Cisco UCS sw:ExtUtilityFsmTask:item managed object property"
    ::= { cucsSwExtUtilityFsmTaskEntry 6 }

cucsSwExtUtilityFsmTaskSeqId OBJECT-TYPE
    SYNTAX       Gauge32
    MAX-ACCESS   read-only
    STATUS       current
    DESCRIPTION
        "Cisco UCS sw:ExtUtilityFsmTask:seqId managed object property"
    ::= { cucsSwExtUtilityFsmTaskEntry 7 }

cucsSwFabricZoneNsTable OBJECT-TYPE
    SYNTAX           SEQUENCE OF CucsSwFabricZoneNsEntry
    MAX-ACCESS       not-accessible
    STATUS           current
    DESCRIPTION
        "Cisco UCS sw:FabricZoneNs managed object table"
    ::= { cucsSwObjects 50 }

cucsSwFabricZoneNsEntry OBJECT-TYPE
    SYNTAX           CucsSwFabricZoneNsEntry
    MAX-ACCESS       not-accessible
    STATUS           current
    DESCRIPTION
        "Entry for the cucsSwFabricZoneNsTable table."
    INDEX { cucsSwFabricZoneNsInstanceId }
    ::= { cucsSwFabricZoneNsTable 1 }

CucsSwFabricZoneNsEntry ::= SEQUENCE {
    cucsSwFabricZoneNsInstanceId                                     CucsManagedObjectId,
    cucsSwFabricZoneNsDn                                             CucsManagedObjectDn,
    cucsSwFabricZoneNsRn                                             SnmpAdminString,
    cucsSwFabricZoneNsAllocStatus                                    CucsSwFabricZoneNsAllocStatus,
    cucsSwFabricZoneNsLimit                                          Gauge32,
    cucsSwFabricZoneNsSwitchId                                       CucsNetworkSwitchId,
    cucsSwFabricZoneNsZoneCount                                      Gauge32,
    cucsSwFabricZoneNsUserZoneAllocStatus                            CucsSwFabricZoneNsUserZoneAllocStatus,
    cucsSwFabricZoneNsUserZoneCount                                  Gauge32,
    cucsSwFabricZoneNsUserZoneLimit                                  Gauge32
}

cucsSwFabricZoneNsInstanceId OBJECT-TYPE
    SYNTAX       CucsManagedObjectId
    MAX-ACCESS   not-accessible
    STATUS       current
    DESCRIPTION
        "Instance identifier of the managed object."
    ::= { cucsSwFabricZoneNsEntry 1 }

cucsSwFabricZoneNsDn OBJECT-TYPE
    SYNTAX       CucsManagedObjectDn
    MAX-ACCESS   read-only
    STATUS       current
    DESCRIPTION
        "Cisco UCS sw:FabricZoneNs:dn managed object property"
    ::= { cucsSwFabricZoneNsEntry 2 }

cucsSwFabricZoneNsRn OBJECT-TYPE
    SYNTAX       SnmpAdminString
    MAX-ACCESS   read-only
    STATUS       current
    DESCRIPTION
        "Cisco UCS sw:FabricZoneNs:rn managed object property"
    ::= { cucsSwFabricZoneNsEntry 3 }

cucsSwFabricZoneNsAllocStatus OBJECT-TYPE
    SYNTAX       CucsSwFabricZoneNsAllocStatus
    MAX-ACCESS   read-only
    STATUS       current
    DESCRIPTION
        "Cisco UCS sw:FabricZoneNs:allocStatus managed object property"
    ::= { cucsSwFabricZoneNsEntry 4 }

cucsSwFabricZoneNsLimit OBJECT-TYPE
    SYNTAX       Gauge32
    MAX-ACCESS   read-only
    STATUS       current
    DESCRIPTION
        "Cisco UCS sw:FabricZoneNs:limit managed object property"
    ::= { cucsSwFabricZoneNsEntry 5 }

cucsSwFabricZoneNsSwitchId OBJECT-TYPE
    SYNTAX       CucsNetworkSwitchId
    MAX-ACCESS   read-only
    STATUS       current
    DESCRIPTION
        "Cisco UCS sw:FabricZoneNs:switchId managed object property"
    ::= { cucsSwFabricZoneNsEntry 6 }

cucsSwFabricZoneNsZoneCount OBJECT-TYPE
    SYNTAX       Gauge32
    MAX-ACCESS   read-only
    STATUS       current
    DESCRIPTION
        "Cisco UCS sw:FabricZoneNs:zoneCount managed object property"
    ::= { cucsSwFabricZoneNsEntry 7 }

cucsSwFabricZoneNsUserZoneAllocStatus OBJECT-TYPE
    SYNTAX       CucsSwFabricZoneNsUserZoneAllocStatus
    MAX-ACCESS   read-only
    STATUS       current
    DESCRIPTION
        "Cisco UCS sw:FabricZoneNs:userZoneAllocStatus
        managed object property"
    ::= { cucsSwFabricZoneNsEntry 8 }

cucsSwFabricZoneNsUserZoneCount OBJECT-TYPE
    SYNTAX       Gauge32
    MAX-ACCESS   read-only
    STATUS       current
    DESCRIPTION
        "Cisco UCS sw:FabricZoneNs:userZoneCount managed object property"
    ::= { cucsSwFabricZoneNsEntry 9 }

cucsSwFabricZoneNsUserZoneLimit OBJECT-TYPE
    SYNTAX       Gauge32
    MAX-ACCESS   read-only
    STATUS       current
    DESCRIPTION
        "Cisco UCS sw:FabricZoneNs:userZoneLimit managed object property"
    ::= { cucsSwFabricZoneNsEntry 10 }

cucsSwFabricZoneNsOverrideTable OBJECT-TYPE
    SYNTAX           SEQUENCE OF CucsSwFabricZoneNsOverrideEntry
    MAX-ACCESS       not-accessible
    STATUS           current
    DESCRIPTION
        "Cisco UCS sw:FabricZoneNsOverride managed object table"
    ::= { cucsSwObjects 51 }

cucsSwFabricZoneNsOverrideEntry OBJECT-TYPE
    SYNTAX           CucsSwFabricZoneNsOverrideEntry
    MAX-ACCESS       not-accessible
    STATUS           current
    DESCRIPTION
        "Entry for the cucsSwFabricZoneNsOverrideTable table."
    INDEX { cucsSwFabricZoneNsOverrideInstanceId }
    ::= { cucsSwFabricZoneNsOverrideTable 1 }

CucsSwFabricZoneNsOverrideEntry ::= SEQUENCE {
    cucsSwFabricZoneNsOverrideInstanceId                             CucsManagedObjectId,
    cucsSwFabricZoneNsOverrideDn                                     CucsManagedObjectDn,
    cucsSwFabricZoneNsOverrideRn                                     SnmpAdminString,
    cucsSwFabricZoneNsOverrideLimit                                  Gauge32
}

cucsSwFabricZoneNsOverrideInstanceId OBJECT-TYPE
    SYNTAX       CucsManagedObjectId
    MAX-ACCESS   not-accessible
    STATUS       current
    DESCRIPTION
        "Instance identifier of the managed object."
    ::= { cucsSwFabricZoneNsOverrideEntry 1 }

cucsSwFabricZoneNsOverrideDn OBJECT-TYPE
    SYNTAX       CucsManagedObjectDn
    MAX-ACCESS   read-only
    STATUS       current
    DESCRIPTION
        "Cisco UCS sw:FabricZoneNsOverride:dn managed object property"
    ::= { cucsSwFabricZoneNsOverrideEntry 2 }

cucsSwFabricZoneNsOverrideRn OBJECT-TYPE
    SYNTAX       SnmpAdminString
    MAX-ACCESS   read-only
    STATUS       current
    DESCRIPTION
        "Cisco UCS sw:FabricZoneNsOverride:rn managed object property"
    ::= { cucsSwFabricZoneNsOverrideEntry 3 }

cucsSwFabricZoneNsOverrideLimit OBJECT-TYPE
    SYNTAX       Gauge32
    MAX-ACCESS   read-only
    STATUS       current
    DESCRIPTION
        "Cisco UCS sw:FabricZoneNsOverride:limit managed object property"
    ::= { cucsSwFabricZoneNsOverrideEntry 4 }

cucsSwFcEndpointTable OBJECT-TYPE
    SYNTAX           SEQUENCE OF CucsSwFcEndpointEntry
    MAX-ACCESS       not-accessible
    STATUS           current
    DESCRIPTION
        "Cisco UCS sw:FcEndpoint managed object table"
    ::= { cucsSwObjects 89 }

cucsSwFcEndpointEntry OBJECT-TYPE
    SYNTAX           CucsSwFcEndpointEntry
    MAX-ACCESS       not-accessible
    STATUS           current
    DESCRIPTION
        "Entry for the cucsSwFcEndpointTable table."
    INDEX { cucsSwFcEndpointInstanceId }
    ::= { cucsSwFcEndpointTable 1 }

CucsSwFcEndpointEntry ::= SEQUENCE {
    cucsSwFcEndpointInstanceId                                       CucsManagedObjectId,
    cucsSwFcEndpointDn                                               CucsManagedObjectDn,
    cucsSwFcEndpointRn                                               SnmpAdminString,
    cucsSwFcEndpointEpDn                                             SnmpAdminString,
    cucsSwFcEndpointLc                                               CucsSwFcZoneMemberLc,
    cucsSwFcEndpointName                                             SnmpAdminString,
    cucsSwFcEndpointPeerDn                                           SnmpAdminString,
    cucsSwFcEndpointWwpn                                             SnmpAdminString
}

cucsSwFcEndpointInstanceId OBJECT-TYPE
    SYNTAX       CucsManagedObjectId
    MAX-ACCESS   not-accessible
    STATUS       current
    DESCRIPTION
        "Instance identifier of the managed object."
    ::= { cucsSwFcEndpointEntry 1 }

cucsSwFcEndpointDn OBJECT-TYPE
    SYNTAX       CucsManagedObjectDn
    MAX-ACCESS   read-only
    STATUS       current
    DESCRIPTION
        "Cisco UCS sw:FcEndpoint:dn managed object property"
    ::= { cucsSwFcEndpointEntry 2 }

cucsSwFcEndpointRn OBJECT-TYPE
    SYNTAX       SnmpAdminString
    MAX-ACCESS   read-only
    STATUS       current
    DESCRIPTION
        "Cisco UCS sw:FcEndpoint:rn managed object property"
    ::= { cucsSwFcEndpointEntry 3 }

cucsSwFcEndpointEpDn OBJECT-TYPE
    SYNTAX       SnmpAdminString
    MAX-ACCESS   read-only
    STATUS       current
    DESCRIPTION
        "Cisco UCS sw:FcEndpoint:epDn managed object property"
    ::= { cucsSwFcEndpointEntry 4 }

cucsSwFcEndpointLc OBJECT-TYPE
    SYNTAX       CucsSwFcZoneMemberLc
    MAX-ACCESS   read-only
    STATUS       current
    DESCRIPTION
        "Cisco UCS sw:FcEndpoint:lc managed object property"
    ::= { cucsSwFcEndpointEntry 5 }

cucsSwFcEndpointName OBJECT-TYPE
    SYNTAX       SnmpAdminString
    MAX-ACCESS   read-only
    STATUS       current
    DESCRIPTION
        "Cisco UCS sw:FcEndpoint:name managed object property"
    ::= { cucsSwFcEndpointEntry 6 }

cucsSwFcEndpointPeerDn OBJECT-TYPE
    SYNTAX       SnmpAdminString
    MAX-ACCESS   read-only
    STATUS       current
    DESCRIPTION
        "Cisco UCS sw:FcEndpoint:peerDn managed object property"
    ::= { cucsSwFcEndpointEntry 7 }

cucsSwFcEndpointWwpn OBJECT-TYPE
    SYNTAX       SnmpAdminString
    MAX-ACCESS   read-only
    STATUS       current
    DESCRIPTION
        "Cisco UCS sw:FcEndpoint:wwpn managed object property"
    ::= { cucsSwFcEndpointEntry 8 }

cucsSwFcEstcEpTable OBJECT-TYPE
    SYNTAX           SEQUENCE OF CucsSwFcEstcEpEntry
    MAX-ACCESS       not-accessible
    STATUS           current
    DESCRIPTION
        "Cisco UCS sw:FcEstcEp managed object table"
    ::= { cucsSwObjects 17 }

cucsSwFcEstcEpEntry OBJECT-TYPE
    SYNTAX           CucsSwFcEstcEpEntry
    MAX-ACCESS       not-accessible
    STATUS           current
    DESCRIPTION
        "Entry for the cucsSwFcEstcEpTable table."
    INDEX { cucsSwFcEstcEpInstanceId }
    ::= { cucsSwFcEstcEpTable 1 }

CucsSwFcEstcEpEntry ::= SEQUENCE {
    cucsSwFcEstcEpInstanceId                                         CucsManagedObjectId,
    cucsSwFcEstcEpDn                                                 CucsManagedObjectDn,
    cucsSwFcEstcEpRn                                                 SnmpAdminString,
    cucsSwFcEstcEpAdminState                                         CucsFabricAdminState,
    cucsSwFcEstcEpChassisId                                          Gauge32,
    cucsSwFcEstcEpEpDn                                               SnmpAdminString,
    cucsSwFcEstcEpIfRole                                             CucsNetworkPortRole,
    cucsSwFcEstcEpIfType                                             CucsSwPIoEpIfType,
    cucsSwFcEstcEpLocale                                             CucsSwEstcEpLocale,
    cucsSwFcEstcEpName                                               SnmpAdminString,
    cucsSwFcEstcEpPeerDn                                             SnmpAdminString,
    cucsSwFcEstcEpPeerPortId                                         Gauge32,
    cucsSwFcEstcEpPeerSlotId                                         Gauge32,
    cucsSwFcEstcEpPortId                                             Gauge32,
    cucsSwFcEstcEpPortVsanId                                         Gauge32,
    cucsSwFcEstcEpSlotId                                             Gauge32,
    cucsSwFcEstcEpSwitchId                                           CucsNetworkSwitchId,
    cucsSwFcEstcEpTransport                                          CucsSwFcEstcEpTransport,
    cucsSwFcEstcEpType                                               CucsNetworkConnectionType,
    cucsSwFcEstcEpPeerChassisId                                      Gauge32,
    cucsSwFcEstcEpLc                                                 CucsSwPIoEpLc,
    cucsSwFcEstcEpFillPattern                                        CucsFabricFillPattern,
    cucsSwFcEstcEpAggrPortId                                         Gauge32,
    cucsSwFcEstcEpPeerAggrPortId                                     Gauge32
}

cucsSwFcEstcEpInstanceId OBJECT-TYPE
    SYNTAX       CucsManagedObjectId
    MAX-ACCESS   not-accessible
    STATUS       current
    DESCRIPTION
        "Instance identifier of the managed object."
    ::= { cucsSwFcEstcEpEntry 1 }

cucsSwFcEstcEpDn OBJECT-TYPE
    SYNTAX       CucsManagedObjectDn
    MAX-ACCESS   read-only
    STATUS       current
    DESCRIPTION
        "Cisco UCS sw:FcEstcEp:dn managed object property"
    ::= { cucsSwFcEstcEpEntry 2 }

cucsSwFcEstcEpRn OBJECT-TYPE
    SYNTAX       SnmpAdminString
    MAX-ACCESS   read-only
    STATUS       current
    DESCRIPTION
        "Cisco UCS sw:FcEstcEp:rn managed object property"
    ::= { cucsSwFcEstcEpEntry 3 }

cucsSwFcEstcEpAdminState OBJECT-TYPE
    SYNTAX       CucsFabricAdminState
    MAX-ACCESS   read-only
    STATUS       current
    DESCRIPTION
        "Cisco UCS sw:FcEstcEp:adminState managed object property"
    ::= { cucsSwFcEstcEpEntry 4 }

cucsSwFcEstcEpChassisId OBJECT-TYPE
    SYNTAX       Gauge32
    MAX-ACCESS   read-only
    STATUS       current
    DESCRIPTION
        "Cisco UCS sw:FcEstcEp:chassisId managed object property"
    ::= { cucsSwFcEstcEpEntry 5 }

cucsSwFcEstcEpEpDn OBJECT-TYPE
    SYNTAX       SnmpAdminString
    MAX-ACCESS   read-only
    STATUS       current
    DESCRIPTION
        "Cisco UCS sw:FcEstcEp:epDn managed object property"
    ::= { cucsSwFcEstcEpEntry 6 }

cucsSwFcEstcEpIfRole OBJECT-TYPE
    SYNTAX       CucsNetworkPortRole
    MAX-ACCESS   read-only
    STATUS       current
    DESCRIPTION
        "Cisco UCS sw:FcEstcEp:ifRole managed object property"
    ::= { cucsSwFcEstcEpEntry 7 }

cucsSwFcEstcEpIfType OBJECT-TYPE
    SYNTAX       CucsSwPIoEpIfType
    MAX-ACCESS   read-only
    STATUS       current
    DESCRIPTION
        "Cisco UCS sw:FcEstcEp:ifType managed object property"
    ::= { cucsSwFcEstcEpEntry 8 }

cucsSwFcEstcEpLocale OBJECT-TYPE
    SYNTAX       CucsSwEstcEpLocale
    MAX-ACCESS   read-only
    STATUS       current
    DESCRIPTION
        "Cisco UCS sw:FcEstcEp:locale managed object property"
    ::= { cucsSwFcEstcEpEntry 9 }

cucsSwFcEstcEpName OBJECT-TYPE
    SYNTAX       SnmpAdminString
    MAX-ACCESS   read-only
    STATUS       current
    DESCRIPTION
        "Cisco UCS sw:FcEstcEp:name managed object property"
    ::= { cucsSwFcEstcEpEntry 10 }

cucsSwFcEstcEpPeerDn OBJECT-TYPE
    SYNTAX       SnmpAdminString
    MAX-ACCESS   read-only
    STATUS       current
    DESCRIPTION
        "Cisco UCS sw:FcEstcEp:peerDn managed object property"
    ::= { cucsSwFcEstcEpEntry 11 }

cucsSwFcEstcEpPeerPortId OBJECT-TYPE
    SYNTAX       Gauge32
    MAX-ACCESS   read-only
    STATUS       current
    DESCRIPTION
        "Cisco UCS sw:FcEstcEp:peerPortId managed object property"
    ::= { cucsSwFcEstcEpEntry 12 }

cucsSwFcEstcEpPeerSlotId OBJECT-TYPE
    SYNTAX       Gauge32
    MAX-ACCESS   read-only
    STATUS       current
    DESCRIPTION
        "Cisco UCS sw:FcEstcEp:peerSlotId managed object property"
    ::= { cucsSwFcEstcEpEntry 13 }

cucsSwFcEstcEpPortId OBJECT-TYPE
    SYNTAX       Gauge32
    MAX-ACCESS   read-only
    STATUS       current
    DESCRIPTION
        "Cisco UCS sw:FcEstcEp:portId managed object property"
    ::= { cucsSwFcEstcEpEntry 14 }

cucsSwFcEstcEpPortVsanId OBJECT-TYPE
    SYNTAX       Gauge32
    MAX-ACCESS   read-only
    STATUS       current
    DESCRIPTION
        "Cisco UCS sw:FcEstcEp:portVsanId managed object property"
    ::= { cucsSwFcEstcEpEntry 15 }

cucsSwFcEstcEpSlotId OBJECT-TYPE
    SYNTAX       Gauge32
    MAX-ACCESS   read-only
    STATUS       current
    DESCRIPTION
        "Cisco UCS sw:FcEstcEp:slotId managed object property"
    ::= { cucsSwFcEstcEpEntry 16 }

cucsSwFcEstcEpSwitchId OBJECT-TYPE
    SYNTAX       CucsNetworkSwitchId
    MAX-ACCESS   read-only
    STATUS       current
    DESCRIPTION
        "Cisco UCS sw:FcEstcEp:switchId managed object property"
    ::= { cucsSwFcEstcEpEntry 17 }

cucsSwFcEstcEpTransport OBJECT-TYPE
    SYNTAX       CucsSwFcEstcEpTransport
    MAX-ACCESS   read-only
    STATUS       current
    DESCRIPTION
        "Cisco UCS sw:FcEstcEp:transport managed object property"
    ::= { cucsSwFcEstcEpEntry 18 }

cucsSwFcEstcEpType OBJECT-TYPE
    SYNTAX       CucsNetworkConnectionType
    MAX-ACCESS   read-only
    STATUS       current
    DESCRIPTION
        "Cisco UCS sw:FcEstcEp:type managed object property"
    ::= { cucsSwFcEstcEpEntry 19 }

cucsSwFcEstcEpPeerChassisId OBJECT-TYPE
    SYNTAX       Gauge32
    MAX-ACCESS   read-only
    STATUS       current
    DESCRIPTION
        "Cisco UCS sw:FcEstcEp:peerChassisId managed object property"
    ::= { cucsSwFcEstcEpEntry 20 }

cucsSwFcEstcEpLc OBJECT-TYPE
    SYNTAX       CucsSwPIoEpLc
    MAX-ACCESS   read-only
    STATUS       current
    DESCRIPTION
        "Cisco UCS sw:FcEstcEp:lc managed object property"
    ::= { cucsSwFcEstcEpEntry 21 }

cucsSwFcEstcEpFillPattern OBJECT-TYPE
    SYNTAX       CucsFabricFillPattern
    MAX-ACCESS   read-only
    STATUS       current
    DESCRIPTION
        "Cisco UCS sw:FcEstcEp:fillPattern managed object property"
    ::= { cucsSwFcEstcEpEntry 22 }

cucsSwFcEstcEpAggrPortId OBJECT-TYPE
    SYNTAX       Gauge32
    MAX-ACCESS   read-only
    STATUS       current
    DESCRIPTION
        "Cisco UCS sw:FcEstcEp:aggrPortId managed object property"
    ::= { cucsSwFcEstcEpEntry 23 }

cucsSwFcEstcEpPeerAggrPortId OBJECT-TYPE
    SYNTAX       Gauge32
    MAX-ACCESS   read-only
    STATUS       current
    DESCRIPTION
        "Cisco UCS sw:FcEstcEp:peerAggrPortId managed object property"
    ::= { cucsSwFcEstcEpEntry 24 }

cucsSwFcMonTable OBJECT-TYPE
    SYNTAX           SEQUENCE OF CucsSwFcMonEntry
    MAX-ACCESS       not-accessible
    STATUS           current
    DESCRIPTION
        "Cisco UCS sw:FcMon managed object table"
    ::= { cucsSwObjects 18 }

cucsSwFcMonEntry OBJECT-TYPE
    SYNTAX           CucsSwFcMonEntry
    MAX-ACCESS       not-accessible
    STATUS           current
    DESCRIPTION
        "Entry for the cucsSwFcMonTable table."
    INDEX { cucsSwFcMonInstanceId }
    ::= { cucsSwFcMonTable 1 }

CucsSwFcMonEntry ::= SEQUENCE {
    cucsSwFcMonInstanceId                                            CucsManagedObjectId,
    cucsSwFcMonDn                                                    CucsManagedObjectDn,
    cucsSwFcMonRn                                                    SnmpAdminString,
    cucsSwFcMonAdminState                                            CucsSwMonAdminState,
    cucsSwFcMonFsmDescr                                              SnmpAdminString,
    cucsSwFcMonFsmPrev                                               SnmpAdminString,
    cucsSwFcMonFsmProgr                                              Gauge32,
    cucsSwFcMonFsmRmtInvErrCode                                      Gauge32,
    cucsSwFcMonFsmRmtInvErrDescr                                     SnmpAdminString,
    cucsSwFcMonFsmRmtInvRslt                                         CucsConditionRemoteInvRslt,
    cucsSwFcMonFsmStageDescr                                         SnmpAdminString,
    cucsSwFcMonFsmStamp                                              DateAndTime,
    cucsSwFcMonFsmStatus                                             SnmpAdminString,
    cucsSwFcMonFsmTry                                                Gauge32,
    cucsSwFcMonLifeCycle                                             CucsSwMonLifeCycle,
    cucsSwFcMonName                                                  SnmpAdminString,
    cucsSwFcMonSession                                               Gauge32,
    cucsSwFcMonSwitchId                                              CucsNetworkSwitchId,
    cucsSwFcMonTransport                                             CucsSwFcMonTransport,
    cucsSwFcMonType                                                  CucsSwFcMonType,
    cucsSwFcMonHasLastDest                                           TruthValue,
    cucsSwFcMonPeerDn                                                SnmpAdminString
}

cucsSwFcMonInstanceId OBJECT-TYPE
    SYNTAX       CucsManagedObjectId
    MAX-ACCESS   not-accessible
    STATUS       current
    DESCRIPTION
        "Instance identifier of the managed object."
    ::= { cucsSwFcMonEntry 1 }

cucsSwFcMonDn OBJECT-TYPE
    SYNTAX       CucsManagedObjectDn
    MAX-ACCESS   read-only
    STATUS       current
    DESCRIPTION
        "Cisco UCS sw:FcMon:dn managed object property"
    ::= { cucsSwFcMonEntry 2 }

cucsSwFcMonRn OBJECT-TYPE
    SYNTAX       SnmpAdminString
    MAX-ACCESS   read-only
    STATUS       current
    DESCRIPTION
        "Cisco UCS sw:FcMon:rn managed object property"
    ::= { cucsSwFcMonEntry 3 }

cucsSwFcMonAdminState OBJECT-TYPE
    SYNTAX       CucsSwMonAdminState
    MAX-ACCESS   read-only
    STATUS       current
    DESCRIPTION
        "Cisco UCS sw:FcMon:adminState managed object property"
    ::= { cucsSwFcMonEntry 4 }

cucsSwFcMonFsmDescr OBJECT-TYPE
    SYNTAX       SnmpAdminString
    MAX-ACCESS   read-only
    STATUS       current
    DESCRIPTION
        "Cisco UCS sw:FcMon:fsmDescr managed object property"
    ::= { cucsSwFcMonEntry 5 }

cucsSwFcMonFsmPrev OBJECT-TYPE
    SYNTAX       SnmpAdminString
    MAX-ACCESS   read-only
    STATUS       current
    DESCRIPTION
        "Cisco UCS sw:FcMon:fsmPrev managed object property"
    ::= { cucsSwFcMonEntry 6 }

cucsSwFcMonFsmProgr OBJECT-TYPE
    SYNTAX       Gauge32
    MAX-ACCESS   read-only
    STATUS       current
    DESCRIPTION
        "Cisco UCS sw:FcMon:fsmProgr managed object property"
    ::= { cucsSwFcMonEntry 7 }

cucsSwFcMonFsmRmtInvErrCode OBJECT-TYPE
    SYNTAX       Gauge32
    MAX-ACCESS   read-only
    STATUS       current
    DESCRIPTION
        "Cisco UCS sw:FcMon:fsmRmtInvErrCode managed object property"
    ::= { cucsSwFcMonEntry 8 }

cucsSwFcMonFsmRmtInvErrDescr OBJECT-TYPE
    SYNTAX       SnmpAdminString
    MAX-ACCESS   read-only
    STATUS       current
    DESCRIPTION
        "Cisco UCS sw:FcMon:fsmRmtInvErrDescr managed object property"
    ::= { cucsSwFcMonEntry 9 }

cucsSwFcMonFsmRmtInvRslt OBJECT-TYPE
    SYNTAX       CucsConditionRemoteInvRslt
    MAX-ACCESS   read-only
    STATUS       current
    DESCRIPTION
        "Cisco UCS sw:FcMon:fsmRmtInvRslt managed object property"
    ::= { cucsSwFcMonEntry 10 }

cucsSwFcMonFsmStageDescr OBJECT-TYPE
    SYNTAX       SnmpAdminString
    MAX-ACCESS   read-only
    STATUS       current
    DESCRIPTION
        "Cisco UCS sw:FcMon:fsmStageDescr managed object property"
    ::= { cucsSwFcMonEntry 11 }

cucsSwFcMonFsmStamp OBJECT-TYPE
    SYNTAX       DateAndTime
    MAX-ACCESS   read-only
    STATUS       current
    DESCRIPTION
        "Cisco UCS sw:FcMon:fsmStamp managed object property"
    ::= { cucsSwFcMonEntry 12 }

cucsSwFcMonFsmStatus OBJECT-TYPE
    SYNTAX       SnmpAdminString
    MAX-ACCESS   read-only
    STATUS       current
    DESCRIPTION
        "Cisco UCS sw:FcMon:fsmStatus managed object property"
    ::= { cucsSwFcMonEntry 13 }

cucsSwFcMonFsmTry OBJECT-TYPE
    SYNTAX       Gauge32
    MAX-ACCESS   read-only
    STATUS       current
    DESCRIPTION
        "Cisco UCS sw:FcMon:fsmTry managed object property"
    ::= { cucsSwFcMonEntry 14 }

cucsSwFcMonLifeCycle OBJECT-TYPE
    SYNTAX       CucsSwMonLifeCycle
    MAX-ACCESS   read-only
    STATUS       current
    DESCRIPTION
        "Cisco UCS sw:FcMon:lifeCycle managed object property"
    ::= { cucsSwFcMonEntry 15 }

cucsSwFcMonName OBJECT-TYPE
    SYNTAX       SnmpAdminString
    MAX-ACCESS   read-only
    STATUS       current
    DESCRIPTION
        "Cisco UCS sw:FcMon:name managed object property"
    ::= { cucsSwFcMonEntry 16 }

cucsSwFcMonSession OBJECT-TYPE
    SYNTAX       Gauge32
    MAX-ACCESS   read-only
    STATUS       current
    DESCRIPTION
        "Cisco UCS sw:FcMon:session managed object property"
    ::= { cucsSwFcMonEntry 17 }

cucsSwFcMonSwitchId OBJECT-TYPE
    SYNTAX       CucsNetworkSwitchId
    MAX-ACCESS   read-only
    STATUS       current
    DESCRIPTION
        "Cisco UCS sw:FcMon:switchId managed object property"
    ::= { cucsSwFcMonEntry 18 }

cucsSwFcMonTransport OBJECT-TYPE
    SYNTAX       CucsSwFcMonTransport
    MAX-ACCESS   read-only
    STATUS       current
    DESCRIPTION
        "Cisco UCS sw:FcMon:transport managed object property"
    ::= { cucsSwFcMonEntry 19 }

cucsSwFcMonType OBJECT-TYPE
    SYNTAX       CucsSwFcMonType
    MAX-ACCESS   read-only
    STATUS       current
    DESCRIPTION
        "Cisco UCS sw:FcMon:type managed object property"
    ::= { cucsSwFcMonEntry 20 }

cucsSwFcMonHasLastDest OBJECT-TYPE
    SYNTAX       TruthValue
    MAX-ACCESS   read-only
    STATUS       current
    DESCRIPTION
        "Cisco UCS sw:FcMon:hasLastDest managed object property"
    ::= { cucsSwFcMonEntry 21 }

cucsSwFcMonPeerDn OBJECT-TYPE
    SYNTAX       SnmpAdminString
    MAX-ACCESS   read-only
    STATUS       current
    DESCRIPTION
        "Cisco UCS sw:FcMon:peerDn managed object property"
    ::= { cucsSwFcMonEntry 22 }

cucsSwFcMonDestEpTable OBJECT-TYPE
    SYNTAX           SEQUENCE OF CucsSwFcMonDestEpEntry
    MAX-ACCESS       not-accessible
    STATUS           current
    DESCRIPTION
        "Cisco UCS sw:FcMonDestEp managed object table"
    ::= { cucsSwObjects 19 }

cucsSwFcMonDestEpEntry OBJECT-TYPE
    SYNTAX           CucsSwFcMonDestEpEntry
    MAX-ACCESS       not-accessible
    STATUS           current
    DESCRIPTION
        "Entry for the cucsSwFcMonDestEpTable table."
    INDEX { cucsSwFcMonDestEpInstanceId }
    ::= { cucsSwFcMonDestEpTable 1 }

CucsSwFcMonDestEpEntry ::= SEQUENCE {
    cucsSwFcMonDestEpInstanceId                                      CucsManagedObjectId,
    cucsSwFcMonDestEpDn                                              CucsManagedObjectDn,
    cucsSwFcMonDestEpRn                                              SnmpAdminString,
    cucsSwFcMonDestEpAdminState                                      CucsFabricAdminState,
    cucsSwFcMonDestEpChassisId                                       Gauge32,
    cucsSwFcMonDestEpEpDn                                            SnmpAdminString,
    cucsSwFcMonDestEpIfRole                                          CucsNetworkPortRole,
    cucsSwFcMonDestEpIfType                                          CucsSwPIoEpIfType,
    cucsSwFcMonDestEpLocale                                          CucsNetworkLocale,
    cucsSwFcMonDestEpName                                            SnmpAdminString,
    cucsSwFcMonDestEpPeerDn                                          SnmpAdminString,
    cucsSwFcMonDestEpPeerPortId                                      Gauge32,
    cucsSwFcMonDestEpPeerSlotId                                      Gauge32,
    cucsSwFcMonDestEpPortId                                          Gauge32,
    cucsSwFcMonDestEpSlotId                                          Gauge32,
    cucsSwFcMonDestEpSwitchId                                        CucsNetworkSwitchId,
    cucsSwFcMonDestEpTransport                                       CucsSwFcMonDestEpTransport,
    cucsSwFcMonDestEpType                                            CucsNetworkConnectionType,
    cucsSwFcMonDestEpPeerChassisId                                   Gauge32,
    cucsSwFcMonDestEpLc                                              CucsSwPIoEpLc,
    cucsSwFcMonDestEpAdminSpeed                                      CucsPortSpeed,
    cucsSwFcMonDestEpAggrPortId                                      Gauge32,
    cucsSwFcMonDestEpPeerAggrPortId                                  Gauge32
}

cucsSwFcMonDestEpInstanceId OBJECT-TYPE
    SYNTAX       CucsManagedObjectId
    MAX-ACCESS   not-accessible
    STATUS       current
    DESCRIPTION
        "Instance identifier of the managed object."
    ::= { cucsSwFcMonDestEpEntry 1 }

cucsSwFcMonDestEpDn OBJECT-TYPE
    SYNTAX       CucsManagedObjectDn
    MAX-ACCESS   read-only
    STATUS       current
    DESCRIPTION
        "Cisco UCS sw:FcMonDestEp:dn managed object property"
    ::= { cucsSwFcMonDestEpEntry 2 }

cucsSwFcMonDestEpRn OBJECT-TYPE
    SYNTAX       SnmpAdminString
    MAX-ACCESS   read-only
    STATUS       current
    DESCRIPTION
        "Cisco UCS sw:FcMonDestEp:rn managed object property"
    ::= { cucsSwFcMonDestEpEntry 3 }

cucsSwFcMonDestEpAdminState OBJECT-TYPE
    SYNTAX       CucsFabricAdminState
    MAX-ACCESS   read-only
    STATUS       current
    DESCRIPTION
        "Cisco UCS sw:FcMonDestEp:adminState managed object property"
    ::= { cucsSwFcMonDestEpEntry 4 }

cucsSwFcMonDestEpChassisId OBJECT-TYPE
    SYNTAX       Gauge32
    MAX-ACCESS   read-only
    STATUS       current
    DESCRIPTION
        "Cisco UCS sw:FcMonDestEp:chassisId managed object property"
    ::= { cucsSwFcMonDestEpEntry 5 }

cucsSwFcMonDestEpEpDn OBJECT-TYPE
    SYNTAX       SnmpAdminString
    MAX-ACCESS   read-only
    STATUS       current
    DESCRIPTION
        "Cisco UCS sw:FcMonDestEp:epDn managed object property"
    ::= { cucsSwFcMonDestEpEntry 6 }

cucsSwFcMonDestEpIfRole OBJECT-TYPE
    SYNTAX       CucsNetworkPortRole
    MAX-ACCESS   read-only
    STATUS       current
    DESCRIPTION
        "Cisco UCS sw:FcMonDestEp:ifRole managed object property"
    ::= { cucsSwFcMonDestEpEntry 7 }

cucsSwFcMonDestEpIfType OBJECT-TYPE
    SYNTAX       CucsSwPIoEpIfType
    MAX-ACCESS   read-only
    STATUS       current
    DESCRIPTION
        "Cisco UCS sw:FcMonDestEp:ifType managed object property"
    ::= { cucsSwFcMonDestEpEntry 8 }

cucsSwFcMonDestEpLocale OBJECT-TYPE
    SYNTAX       CucsNetworkLocale
    MAX-ACCESS   read-only
    STATUS       current
    DESCRIPTION
        "Cisco UCS sw:FcMonDestEp:locale managed object property"
    ::= { cucsSwFcMonDestEpEntry 9 }

cucsSwFcMonDestEpName OBJECT-TYPE
    SYNTAX       SnmpAdminString
    MAX-ACCESS   read-only
    STATUS       current
    DESCRIPTION
        "Cisco UCS sw:FcMonDestEp:name managed object property"
    ::= { cucsSwFcMonDestEpEntry 10 }

cucsSwFcMonDestEpPeerDn OBJECT-TYPE
    SYNTAX       SnmpAdminString
    MAX-ACCESS   read-only
    STATUS       current
    DESCRIPTION
        "Cisco UCS sw:FcMonDestEp:peerDn managed object property"
    ::= { cucsSwFcMonDestEpEntry 11 }

cucsSwFcMonDestEpPeerPortId OBJECT-TYPE
    SYNTAX       Gauge32
    MAX-ACCESS   read-only
    STATUS       current
    DESCRIPTION
        "Cisco UCS sw:FcMonDestEp:peerPortId managed object property"
    ::= { cucsSwFcMonDestEpEntry 12 }

cucsSwFcMonDestEpPeerSlotId OBJECT-TYPE
    SYNTAX       Gauge32
    MAX-ACCESS   read-only
    STATUS       current
    DESCRIPTION
        "Cisco UCS sw:FcMonDestEp:peerSlotId managed object property"
    ::= { cucsSwFcMonDestEpEntry 13 }

cucsSwFcMonDestEpPortId OBJECT-TYPE
    SYNTAX       Gauge32
    MAX-ACCESS   read-only
    STATUS       current
    DESCRIPTION
        "Cisco UCS sw:FcMonDestEp:portId managed object property"
    ::= { cucsSwFcMonDestEpEntry 14 }

cucsSwFcMonDestEpSlotId OBJECT-TYPE
    SYNTAX       Gauge32
    MAX-ACCESS   read-only
    STATUS       current
    DESCRIPTION
        "Cisco UCS sw:FcMonDestEp:slotId managed object property"
    ::= { cucsSwFcMonDestEpEntry 15 }

cucsSwFcMonDestEpSwitchId OBJECT-TYPE
    SYNTAX       CucsNetworkSwitchId
    MAX-ACCESS   read-only
    STATUS       current
    DESCRIPTION
        "Cisco UCS sw:FcMonDestEp:switchId managed object property"
    ::= { cucsSwFcMonDestEpEntry 16 }

cucsSwFcMonDestEpTransport OBJECT-TYPE
    SYNTAX       CucsSwFcMonDestEpTransport
    MAX-ACCESS   read-only
    STATUS       current
    DESCRIPTION
        "Cisco UCS sw:FcMonDestEp:transport managed object property"
    ::= { cucsSwFcMonDestEpEntry 17 }

cucsSwFcMonDestEpType OBJECT-TYPE
    SYNTAX       CucsNetworkConnectionType
    MAX-ACCESS   read-only
    STATUS       current
    DESCRIPTION
        "Cisco UCS sw:FcMonDestEp:type managed object property"
    ::= { cucsSwFcMonDestEpEntry 18 }

cucsSwFcMonDestEpPeerChassisId OBJECT-TYPE
    SYNTAX       Gauge32
    MAX-ACCESS   read-only
    STATUS       current
    DESCRIPTION
        "Cisco UCS sw:FcMonDestEp:peerChassisId managed object property"
    ::= { cucsSwFcMonDestEpEntry 19 }

cucsSwFcMonDestEpLc OBJECT-TYPE
    SYNTAX       CucsSwPIoEpLc
    MAX-ACCESS   read-only
    STATUS       current
    DESCRIPTION
        "Cisco UCS sw:FcMonDestEp:lc managed object property"
    ::= { cucsSwFcMonDestEpEntry 20 }

cucsSwFcMonDestEpAdminSpeed OBJECT-TYPE
    SYNTAX       CucsPortSpeed
    MAX-ACCESS   read-only
    STATUS       current
    DESCRIPTION
        "Cisco UCS sw:FcMonDestEp:adminSpeed managed object property"
    ::= { cucsSwFcMonDestEpEntry 21 }

cucsSwFcMonDestEpAggrPortId OBJECT-TYPE
    SYNTAX       Gauge32
    MAX-ACCESS   read-only
    STATUS       current
    DESCRIPTION
        "Cisco UCS sw:FcMonDestEp:aggrPortId managed object property"
    ::= { cucsSwFcMonDestEpEntry 22 }

cucsSwFcMonDestEpPeerAggrPortId OBJECT-TYPE
    SYNTAX       Gauge32
    MAX-ACCESS   read-only
    STATUS       current
    DESCRIPTION
        "Cisco UCS sw:FcMonDestEp:peerAggrPortId managed object property"
    ::= { cucsSwFcMonDestEpEntry 23 }

cucsSwFcMonFsmTable OBJECT-TYPE
    SYNTAX           SEQUENCE OF CucsSwFcMonFsmEntry
    MAX-ACCESS       not-accessible
    STATUS           current
    DESCRIPTION
        "Cisco UCS sw:FcMonFsm managed object table"
    ::= { cucsSwObjects 52 }

cucsSwFcMonFsmEntry OBJECT-TYPE
    SYNTAX           CucsSwFcMonFsmEntry
    MAX-ACCESS       not-accessible
    STATUS           current
    DESCRIPTION
        "Entry for the cucsSwFcMonFsmTable table."
    INDEX { cucsSwFcMonFsmInstanceId }
    ::= { cucsSwFcMonFsmTable 1 }

CucsSwFcMonFsmEntry ::= SEQUENCE {
    cucsSwFcMonFsmInstanceId                                         CucsManagedObjectId,
    cucsSwFcMonFsmDn                                                 CucsManagedObjectDn,
    cucsSwFcMonFsmRn                                                 SnmpAdminString,
    cucsSwFcMonFsmCompletionTime                                     DateAndTime,
    cucsSwFcMonFsmCurrentFsm                                         CucsSwFcMonFsmCurrentFsm,
    cucsSwFcMonFsmDescrData                                          SnmpAdminString,
    cucsSwFcMonFsmFsmStatus                                          CucsFsmFsmStageStatus,
    cucsSwFcMonFsmProgress                                           Gauge32,
    cucsSwFcMonFsmRmtErrCode                                         Gauge32,
    cucsSwFcMonFsmRmtErrDescr                                        SnmpAdminString,
    cucsSwFcMonFsmRmtRslt                                            CucsConditionRemoteInvRslt
}

cucsSwFcMonFsmInstanceId OBJECT-TYPE
    SYNTAX       CucsManagedObjectId
    MAX-ACCESS   not-accessible
    STATUS       current
    DESCRIPTION
        "Instance identifier of the managed object."
    ::= { cucsSwFcMonFsmEntry 1 }

cucsSwFcMonFsmDn OBJECT-TYPE
    SYNTAX       CucsManagedObjectDn
    MAX-ACCESS   read-only
    STATUS       current
    DESCRIPTION
        "Cisco UCS sw:FcMonFsm:dn managed object property"
    ::= { cucsSwFcMonFsmEntry 2 }

cucsSwFcMonFsmRn OBJECT-TYPE
    SYNTAX       SnmpAdminString
    MAX-ACCESS   read-only
    STATUS       current
    DESCRIPTION
        "Cisco UCS sw:FcMonFsm:rn managed object property"
    ::= { cucsSwFcMonFsmEntry 3 }

cucsSwFcMonFsmCompletionTime OBJECT-TYPE
    SYNTAX       DateAndTime
    MAX-ACCESS   read-only
    STATUS       current
    DESCRIPTION
        "Cisco UCS sw:FcMonFsm:completionTime managed object property"
    ::= { cucsSwFcMonFsmEntry 4 }

cucsSwFcMonFsmCurrentFsm OBJECT-TYPE
    SYNTAX       CucsSwFcMonFsmCurrentFsm
    MAX-ACCESS   read-only
    STATUS       current
    DESCRIPTION
        "Cisco UCS sw:FcMonFsm:currentFsm managed object property"
    ::= { cucsSwFcMonFsmEntry 5 }

cucsSwFcMonFsmDescrData OBJECT-TYPE
    SYNTAX       SnmpAdminString
    MAX-ACCESS   read-only
    STATUS       current
    DESCRIPTION
        "Cisco UCS sw:FcMonFsm:descr managed object property"
    ::= { cucsSwFcMonFsmEntry 6 }

cucsSwFcMonFsmFsmStatus OBJECT-TYPE
    SYNTAX       CucsFsmFsmStageStatus
    MAX-ACCESS   read-only
    STATUS       current
    DESCRIPTION
        "Cisco UCS sw:FcMonFsm:fsmStatus managed object property"
    ::= { cucsSwFcMonFsmEntry 7 }

cucsSwFcMonFsmProgress OBJECT-TYPE
    SYNTAX       Gauge32
    MAX-ACCESS   read-only
    STATUS       current
    DESCRIPTION
        "Cisco UCS sw:FcMonFsm:progress managed object property"
    ::= { cucsSwFcMonFsmEntry 8 }

cucsSwFcMonFsmRmtErrCode OBJECT-TYPE
    SYNTAX       Gauge32
    MAX-ACCESS   read-only
    STATUS       current
    DESCRIPTION
        "Cisco UCS sw:FcMonFsm:rmtErrCode managed object property"
    ::= { cucsSwFcMonFsmEntry 9 }

cucsSwFcMonFsmRmtErrDescr OBJECT-TYPE
    SYNTAX       SnmpAdminString
    MAX-ACCESS   read-only
    STATUS       current
    DESCRIPTION
        "Cisco UCS sw:FcMonFsm:rmtErrDescr managed object property"
    ::= { cucsSwFcMonFsmEntry 10 }

cucsSwFcMonFsmRmtRslt OBJECT-TYPE
    SYNTAX       CucsConditionRemoteInvRslt
    MAX-ACCESS   read-only
    STATUS       current
    DESCRIPTION
        "Cisco UCS sw:FcMonFsm:rmtRslt managed object property"
    ::= { cucsSwFcMonFsmEntry 11 }

cucsSwFcMonFsmStageTable OBJECT-TYPE
    SYNTAX           SEQUENCE OF CucsSwFcMonFsmStageEntry
    MAX-ACCESS       not-accessible
    STATUS           current
    DESCRIPTION
        "Cisco UCS sw:FcMonFsmStage managed object table"
    ::= { cucsSwObjects 53 }

cucsSwFcMonFsmStageEntry OBJECT-TYPE
    SYNTAX           CucsSwFcMonFsmStageEntry
    MAX-ACCESS       not-accessible
    STATUS           current
    DESCRIPTION
        "Entry for the cucsSwFcMonFsmStageTable table."
    INDEX { cucsSwFcMonFsmStageInstanceId }
    ::= { cucsSwFcMonFsmStageTable 1 }

CucsSwFcMonFsmStageEntry ::= SEQUENCE {
    cucsSwFcMonFsmStageInstanceId                                    CucsManagedObjectId,
    cucsSwFcMonFsmStageDn                                            CucsManagedObjectDn,
    cucsSwFcMonFsmStageRn                                            SnmpAdminString,
    cucsSwFcMonFsmStageDescrData                                     SnmpAdminString,
    cucsSwFcMonFsmStageLastUpdateTime                                DateAndTime,
    cucsSwFcMonFsmStageName                                          CucsSwFcMonFsmStageName,
    cucsSwFcMonFsmStageOrder                                         Gauge32,
    cucsSwFcMonFsmStageRetry                                         Gauge32,
    cucsSwFcMonFsmStageStageStatus                                   CucsFsmFsmStageStatus
}

cucsSwFcMonFsmStageInstanceId OBJECT-TYPE
    SYNTAX       CucsManagedObjectId
    MAX-ACCESS   not-accessible
    STATUS       current
    DESCRIPTION
        "Instance identifier of the managed object."
    ::= { cucsSwFcMonFsmStageEntry 1 }

cucsSwFcMonFsmStageDn OBJECT-TYPE
    SYNTAX       CucsManagedObjectDn
    MAX-ACCESS   read-only
    STATUS       current
    DESCRIPTION
        "Cisco UCS sw:FcMonFsmStage:dn managed object property"
    ::= { cucsSwFcMonFsmStageEntry 2 }

cucsSwFcMonFsmStageRn OBJECT-TYPE
    SYNTAX       SnmpAdminString
    MAX-ACCESS   read-only
    STATUS       current
    DESCRIPTION
        "Cisco UCS sw:FcMonFsmStage:rn managed object property"
    ::= { cucsSwFcMonFsmStageEntry 3 }

cucsSwFcMonFsmStageDescrData OBJECT-TYPE
    SYNTAX       SnmpAdminString
    MAX-ACCESS   read-only
    STATUS       current
    DESCRIPTION
        "Cisco UCS sw:FcMonFsmStage:descr managed object property"
    ::= { cucsSwFcMonFsmStageEntry 4 }

cucsSwFcMonFsmStageLastUpdateTime OBJECT-TYPE
    SYNTAX       DateAndTime
    MAX-ACCESS   read-only
    STATUS       current
    DESCRIPTION
        "Cisco UCS sw:FcMonFsmStage:lastUpdateTime managed
        object property"
    ::= { cucsSwFcMonFsmStageEntry 5 }

cucsSwFcMonFsmStageName OBJECT-TYPE
    SYNTAX       CucsSwFcMonFsmStageName
    MAX-ACCESS   read-only
    STATUS       current
    DESCRIPTION
        "Cisco UCS sw:FcMonFsmStage:name managed object property"
    ::= { cucsSwFcMonFsmStageEntry 6 }

cucsSwFcMonFsmStageOrder OBJECT-TYPE
    SYNTAX       Gauge32
    MAX-ACCESS   read-only
    STATUS       current
    DESCRIPTION
        "Cisco UCS sw:FcMonFsmStage:order managed object property"
    ::= { cucsSwFcMonFsmStageEntry 7 }

cucsSwFcMonFsmStageRetry OBJECT-TYPE
    SYNTAX       Gauge32
    MAX-ACCESS   read-only
    STATUS       current
    DESCRIPTION
        "Cisco UCS sw:FcMonFsmStage:retry managed object property"
    ::= { cucsSwFcMonFsmStageEntry 8 }

cucsSwFcMonFsmStageStageStatus OBJECT-TYPE
    SYNTAX       CucsFsmFsmStageStatus
    MAX-ACCESS   read-only
    STATUS       current
    DESCRIPTION
        "Cisco UCS sw:FcMonFsmStage:stageStatus managed object property"
    ::= { cucsSwFcMonFsmStageEntry 9 }

cucsSwFcMonFsmTaskTable OBJECT-TYPE
    SYNTAX           SEQUENCE OF CucsSwFcMonFsmTaskEntry
    MAX-ACCESS       not-accessible
    STATUS           current
    DESCRIPTION
        "Cisco UCS sw:FcMonFsmTask managed object table"
    ::= { cucsSwObjects 20 }

cucsSwFcMonFsmTaskEntry OBJECT-TYPE
    SYNTAX           CucsSwFcMonFsmTaskEntry
    MAX-ACCESS       not-accessible
    STATUS           current
    DESCRIPTION
        "Entry for the cucsSwFcMonFsmTaskTable table."
    INDEX { cucsSwFcMonFsmTaskInstanceId }
    ::= { cucsSwFcMonFsmTaskTable 1 }

CucsSwFcMonFsmTaskEntry ::= SEQUENCE {
    cucsSwFcMonFsmTaskInstanceId                                     CucsManagedObjectId,
    cucsSwFcMonFsmTaskDn                                             CucsManagedObjectDn,
    cucsSwFcMonFsmTaskRn                                             SnmpAdminString,
    cucsSwFcMonFsmTaskCompletion                                     CucsFsmCompletion,
    cucsSwFcMonFsmTaskFlags                                          CucsFsmFlags,
    cucsSwFcMonFsmTaskItem                                           CucsSwFcMonFsmTaskItem,
    cucsSwFcMonFsmTaskSeqId                                          Gauge32
}

cucsSwFcMonFsmTaskInstanceId OBJECT-TYPE
    SYNTAX       CucsManagedObjectId
    MAX-ACCESS   not-accessible
    STATUS       current
    DESCRIPTION
        "Instance identifier of the managed object."
    ::= { cucsSwFcMonFsmTaskEntry 1 }

cucsSwFcMonFsmTaskDn OBJECT-TYPE
    SYNTAX       CucsManagedObjectDn
    MAX-ACCESS   read-only
    STATUS       current
    DESCRIPTION
        "Cisco UCS sw:FcMonFsmTask:dn managed object property"
    ::= { cucsSwFcMonFsmTaskEntry 2 }

cucsSwFcMonFsmTaskRn OBJECT-TYPE
    SYNTAX       SnmpAdminString
    MAX-ACCESS   read-only
    STATUS       current
    DESCRIPTION
        "Cisco UCS sw:FcMonFsmTask:rn managed object property"
    ::= { cucsSwFcMonFsmTaskEntry 3 }

cucsSwFcMonFsmTaskCompletion OBJECT-TYPE
    SYNTAX       CucsFsmCompletion
    MAX-ACCESS   read-only
    STATUS       current
    DESCRIPTION
        "Cisco UCS sw:FcMonFsmTask:completion managed object property"
    ::= { cucsSwFcMonFsmTaskEntry 4 }

cucsSwFcMonFsmTaskFlags OBJECT-TYPE
    SYNTAX       CucsFsmFlags
    MAX-ACCESS   read-only
    STATUS       current
    DESCRIPTION
        "Cisco UCS sw:FcMonFsmTask:flags managed object property"
    ::= { cucsSwFcMonFsmTaskEntry 5 }

cucsSwFcMonFsmTaskItem OBJECT-TYPE
    SYNTAX       CucsSwFcMonFsmTaskItem
    MAX-ACCESS   read-only
    STATUS       current
    DESCRIPTION
        "Cisco UCS sw:FcMonFsmTask:item managed object property"
    ::= { cucsSwFcMonFsmTaskEntry 6 }

cucsSwFcMonFsmTaskSeqId OBJECT-TYPE
    SYNTAX       Gauge32
    MAX-ACCESS   read-only
    STATUS       current
    DESCRIPTION
        "Cisco UCS sw:FcMonFsmTask:seqId managed object property"
    ::= { cucsSwFcMonFsmTaskEntry 7 }

cucsSwFcMonSrcEpTable OBJECT-TYPE
    SYNTAX           SEQUENCE OF CucsSwFcMonSrcEpEntry
    MAX-ACCESS       not-accessible
    STATUS           current
    DESCRIPTION
        "Cisco UCS sw:FcMonSrcEp managed object table"
    ::= { cucsSwObjects 21 }

cucsSwFcMonSrcEpEntry OBJECT-TYPE
    SYNTAX           CucsSwFcMonSrcEpEntry
    MAX-ACCESS       not-accessible
    STATUS           current
    DESCRIPTION
        "Entry for the cucsSwFcMonSrcEpTable table."
    INDEX { cucsSwFcMonSrcEpInstanceId }
    ::= { cucsSwFcMonSrcEpTable 1 }

CucsSwFcMonSrcEpEntry ::= SEQUENCE {
    cucsSwFcMonSrcEpInstanceId                                       CucsManagedObjectId,
    cucsSwFcMonSrcEpDn                                               CucsManagedObjectDn,
    cucsSwFcMonSrcEpRn                                               SnmpAdminString,
    cucsSwFcMonSrcEpAdminState                                       CucsFabricAdminState,
    cucsSwFcMonSrcEpChassisId                                        Gauge32,
    cucsSwFcMonSrcEpEpDn                                             SnmpAdminString,
    cucsSwFcMonSrcEpIfRole                                           CucsNetworkPortRole,
    cucsSwFcMonSrcEpIfType                                           CucsSwPIoEpIfType,
    cucsSwFcMonSrcEpLocale                                           CucsSwMonSrcEpLocale,
    cucsSwFcMonSrcEpMonTrafDir                                       CucsFabricTrafficDirection,
    cucsSwFcMonSrcEpName                                             SnmpAdminString,
    cucsSwFcMonSrcEpPeerDn                                           SnmpAdminString,
    cucsSwFcMonSrcEpPeerPortId                                       Gauge32,
    cucsSwFcMonSrcEpPeerSlotId                                       Gauge32,
    cucsSwFcMonSrcEpPortId                                           Gauge32,
    cucsSwFcMonSrcEpSlotId                                           Gauge32,
    cucsSwFcMonSrcEpSwitchId                                         CucsNetworkSwitchId,
    cucsSwFcMonSrcEpTransport                                        CucsSwFcMonSrcEpTransport,
    cucsSwFcMonSrcEpType                                             CucsNetworkConnectionType,
    cucsSwFcMonSrcEpPeerChassisId                                    Gauge32,
    cucsSwFcMonSrcEpLc                                               CucsSwPIoEpLc,
    cucsSwFcMonSrcEpAggrPortId                                       Gauge32,
    cucsSwFcMonSrcEpPeerAggrPortId                                   Gauge32
}

cucsSwFcMonSrcEpInstanceId OBJECT-TYPE
    SYNTAX       CucsManagedObjectId
    MAX-ACCESS   not-accessible
    STATUS       current
    DESCRIPTION
        "Instance identifier of the managed object."
    ::= { cucsSwFcMonSrcEpEntry 1 }

cucsSwFcMonSrcEpDn OBJECT-TYPE
    SYNTAX       CucsManagedObjectDn
    MAX-ACCESS   read-only
    STATUS       current
    DESCRIPTION
        "Cisco UCS sw:FcMonSrcEp:dn managed object property"
    ::= { cucsSwFcMonSrcEpEntry 2 }

cucsSwFcMonSrcEpRn OBJECT-TYPE
    SYNTAX       SnmpAdminString
    MAX-ACCESS   read-only
    STATUS       current
    DESCRIPTION
        "Cisco UCS sw:FcMonSrcEp:rn managed object property"
    ::= { cucsSwFcMonSrcEpEntry 3 }

cucsSwFcMonSrcEpAdminState OBJECT-TYPE
    SYNTAX       CucsFabricAdminState
    MAX-ACCESS   read-only
    STATUS       current
    DESCRIPTION
        "Cisco UCS sw:FcMonSrcEp:adminState managed object property"
    ::= { cucsSwFcMonSrcEpEntry 4 }

cucsSwFcMonSrcEpChassisId OBJECT-TYPE
    SYNTAX       Gauge32
    MAX-ACCESS   read-only
    STATUS       current
    DESCRIPTION
        "Cisco UCS sw:FcMonSrcEp:chassisId managed object property"
    ::= { cucsSwFcMonSrcEpEntry 5 }

cucsSwFcMonSrcEpEpDn OBJECT-TYPE
    SYNTAX       SnmpAdminString
    MAX-ACCESS   read-only
    STATUS       current
    DESCRIPTION
        "Cisco UCS sw:FcMonSrcEp:epDn managed object property"
    ::= { cucsSwFcMonSrcEpEntry 6 }

cucsSwFcMonSrcEpIfRole OBJECT-TYPE
    SYNTAX       CucsNetworkPortRole
    MAX-ACCESS   read-only
    STATUS       current
    DESCRIPTION
        "Cisco UCS sw:FcMonSrcEp:ifRole managed object property"
    ::= { cucsSwFcMonSrcEpEntry 7 }

cucsSwFcMonSrcEpIfType OBJECT-TYPE
    SYNTAX       CucsSwPIoEpIfType
    MAX-ACCESS   read-only
    STATUS       current
    DESCRIPTION
        "Cisco UCS sw:FcMonSrcEp:ifType managed object property"
    ::= { cucsSwFcMonSrcEpEntry 8 }

cucsSwFcMonSrcEpLocale OBJECT-TYPE
    SYNTAX       CucsSwMonSrcEpLocale
    MAX-ACCESS   read-only
    STATUS       current
    DESCRIPTION
        "Cisco UCS sw:FcMonSrcEp:locale managed object property"
    ::= { cucsSwFcMonSrcEpEntry 9 }

cucsSwFcMonSrcEpMonTrafDir OBJECT-TYPE
    SYNTAX       CucsFabricTrafficDirection
    MAX-ACCESS   read-only
    STATUS       current
    DESCRIPTION
        "Cisco UCS sw:FcMonSrcEp:monTrafDir managed object property"
    ::= { cucsSwFcMonSrcEpEntry 10 }

cucsSwFcMonSrcEpName OBJECT-TYPE
    SYNTAX       SnmpAdminString
    MAX-ACCESS   read-only
    STATUS       current
    DESCRIPTION
        "Cisco UCS sw:FcMonSrcEp:name managed object property"
    ::= { cucsSwFcMonSrcEpEntry 11 }

cucsSwFcMonSrcEpPeerDn OBJECT-TYPE
    SYNTAX       SnmpAdminString
    MAX-ACCESS   read-only
    STATUS       current
    DESCRIPTION
        "Cisco UCS sw:FcMonSrcEp:peerDn managed object property"
    ::= { cucsSwFcMonSrcEpEntry 12 }

cucsSwFcMonSrcEpPeerPortId OBJECT-TYPE
    SYNTAX       Gauge32
    MAX-ACCESS   read-only
    STATUS       current
    DESCRIPTION
        "Cisco UCS sw:FcMonSrcEp:peerPortId managed object property"
    ::= { cucsSwFcMonSrcEpEntry 13 }

cucsSwFcMonSrcEpPeerSlotId OBJECT-TYPE
    SYNTAX       Gauge32
    MAX-ACCESS   read-only
    STATUS       current
    DESCRIPTION
        "Cisco UCS sw:FcMonSrcEp:peerSlotId managed object property"
    ::= { cucsSwFcMonSrcEpEntry 14 }

cucsSwFcMonSrcEpPortId OBJECT-TYPE
    SYNTAX       Gauge32
    MAX-ACCESS   read-only
    STATUS       current
    DESCRIPTION
        "Cisco UCS sw:FcMonSrcEp:portId managed object property"
    ::= { cucsSwFcMonSrcEpEntry 15 }

cucsSwFcMonSrcEpSlotId OBJECT-TYPE
    SYNTAX       Gauge32
    MAX-ACCESS   read-only
    STATUS       current
    DESCRIPTION
        "Cisco UCS sw:FcMonSrcEp:slotId managed object property"
    ::= { cucsSwFcMonSrcEpEntry 16 }

cucsSwFcMonSrcEpSwitchId OBJECT-TYPE
    SYNTAX       CucsNetworkSwitchId
    MAX-ACCESS   read-only
    STATUS       current
    DESCRIPTION
        "Cisco UCS sw:FcMonSrcEp:switchId managed object property"
    ::= { cucsSwFcMonSrcEpEntry 17 }

cucsSwFcMonSrcEpTransport OBJECT-TYPE
    SYNTAX       CucsSwFcMonSrcEpTransport
    MAX-ACCESS   read-only
    STATUS       current
    DESCRIPTION
        "Cisco UCS sw:FcMonSrcEp:transport managed object property"
    ::= { cucsSwFcMonSrcEpEntry 18 }

cucsSwFcMonSrcEpType OBJECT-TYPE
    SYNTAX       CucsNetworkConnectionType
    MAX-ACCESS   read-only
    STATUS       current
    DESCRIPTION
        "Cisco UCS sw:FcMonSrcEp:type managed object property"
    ::= { cucsSwFcMonSrcEpEntry 19 }

cucsSwFcMonSrcEpPeerChassisId OBJECT-TYPE
    SYNTAX       Gauge32
    MAX-ACCESS   read-only
    STATUS       current
    DESCRIPTION
        "Cisco UCS sw:FcMonSrcEp:peerChassisId managed object property"
    ::= { cucsSwFcMonSrcEpEntry 20 }

cucsSwFcMonSrcEpLc OBJECT-TYPE
    SYNTAX       CucsSwPIoEpLc
    MAX-ACCESS   read-only
    STATUS       current
    DESCRIPTION
        "Cisco UCS sw:FcMonSrcEp:lc managed object property"
    ::= { cucsSwFcMonSrcEpEntry 21 }

cucsSwFcMonSrcEpAggrPortId OBJECT-TYPE
    SYNTAX       Gauge32
    MAX-ACCESS   read-only
    STATUS       current
    DESCRIPTION
        "Cisco UCS sw:FcMonSrcEp:aggrPortId managed object property"
    ::= { cucsSwFcMonSrcEpEntry 22 }

cucsSwFcMonSrcEpPeerAggrPortId OBJECT-TYPE
    SYNTAX       Gauge32
    MAX-ACCESS   read-only
    STATUS       current
    DESCRIPTION
        "Cisco UCS sw:FcMonSrcEp:peerAggrPortId managed object property"
    ::= { cucsSwFcMonSrcEpEntry 23 }

cucsSwFcSanBorderTable OBJECT-TYPE
    SYNTAX           SEQUENCE OF CucsSwFcSanBorderEntry
    MAX-ACCESS       not-accessible
    STATUS           current
    DESCRIPTION
        "Cisco UCS sw:FcSanBorder managed object table"
    ::= { cucsSwObjects 22 }

cucsSwFcSanBorderEntry OBJECT-TYPE
    SYNTAX           CucsSwFcSanBorderEntry
    MAX-ACCESS       not-accessible
    STATUS           current
    DESCRIPTION
        "Entry for the cucsSwFcSanBorderTable table."
    INDEX { cucsSwFcSanBorderInstanceId }
    ::= { cucsSwFcSanBorderTable 1 }

CucsSwFcSanBorderEntry ::= SEQUENCE {
    cucsSwFcSanBorderInstanceId                                      CucsManagedObjectId,
    cucsSwFcSanBorderDn                                              CucsManagedObjectDn,
    cucsSwFcSanBorderRn                                              SnmpAdminString,
    cucsSwFcSanBorderFsmDescr                                        SnmpAdminString,
    cucsSwFcSanBorderFsmPrev                                         SnmpAdminString,
    cucsSwFcSanBorderFsmProgr                                        Gauge32,
    cucsSwFcSanBorderFsmRmtInvErrCode                                Gauge32,
    cucsSwFcSanBorderFsmRmtInvErrDescr                               SnmpAdminString,
    cucsSwFcSanBorderFsmRmtInvRslt                                   CucsConditionRemoteInvRslt,
    cucsSwFcSanBorderFsmStageDescr                                   SnmpAdminString,
    cucsSwFcSanBorderFsmStamp                                        DateAndTime,
    cucsSwFcSanBorderFsmStatus                                       SnmpAdminString,
    cucsSwFcSanBorderFsmTry                                          Gauge32,
    cucsSwFcSanBorderLocale                                          CucsSwBorderDomainLocale,
    cucsSwFcSanBorderName                                            SnmpAdminString,
    cucsSwFcSanBorderSwitchId                                        CucsNetworkSwitchId,
    cucsSwFcSanBorderTransport                                       CucsSwFcSanBorderTransport,
    cucsSwFcSanBorderType                                            CucsSwSanBorderType,
    cucsSwFcSanBorderUplinkTrunking                                  CucsSwFcSanBorderUplinkTrunking,
    cucsSwFcSanBorderFsmFlags                                        SnmpAdminString
}

cucsSwFcSanBorderInstanceId OBJECT-TYPE
    SYNTAX       CucsManagedObjectId
    MAX-ACCESS   not-accessible
    STATUS       current
    DESCRIPTION
        "Instance identifier of the managed object."
    ::= { cucsSwFcSanBorderEntry 1 }

cucsSwFcSanBorderDn OBJECT-TYPE
    SYNTAX       CucsManagedObjectDn
    MAX-ACCESS   read-only
    STATUS       current
    DESCRIPTION
        "Cisco UCS sw:FcSanBorder:dn managed object property"
    ::= { cucsSwFcSanBorderEntry 2 }

cucsSwFcSanBorderRn OBJECT-TYPE
    SYNTAX       SnmpAdminString
    MAX-ACCESS   read-only
    STATUS       current
    DESCRIPTION
        "Cisco UCS sw:FcSanBorder:rn managed object property"
    ::= { cucsSwFcSanBorderEntry 3 }

cucsSwFcSanBorderFsmDescr OBJECT-TYPE
    SYNTAX       SnmpAdminString
    MAX-ACCESS   read-only
    STATUS       current
    DESCRIPTION
        "Cisco UCS sw:FcSanBorder:fsmDescr managed object property"
    ::= { cucsSwFcSanBorderEntry 4 }

cucsSwFcSanBorderFsmPrev OBJECT-TYPE
    SYNTAX       SnmpAdminString
    MAX-ACCESS   read-only
    STATUS       current
    DESCRIPTION
        "Cisco UCS sw:FcSanBorder:fsmPrev managed object property"
    ::= { cucsSwFcSanBorderEntry 5 }

cucsSwFcSanBorderFsmProgr OBJECT-TYPE
    SYNTAX       Gauge32
    MAX-ACCESS   read-only
    STATUS       current
    DESCRIPTION
        "Cisco UCS sw:FcSanBorder:fsmProgr managed object property"
    ::= { cucsSwFcSanBorderEntry 6 }

cucsSwFcSanBorderFsmRmtInvErrCode OBJECT-TYPE
    SYNTAX       Gauge32
    MAX-ACCESS   read-only
    STATUS       current
    DESCRIPTION
        "Cisco UCS sw:FcSanBorder:fsmRmtInvErrCode managed
        object property"
    ::= { cucsSwFcSanBorderEntry 7 }

cucsSwFcSanBorderFsmRmtInvErrDescr OBJECT-TYPE
    SYNTAX       SnmpAdminString
    MAX-ACCESS   read-only
    STATUS       current
    DESCRIPTION
        "Cisco UCS sw:FcSanBorder:fsmRmtInvErrDescr managed
        object property"
    ::= { cucsSwFcSanBorderEntry 8 }

cucsSwFcSanBorderFsmRmtInvRslt OBJECT-TYPE
    SYNTAX       CucsConditionRemoteInvRslt
    MAX-ACCESS   read-only
    STATUS       current
    DESCRIPTION
        "Cisco UCS sw:FcSanBorder:fsmRmtInvRslt managed object property"
    ::= { cucsSwFcSanBorderEntry 9 }

cucsSwFcSanBorderFsmStageDescr OBJECT-TYPE
    SYNTAX       SnmpAdminString
    MAX-ACCESS   read-only
    STATUS       current
    DESCRIPTION
        "Cisco UCS sw:FcSanBorder:fsmStageDescr managed object property"
    ::= { cucsSwFcSanBorderEntry 10 }

cucsSwFcSanBorderFsmStamp OBJECT-TYPE
    SYNTAX       DateAndTime
    MAX-ACCESS   read-only
    STATUS       current
    DESCRIPTION
        "Cisco UCS sw:FcSanBorder:fsmStamp managed object property"
    ::= { cucsSwFcSanBorderEntry 11 }

cucsSwFcSanBorderFsmStatus OBJECT-TYPE
    SYNTAX       SnmpAdminString
    MAX-ACCESS   read-only
    STATUS       current
    DESCRIPTION
        "Cisco UCS sw:FcSanBorder:fsmStatus managed object property"
    ::= { cucsSwFcSanBorderEntry 12 }

cucsSwFcSanBorderFsmTry OBJECT-TYPE
    SYNTAX       Gauge32
    MAX-ACCESS   read-only
    STATUS       current
    DESCRIPTION
        "Cisco UCS sw:FcSanBorder:fsmTry managed object property"
    ::= { cucsSwFcSanBorderEntry 13 }

cucsSwFcSanBorderLocale OBJECT-TYPE
    SYNTAX       CucsSwBorderDomainLocale
    MAX-ACCESS   read-only
    STATUS       current
    DESCRIPTION
        "Cisco UCS sw:FcSanBorder:locale managed object property"
    ::= { cucsSwFcSanBorderEntry 14 }

cucsSwFcSanBorderName OBJECT-TYPE
    SYNTAX       SnmpAdminString
    MAX-ACCESS   read-only
    STATUS       current
    DESCRIPTION
        "Cisco UCS sw:FcSanBorder:name managed object property"
    ::= { cucsSwFcSanBorderEntry 15 }

cucsSwFcSanBorderSwitchId OBJECT-TYPE
    SYNTAX       CucsNetworkSwitchId
    MAX-ACCESS   read-only
    STATUS       current
    DESCRIPTION
        "Cisco UCS sw:FcSanBorder:switchId managed object property"
    ::= { cucsSwFcSanBorderEntry 16 }

cucsSwFcSanBorderTransport OBJECT-TYPE
    SYNTAX       CucsSwFcSanBorderTransport
    MAX-ACCESS   read-only
    STATUS       current
    DESCRIPTION
        "Cisco UCS sw:FcSanBorder:transport managed object property"
    ::= { cucsSwFcSanBorderEntry 17 }

cucsSwFcSanBorderType OBJECT-TYPE
    SYNTAX       CucsSwSanBorderType
    MAX-ACCESS   read-only
    STATUS       current
    DESCRIPTION
        "Cisco UCS sw:FcSanBorder:type managed object property"
    ::= { cucsSwFcSanBorderEntry 18 }

cucsSwFcSanBorderUplinkTrunking OBJECT-TYPE
    SYNTAX       CucsSwFcSanBorderUplinkTrunking
    MAX-ACCESS   read-only
    STATUS       current
    DESCRIPTION
        "Cisco UCS sw:FcSanBorder:uplinkTrunking managed object property"
    ::= { cucsSwFcSanBorderEntry 19 }

cucsSwFcSanBorderFsmFlags OBJECT-TYPE
    SYNTAX       SnmpAdminString
    MAX-ACCESS   read-only
    STATUS       current
    DESCRIPTION
        "Cisco UCS sw:FcSanBorder:fsmFlags managed object property"
    ::= { cucsSwFcSanBorderEntry 21 }

cucsSwFcSanBorderFsmTable OBJECT-TYPE
    SYNTAX           SEQUENCE OF CucsSwFcSanBorderFsmEntry
    MAX-ACCESS       not-accessible
    STATUS           current
    DESCRIPTION
        "Cisco UCS sw:FcSanBorderFsm managed object table"
    ::= { cucsSwObjects 54 }

cucsSwFcSanBorderFsmEntry OBJECT-TYPE
    SYNTAX           CucsSwFcSanBorderFsmEntry
    MAX-ACCESS       not-accessible
    STATUS           current
    DESCRIPTION
        "Entry for the cucsSwFcSanBorderFsmTable table."
    INDEX { cucsSwFcSanBorderFsmInstanceId }
    ::= { cucsSwFcSanBorderFsmTable 1 }

CucsSwFcSanBorderFsmEntry ::= SEQUENCE {
    cucsSwFcSanBorderFsmInstanceId                                   CucsManagedObjectId,
    cucsSwFcSanBorderFsmDn                                           CucsManagedObjectDn,
    cucsSwFcSanBorderFsmRn                                           SnmpAdminString,
    cucsSwFcSanBorderFsmCompletionTime                               DateAndTime,
    cucsSwFcSanBorderFsmCurrentFsm                                   CucsSwFcSanBorderFsmCurrentFsm,
    cucsSwFcSanBorderFsmDescrData                                    SnmpAdminString,
    cucsSwFcSanBorderFsmFsmStatus                                    CucsFsmFsmStageStatus,
    cucsSwFcSanBorderFsmProgress                                     Gauge32,
    cucsSwFcSanBorderFsmRmtErrCode                                   Gauge32,
    cucsSwFcSanBorderFsmRmtErrDescr                                  SnmpAdminString,
    cucsSwFcSanBorderFsmRmtRslt                                      CucsConditionRemoteInvRslt
}

cucsSwFcSanBorderFsmInstanceId OBJECT-TYPE
    SYNTAX       CucsManagedObjectId
    MAX-ACCESS   not-accessible
    STATUS       current
    DESCRIPTION
        "Instance identifier of the managed object."
    ::= { cucsSwFcSanBorderFsmEntry 1 }

cucsSwFcSanBorderFsmDn OBJECT-TYPE
    SYNTAX       CucsManagedObjectDn
    MAX-ACCESS   read-only
    STATUS       current
    DESCRIPTION
        "Cisco UCS sw:FcSanBorderFsm:dn managed object property"
    ::= { cucsSwFcSanBorderFsmEntry 2 }

cucsSwFcSanBorderFsmRn OBJECT-TYPE
    SYNTAX       SnmpAdminString
    MAX-ACCESS   read-only
    STATUS       current
    DESCRIPTION
        "Cisco UCS sw:FcSanBorderFsm:rn managed object property"
    ::= { cucsSwFcSanBorderFsmEntry 3 }

cucsSwFcSanBorderFsmCompletionTime OBJECT-TYPE
    SYNTAX       DateAndTime
    MAX-ACCESS   read-only
    STATUS       current
    DESCRIPTION
        "Cisco UCS sw:FcSanBorderFsm:completionTime managed
        object property"
    ::= { cucsSwFcSanBorderFsmEntry 4 }

cucsSwFcSanBorderFsmCurrentFsm OBJECT-TYPE
    SYNTAX       CucsSwFcSanBorderFsmCurrentFsm
    MAX-ACCESS   read-only
    STATUS       current
    DESCRIPTION
        "Cisco UCS sw:FcSanBorderFsm:currentFsm managed object property"
    ::= { cucsSwFcSanBorderFsmEntry 5 }

cucsSwFcSanBorderFsmDescrData OBJECT-TYPE
    SYNTAX       SnmpAdminString
    MAX-ACCESS   read-only
    STATUS       current
    DESCRIPTION
        "Cisco UCS sw:FcSanBorderFsm:descr managed object property"
    ::= { cucsSwFcSanBorderFsmEntry 6 }

cucsSwFcSanBorderFsmFsmStatus OBJECT-TYPE
    SYNTAX       CucsFsmFsmStageStatus
    MAX-ACCESS   read-only
    STATUS       current
    DESCRIPTION
        "Cisco UCS sw:FcSanBorderFsm:fsmStatus managed object property"
    ::= { cucsSwFcSanBorderFsmEntry 7 }

cucsSwFcSanBorderFsmProgress OBJECT-TYPE
    SYNTAX       Gauge32
    MAX-ACCESS   read-only
    STATUS       current
    DESCRIPTION
        "Cisco UCS sw:FcSanBorderFsm:progress managed object property"
    ::= { cucsSwFcSanBorderFsmEntry 8 }

cucsSwFcSanBorderFsmRmtErrCode OBJECT-TYPE
    SYNTAX       Gauge32
    MAX-ACCESS   read-only
    STATUS       current
    DESCRIPTION
        "Cisco UCS sw:FcSanBorderFsm:rmtErrCode managed object property"
    ::= { cucsSwFcSanBorderFsmEntry 9 }

cucsSwFcSanBorderFsmRmtErrDescr OBJECT-TYPE
    SYNTAX       SnmpAdminString
    MAX-ACCESS   read-only
    STATUS       current
    DESCRIPTION
        "Cisco UCS sw:FcSanBorderFsm:rmtErrDescr managed object property"
    ::= { cucsSwFcSanBorderFsmEntry 10 }

cucsSwFcSanBorderFsmRmtRslt OBJECT-TYPE
    SYNTAX       CucsConditionRemoteInvRslt
    MAX-ACCESS   read-only
    STATUS       current
    DESCRIPTION
        "Cisco UCS sw:FcSanBorderFsm:rmtRslt managed object property"
    ::= { cucsSwFcSanBorderFsmEntry 11 }

cucsSwFcSanBorderFsmStageTable OBJECT-TYPE
    SYNTAX           SEQUENCE OF CucsSwFcSanBorderFsmStageEntry
    MAX-ACCESS       not-accessible
    STATUS           current
    DESCRIPTION
        "Cisco UCS sw:FcSanBorderFsmStage managed object table"
    ::= { cucsSwObjects 55 }

cucsSwFcSanBorderFsmStageEntry OBJECT-TYPE
    SYNTAX           CucsSwFcSanBorderFsmStageEntry
    MAX-ACCESS       not-accessible
    STATUS           current
    DESCRIPTION
        "Entry for the cucsSwFcSanBorderFsmStageTable table."
    INDEX { cucsSwFcSanBorderFsmStageInstanceId }
    ::= { cucsSwFcSanBorderFsmStageTable 1 }

CucsSwFcSanBorderFsmStageEntry ::= SEQUENCE {
    cucsSwFcSanBorderFsmStageInstanceId                              CucsManagedObjectId,
    cucsSwFcSanBorderFsmStageDn                                      CucsManagedObjectDn,
    cucsSwFcSanBorderFsmStageRn                                      SnmpAdminString,
    cucsSwFcSanBorderFsmStageDescrData                               SnmpAdminString,
    cucsSwFcSanBorderFsmStageLastUpdateTime                          DateAndTime,
    cucsSwFcSanBorderFsmStageName                                    CucsSwFcSanBorderFsmStageName,
    cucsSwFcSanBorderFsmStageOrder                                   Gauge32,
    cucsSwFcSanBorderFsmStageRetry                                   Gauge32,
    cucsSwFcSanBorderFsmStageStageStatus                             CucsFsmFsmStageStatus
}

cucsSwFcSanBorderFsmStageInstanceId OBJECT-TYPE
    SYNTAX       CucsManagedObjectId
    MAX-ACCESS   not-accessible
    STATUS       current
    DESCRIPTION
        "Instance identifier of the managed object."
    ::= { cucsSwFcSanBorderFsmStageEntry 1 }

cucsSwFcSanBorderFsmStageDn OBJECT-TYPE
    SYNTAX       CucsManagedObjectDn
    MAX-ACCESS   read-only
    STATUS       current
    DESCRIPTION
        "Cisco UCS sw:FcSanBorderFsmStage:dn managed object property"
    ::= { cucsSwFcSanBorderFsmStageEntry 2 }

cucsSwFcSanBorderFsmStageRn OBJECT-TYPE
    SYNTAX       SnmpAdminString
    MAX-ACCESS   read-only
    STATUS       current
    DESCRIPTION
        "Cisco UCS sw:FcSanBorderFsmStage:rn managed object property"
    ::= { cucsSwFcSanBorderFsmStageEntry 3 }

cucsSwFcSanBorderFsmStageDescrData OBJECT-TYPE
    SYNTAX       SnmpAdminString
    MAX-ACCESS   read-only
    STATUS       current
    DESCRIPTION
        "Cisco UCS sw:FcSanBorderFsmStage:descr managed object property"
    ::= { cucsSwFcSanBorderFsmStageEntry 4 }

cucsSwFcSanBorderFsmStageLastUpdateTime OBJECT-TYPE
    SYNTAX       DateAndTime
    MAX-ACCESS   read-only
    STATUS       current
    DESCRIPTION
        "Cisco UCS sw:FcSanBorderFsmStage:lastUpdateTime
        managed object property"
    ::= { cucsSwFcSanBorderFsmStageEntry 5 }

cucsSwFcSanBorderFsmStageName OBJECT-TYPE
    SYNTAX       CucsSwFcSanBorderFsmStageName
    MAX-ACCESS   read-only
    STATUS       current
    DESCRIPTION
        "Cisco UCS sw:FcSanBorderFsmStage:name managed object property"
    ::= { cucsSwFcSanBorderFsmStageEntry 6 }

cucsSwFcSanBorderFsmStageOrder OBJECT-TYPE
    SYNTAX       Gauge32
    MAX-ACCESS   read-only
    STATUS       current
    DESCRIPTION
        "Cisco UCS sw:FcSanBorderFsmStage:order managed object property"
    ::= { cucsSwFcSanBorderFsmStageEntry 7 }

cucsSwFcSanBorderFsmStageRetry OBJECT-TYPE
    SYNTAX       Gauge32
    MAX-ACCESS   read-only
    STATUS       current
    DESCRIPTION
        "Cisco UCS sw:FcSanBorderFsmStage:retry managed object property"
    ::= { cucsSwFcSanBorderFsmStageEntry 8 }

cucsSwFcSanBorderFsmStageStageStatus OBJECT-TYPE
    SYNTAX       CucsFsmFsmStageStatus
    MAX-ACCESS   read-only
    STATUS       current
    DESCRIPTION
        "Cisco UCS sw:FcSanBorderFsmStage:stageStatus managed
        object property"
    ::= { cucsSwFcSanBorderFsmStageEntry 9 }

cucsSwFcSanBorderFsmTaskTable OBJECT-TYPE
    SYNTAX           SEQUENCE OF CucsSwFcSanBorderFsmTaskEntry
    MAX-ACCESS       not-accessible
    STATUS           current
    DESCRIPTION
        "Cisco UCS sw:FcSanBorderFsmTask managed object table"
    ::= { cucsSwObjects 23 }

cucsSwFcSanBorderFsmTaskEntry OBJECT-TYPE
    SYNTAX           CucsSwFcSanBorderFsmTaskEntry
    MAX-ACCESS       not-accessible
    STATUS           current
    DESCRIPTION
        "Entry for the cucsSwFcSanBorderFsmTaskTable table."
    INDEX { cucsSwFcSanBorderFsmTaskInstanceId }
    ::= { cucsSwFcSanBorderFsmTaskTable 1 }

CucsSwFcSanBorderFsmTaskEntry ::= SEQUENCE {
    cucsSwFcSanBorderFsmTaskInstanceId                               CucsManagedObjectId,
    cucsSwFcSanBorderFsmTaskDn                                       CucsManagedObjectDn,
    cucsSwFcSanBorderFsmTaskRn                                       SnmpAdminString,
    cucsSwFcSanBorderFsmTaskCompletion                               CucsFsmCompletion,
    cucsSwFcSanBorderFsmTaskFlags                                    CucsSwFcSanBorderFsmTaskFlags,
    cucsSwFcSanBorderFsmTaskItem                                     CucsSwFcSanBorderFsmTaskItem,
    cucsSwFcSanBorderFsmTaskSeqId                                    Gauge32
}

cucsSwFcSanBorderFsmTaskInstanceId OBJECT-TYPE
    SYNTAX       CucsManagedObjectId
    MAX-ACCESS   not-accessible
    STATUS       current
    DESCRIPTION
        "Instance identifier of the managed object."
    ::= { cucsSwFcSanBorderFsmTaskEntry 1 }

cucsSwFcSanBorderFsmTaskDn OBJECT-TYPE
    SYNTAX       CucsManagedObjectDn
    MAX-ACCESS   read-only
    STATUS       current
    DESCRIPTION
        "Cisco UCS sw:FcSanBorderFsmTask:dn managed object property"
    ::= { cucsSwFcSanBorderFsmTaskEntry 2 }

cucsSwFcSanBorderFsmTaskRn OBJECT-TYPE
    SYNTAX       SnmpAdminString
    MAX-ACCESS   read-only
    STATUS       current
    DESCRIPTION
        "Cisco UCS sw:FcSanBorderFsmTask:rn managed object property"
    ::= { cucsSwFcSanBorderFsmTaskEntry 3 }

cucsSwFcSanBorderFsmTaskCompletion OBJECT-TYPE
    SYNTAX       CucsFsmCompletion
    MAX-ACCESS   read-only
    STATUS       current
    DESCRIPTION
        "Cisco UCS sw:FcSanBorderFsmTask:completion managed
        object property"
    ::= { cucsSwFcSanBorderFsmTaskEntry 4 }

cucsSwFcSanBorderFsmTaskFlags OBJECT-TYPE
    SYNTAX       CucsSwFcSanBorderFsmTaskFlags
    MAX-ACCESS   read-only
    STATUS       current
    DESCRIPTION
        "Cisco UCS sw:FcSanBorderFsmTask:flags managed object property"
    ::= { cucsSwFcSanBorderFsmTaskEntry 5 }

cucsSwFcSanBorderFsmTaskItem OBJECT-TYPE
    SYNTAX       CucsSwFcSanBorderFsmTaskItem
    MAX-ACCESS   read-only
    STATUS       current
    DESCRIPTION
        "Cisco UCS sw:FcSanBorderFsmTask:item managed object property"
    ::= { cucsSwFcSanBorderFsmTaskEntry 6 }

cucsSwFcSanBorderFsmTaskSeqId OBJECT-TYPE
    SYNTAX       Gauge32
    MAX-ACCESS   read-only
    STATUS       current
    DESCRIPTION
        "Cisco UCS sw:FcSanBorderFsmTask:seqId managed object property"
    ::= { cucsSwFcSanBorderFsmTaskEntry 7 }

cucsSwFcSanEpTable OBJECT-TYPE
    SYNTAX           SEQUENCE OF CucsSwFcSanEpEntry
    MAX-ACCESS       not-accessible
    STATUS           current
    DESCRIPTION
        "Cisco UCS sw:FcSanEp managed object table"
    ::= { cucsSwObjects 24 }

cucsSwFcSanEpEntry OBJECT-TYPE
    SYNTAX           CucsSwFcSanEpEntry
    MAX-ACCESS       not-accessible
    STATUS           current
    DESCRIPTION
        "Entry for the cucsSwFcSanEpTable table."
    INDEX { cucsSwFcSanEpInstanceId }
    ::= { cucsSwFcSanEpTable 1 }

CucsSwFcSanEpEntry ::= SEQUENCE {
    cucsSwFcSanEpInstanceId                                          CucsManagedObjectId,
    cucsSwFcSanEpDn                                                  CucsManagedObjectDn,
    cucsSwFcSanEpRn                                                  SnmpAdminString,
    cucsSwFcSanEpAdminState                                          CucsFabricAdminState,
    cucsSwFcSanEpChassisId                                           Gauge32,
    cucsSwFcSanEpEpDn                                                SnmpAdminString,
    cucsSwFcSanEpIfRole                                              CucsSwSanEpIfRole,
    cucsSwFcSanEpIfType                                              CucsSwPIoEpIfType,
    cucsSwFcSanEpLocale                                              CucsSwBorderEpLocale,
    cucsSwFcSanEpName                                                SnmpAdminString,
    cucsSwFcSanEpPcId                                                Gauge32,
    cucsSwFcSanEpPeerDn                                              SnmpAdminString,
    cucsSwFcSanEpPeerPortId                                          Gauge32,
    cucsSwFcSanEpPeerSlotId                                          Gauge32,
    cucsSwFcSanEpPortId                                              Gauge32,
    cucsSwFcSanEpPortVsanId                                          Gauge32,
    cucsSwFcSanEpSlotId                                              Gauge32,
    cucsSwFcSanEpSwitchId                                            CucsNetworkSwitchId,
    cucsSwFcSanEpTransport                                           CucsSwFcSanEpTransport,
    cucsSwFcSanEpType                                                CucsSwSanEpType,
    cucsSwFcSanEpAdminSpeed                                          CucsPortSpeed,
    cucsSwFcSanEpPeerChassisId                                       Gauge32,
    cucsSwFcSanEpLc                                                  CucsSwPIoEpLc,
    cucsSwFcSanEpFillPattern                                         CucsFabricFillPattern,
    cucsSwFcSanEpAggrPortId                                          Gauge32,
    cucsSwFcSanEpPeerAggrPortId                                      Gauge32
}

cucsSwFcSanEpInstanceId OBJECT-TYPE
    SYNTAX       CucsManagedObjectId
    MAX-ACCESS   not-accessible
    STATUS       current
    DESCRIPTION
        "Instance identifier of the managed object."
    ::= { cucsSwFcSanEpEntry 1 }

cucsSwFcSanEpDn OBJECT-TYPE
    SYNTAX       CucsManagedObjectDn
    MAX-ACCESS   read-only
    STATUS       current
    DESCRIPTION
        "Cisco UCS sw:FcSanEp:dn managed object property"
    ::= { cucsSwFcSanEpEntry 2 }

cucsSwFcSanEpRn OBJECT-TYPE
    SYNTAX       SnmpAdminString
    MAX-ACCESS   read-only
    STATUS       current
    DESCRIPTION
        "Cisco UCS sw:FcSanEp:rn managed object property"
    ::= { cucsSwFcSanEpEntry 3 }

cucsSwFcSanEpAdminState OBJECT-TYPE
    SYNTAX       CucsFabricAdminState
    MAX-ACCESS   read-only
    STATUS       current
    DESCRIPTION
        "Cisco UCS sw:FcSanEp:adminState managed object property"
    ::= { cucsSwFcSanEpEntry 4 }

cucsSwFcSanEpChassisId OBJECT-TYPE
    SYNTAX       Gauge32
    MAX-ACCESS   read-only
    STATUS       current
    DESCRIPTION
        "Cisco UCS sw:FcSanEp:chassisId managed object property"
    ::= { cucsSwFcSanEpEntry 5 }

cucsSwFcSanEpEpDn OBJECT-TYPE
    SYNTAX       SnmpAdminString
    MAX-ACCESS   read-only
    STATUS       current
    DESCRIPTION
        "Cisco UCS sw:FcSanEp:epDn managed object property"
    ::= { cucsSwFcSanEpEntry 6 }

cucsSwFcSanEpIfRole OBJECT-TYPE
    SYNTAX       CucsSwSanEpIfRole
    MAX-ACCESS   read-only
    STATUS       current
    DESCRIPTION
        "Cisco UCS sw:FcSanEp:ifRole managed object property"
    ::= { cucsSwFcSanEpEntry 7 }

cucsSwFcSanEpIfType OBJECT-TYPE
    SYNTAX       CucsSwPIoEpIfType
    MAX-ACCESS   read-only
    STATUS       current
    DESCRIPTION
        "Cisco UCS sw:FcSanEp:ifType managed object property"
    ::= { cucsSwFcSanEpEntry 8 }

cucsSwFcSanEpLocale OBJECT-TYPE
    SYNTAX       CucsSwBorderEpLocale
    MAX-ACCESS   read-only
    STATUS       current
    DESCRIPTION
        "Cisco UCS sw:FcSanEp:locale managed object property"
    ::= { cucsSwFcSanEpEntry 9 }

cucsSwFcSanEpName OBJECT-TYPE
    SYNTAX       SnmpAdminString
    MAX-ACCESS   read-only
    STATUS       current
    DESCRIPTION
        "Cisco UCS sw:FcSanEp:name managed object property"
    ::= { cucsSwFcSanEpEntry 10 }

cucsSwFcSanEpPcId OBJECT-TYPE
    SYNTAX       Gauge32
    MAX-ACCESS   read-only
    STATUS       current
    DESCRIPTION
        "Cisco UCS sw:FcSanEp:pcId managed object property"
    ::= { cucsSwFcSanEpEntry 11 }

cucsSwFcSanEpPeerDn OBJECT-TYPE
    SYNTAX       SnmpAdminString
    MAX-ACCESS   read-only
    STATUS       current
    DESCRIPTION
        "Cisco UCS sw:FcSanEp:peerDn managed object property"
    ::= { cucsSwFcSanEpEntry 12 }

cucsSwFcSanEpPeerPortId OBJECT-TYPE
    SYNTAX       Gauge32
    MAX-ACCESS   read-only
    STATUS       current
    DESCRIPTION
        "Cisco UCS sw:FcSanEp:peerPortId managed object property"
    ::= { cucsSwFcSanEpEntry 13 }

cucsSwFcSanEpPeerSlotId OBJECT-TYPE
    SYNTAX       Gauge32
    MAX-ACCESS   read-only
    STATUS       current
    DESCRIPTION
        "Cisco UCS sw:FcSanEp:peerSlotId managed object property"
    ::= { cucsSwFcSanEpEntry 14 }

cucsSwFcSanEpPortId OBJECT-TYPE
    SYNTAX       Gauge32
    MAX-ACCESS   read-only
    STATUS       current
    DESCRIPTION
        "Cisco UCS sw:FcSanEp:portId managed object property"
    ::= { cucsSwFcSanEpEntry 15 }

cucsSwFcSanEpPortVsanId OBJECT-TYPE
    SYNTAX       Gauge32
    MAX-ACCESS   read-only
    STATUS       current
    DESCRIPTION
        "Cisco UCS sw:FcSanEp:portVsanId managed object property"
    ::= { cucsSwFcSanEpEntry 16 }

cucsSwFcSanEpSlotId OBJECT-TYPE
    SYNTAX       Gauge32
    MAX-ACCESS   read-only
    STATUS       current
    DESCRIPTION
        "Cisco UCS sw:FcSanEp:slotId managed object property"
    ::= { cucsSwFcSanEpEntry 17 }

cucsSwFcSanEpSwitchId OBJECT-TYPE
    SYNTAX       CucsNetworkSwitchId
    MAX-ACCESS   read-only
    STATUS       current
    DESCRIPTION
        "Cisco UCS sw:FcSanEp:switchId managed object property"
    ::= { cucsSwFcSanEpEntry 18 }

cucsSwFcSanEpTransport OBJECT-TYPE
    SYNTAX       CucsSwFcSanEpTransport
    MAX-ACCESS   read-only
    STATUS       current
    DESCRIPTION
        "Cisco UCS sw:FcSanEp:transport managed object property"
    ::= { cucsSwFcSanEpEntry 19 }

cucsSwFcSanEpType OBJECT-TYPE
    SYNTAX       CucsSwSanEpType
    MAX-ACCESS   read-only
    STATUS       current
    DESCRIPTION
        "Cisco UCS sw:FcSanEp:type managed object property"
    ::= { cucsSwFcSanEpEntry 20 }

cucsSwFcSanEpAdminSpeed OBJECT-TYPE
    SYNTAX       CucsPortSpeed
    MAX-ACCESS   read-only
    STATUS       current
    DESCRIPTION
        "Cisco UCS sw:FcSanEp:adminSpeed managed object property"
    ::= { cucsSwFcSanEpEntry 21 }

cucsSwFcSanEpPeerChassisId OBJECT-TYPE
    SYNTAX       Gauge32
    MAX-ACCESS   read-only
    STATUS       current
    DESCRIPTION
        "Cisco UCS sw:FcSanEp:peerChassisId managed object property"
    ::= { cucsSwFcSanEpEntry 22 }

cucsSwFcSanEpLc OBJECT-TYPE
    SYNTAX       CucsSwPIoEpLc
    MAX-ACCESS   read-only
    STATUS       current
    DESCRIPTION
        "Cisco UCS sw:FcSanEp:lc managed object property"
    ::= { cucsSwFcSanEpEntry 23 }

cucsSwFcSanEpFillPattern OBJECT-TYPE
    SYNTAX       CucsFabricFillPattern
    MAX-ACCESS   read-only
    STATUS       current
    DESCRIPTION
        "Cisco UCS sw:FcSanEp:fillPattern managed object property"
    ::= { cucsSwFcSanEpEntry 24 }

cucsSwFcSanEpAggrPortId OBJECT-TYPE
    SYNTAX       Gauge32
    MAX-ACCESS   read-only
    STATUS       current
    DESCRIPTION
        "Cisco UCS sw:FcSanEp:aggrPortId managed object property"
    ::= { cucsSwFcSanEpEntry 25 }

cucsSwFcSanEpPeerAggrPortId OBJECT-TYPE
    SYNTAX       Gauge32
    MAX-ACCESS   read-only
    STATUS       current
    DESCRIPTION
        "Cisco UCS sw:FcSanEp:peerAggrPortId managed object property"
    ::= { cucsSwFcSanEpEntry 26 }

cucsSwFcSanMonTable OBJECT-TYPE
    SYNTAX           SEQUENCE OF CucsSwFcSanMonEntry
    MAX-ACCESS       not-accessible
    STATUS           current
    DESCRIPTION
        "Cisco UCS sw:FcSanMon managed object table"
    ::= { cucsSwObjects 25 }

cucsSwFcSanMonEntry OBJECT-TYPE
    SYNTAX           CucsSwFcSanMonEntry
    MAX-ACCESS       not-accessible
    STATUS           current
    DESCRIPTION
        "Entry for the cucsSwFcSanMonTable table."
    INDEX { cucsSwFcSanMonInstanceId }
    ::= { cucsSwFcSanMonTable 1 }

CucsSwFcSanMonEntry ::= SEQUENCE {
    cucsSwFcSanMonInstanceId                                         CucsManagedObjectId,
    cucsSwFcSanMonDn                                                 CucsManagedObjectDn,
    cucsSwFcSanMonRn                                                 SnmpAdminString,
    cucsSwFcSanMonLocale                                             CucsSwMonDomainLocale,
    cucsSwFcSanMonName                                               SnmpAdminString,
    cucsSwFcSanMonSwitchId                                           CucsNetworkSwitchId,
    cucsSwFcSanMonTransport                                          CucsSwFcSanMonTransport,
    cucsSwFcSanMonType                                               CucsSwSanMonType
}

cucsSwFcSanMonInstanceId OBJECT-TYPE
    SYNTAX       CucsManagedObjectId
    MAX-ACCESS   not-accessible
    STATUS       current
    DESCRIPTION
        "Instance identifier of the managed object."
    ::= { cucsSwFcSanMonEntry 1 }

cucsSwFcSanMonDn OBJECT-TYPE
    SYNTAX       CucsManagedObjectDn
    MAX-ACCESS   read-only
    STATUS       current
    DESCRIPTION
        "Cisco UCS sw:FcSanMon:dn managed object property"
    ::= { cucsSwFcSanMonEntry 2 }

cucsSwFcSanMonRn OBJECT-TYPE
    SYNTAX       SnmpAdminString
    MAX-ACCESS   read-only
    STATUS       current
    DESCRIPTION
        "Cisco UCS sw:FcSanMon:rn managed object property"
    ::= { cucsSwFcSanMonEntry 3 }

cucsSwFcSanMonLocale OBJECT-TYPE
    SYNTAX       CucsSwMonDomainLocale
    MAX-ACCESS   read-only
    STATUS       current
    DESCRIPTION
        "Cisco UCS sw:FcSanMon:locale managed object property"
    ::= { cucsSwFcSanMonEntry 4 }

cucsSwFcSanMonName OBJECT-TYPE
    SYNTAX       SnmpAdminString
    MAX-ACCESS   read-only
    STATUS       current
    DESCRIPTION
        "Cisco UCS sw:FcSanMon:name managed object property"
    ::= { cucsSwFcSanMonEntry 5 }

cucsSwFcSanMonSwitchId OBJECT-TYPE
    SYNTAX       CucsNetworkSwitchId
    MAX-ACCESS   read-only
    STATUS       current
    DESCRIPTION
        "Cisco UCS sw:FcSanMon:switchId managed object property"
    ::= { cucsSwFcSanMonEntry 6 }

cucsSwFcSanMonTransport OBJECT-TYPE
    SYNTAX       CucsSwFcSanMonTransport
    MAX-ACCESS   read-only
    STATUS       current
    DESCRIPTION
        "Cisco UCS sw:FcSanMon:transport managed object property"
    ::= { cucsSwFcSanMonEntry 7 }

cucsSwFcSanMonType OBJECT-TYPE
    SYNTAX       CucsSwSanMonType
    MAX-ACCESS   read-only
    STATUS       current
    DESCRIPTION
        "Cisco UCS sw:FcSanMon:type managed object property"
    ::= { cucsSwFcSanMonEntry 8 }

cucsSwFcSanPcTable OBJECT-TYPE
    SYNTAX           SEQUENCE OF CucsSwFcSanPcEntry
    MAX-ACCESS       not-accessible
    STATUS           current
    DESCRIPTION
        "Cisco UCS sw:FcSanPc managed object table"
    ::= { cucsSwObjects 26 }

cucsSwFcSanPcEntry OBJECT-TYPE
    SYNTAX           CucsSwFcSanPcEntry
    MAX-ACCESS       not-accessible
    STATUS           current
    DESCRIPTION
        "Entry for the cucsSwFcSanPcTable table."
    INDEX { cucsSwFcSanPcInstanceId }
    ::= { cucsSwFcSanPcTable 1 }

CucsSwFcSanPcEntry ::= SEQUENCE {
    cucsSwFcSanPcInstanceId                                          CucsManagedObjectId,
    cucsSwFcSanPcDn                                                  CucsManagedObjectDn,
    cucsSwFcSanPcRn                                                  SnmpAdminString,
    cucsSwFcSanPcAdminState                                          CucsFabricAdminState,
    cucsSwFcSanPcEpDn                                                SnmpAdminString,
    cucsSwFcSanPcIfRole                                              CucsSwSanPcIfRole,
    cucsSwFcSanPcIfType                                              CucsSwCIoEpIfType,
    cucsSwFcSanPcLocale                                              CucsSwBorderPcLocale,
    cucsSwFcSanPcName                                                SnmpAdminString,
    cucsSwFcSanPcPcId                                                Gauge32,
    cucsSwFcSanPcPeerDn                                              SnmpAdminString,
    cucsSwFcSanPcPortId                                              Gauge32,
    cucsSwFcSanPcPortVsanId                                          Gauge32,
    cucsSwFcSanPcSwitchId                                            CucsNetworkSwitchId,
    cucsSwFcSanPcTransport                                           CucsSwFcSanPcTransport,
    cucsSwFcSanPcType                                                CucsSwSanPcType,
    cucsSwFcSanPcMonTrafDir                                          CucsFabricTrafficDirection,
    cucsSwFcSanPcAdminSpeed                                          CucsPortSpeed
}

cucsSwFcSanPcInstanceId OBJECT-TYPE
    SYNTAX       CucsManagedObjectId
    MAX-ACCESS   not-accessible
    STATUS       current
    DESCRIPTION
        "Instance identifier of the managed object."
    ::= { cucsSwFcSanPcEntry 1 }

cucsSwFcSanPcDn OBJECT-TYPE
    SYNTAX       CucsManagedObjectDn
    MAX-ACCESS   read-only
    STATUS       current
    DESCRIPTION
        "Cisco UCS sw:FcSanPc:dn managed object property"
    ::= { cucsSwFcSanPcEntry 2 }

cucsSwFcSanPcRn OBJECT-TYPE
    SYNTAX       SnmpAdminString
    MAX-ACCESS   read-only
    STATUS       current
    DESCRIPTION
        "Cisco UCS sw:FcSanPc:rn managed object property"
    ::= { cucsSwFcSanPcEntry 3 }

cucsSwFcSanPcAdminState OBJECT-TYPE
    SYNTAX       CucsFabricAdminState
    MAX-ACCESS   read-only
    STATUS       current
    DESCRIPTION
        "Cisco UCS sw:FcSanPc:adminState managed object property"
    ::= { cucsSwFcSanPcEntry 4 }

cucsSwFcSanPcEpDn OBJECT-TYPE
    SYNTAX       SnmpAdminString
    MAX-ACCESS   read-only
    STATUS       current
    DESCRIPTION
        "Cisco UCS sw:FcSanPc:epDn managed object property"
    ::= { cucsSwFcSanPcEntry 5 }

cucsSwFcSanPcIfRole OBJECT-TYPE
    SYNTAX       CucsSwSanPcIfRole
    MAX-ACCESS   read-only
    STATUS       current
    DESCRIPTION
        "Cisco UCS sw:FcSanPc:ifRole managed object property"
    ::= { cucsSwFcSanPcEntry 6 }

cucsSwFcSanPcIfType OBJECT-TYPE
    SYNTAX       CucsSwCIoEpIfType
    MAX-ACCESS   read-only
    STATUS       current
    DESCRIPTION
        "Cisco UCS sw:FcSanPc:ifType managed object property"
    ::= { cucsSwFcSanPcEntry 7 }

cucsSwFcSanPcLocale OBJECT-TYPE
    SYNTAX       CucsSwBorderPcLocale
    MAX-ACCESS   read-only
    STATUS       current
    DESCRIPTION
        "Cisco UCS sw:FcSanPc:locale managed object property"
    ::= { cucsSwFcSanPcEntry 8 }

cucsSwFcSanPcName OBJECT-TYPE
    SYNTAX       SnmpAdminString
    MAX-ACCESS   read-only
    STATUS       current
    DESCRIPTION
        "Cisco UCS sw:FcSanPc:name managed object property"
    ::= { cucsSwFcSanPcEntry 9 }

cucsSwFcSanPcPcId OBJECT-TYPE
    SYNTAX       Gauge32
    MAX-ACCESS   read-only
    STATUS       current
    DESCRIPTION
        "Cisco UCS sw:FcSanPc:pcId managed object property"
    ::= { cucsSwFcSanPcEntry 10 }

cucsSwFcSanPcPeerDn OBJECT-TYPE
    SYNTAX       SnmpAdminString
    MAX-ACCESS   read-only
    STATUS       current
    DESCRIPTION
        "Cisco UCS sw:FcSanPc:peerDn managed object property"
    ::= { cucsSwFcSanPcEntry 11 }

cucsSwFcSanPcPortId OBJECT-TYPE
    SYNTAX       Gauge32
    MAX-ACCESS   read-only
    STATUS       current
    DESCRIPTION
        "Cisco UCS sw:FcSanPc:portId managed object property"
    ::= { cucsSwFcSanPcEntry 12 }

cucsSwFcSanPcPortVsanId OBJECT-TYPE
    SYNTAX       Gauge32
    MAX-ACCESS   read-only
    STATUS       current
    DESCRIPTION
        "Cisco UCS sw:FcSanPc:portVsanId managed object property"
    ::= { cucsSwFcSanPcEntry 13 }

cucsSwFcSanPcSwitchId OBJECT-TYPE
    SYNTAX       CucsNetworkSwitchId
    MAX-ACCESS   read-only
    STATUS       current
    DESCRIPTION
        "Cisco UCS sw:FcSanPc:switchId managed object property"
    ::= { cucsSwFcSanPcEntry 14 }

cucsSwFcSanPcTransport OBJECT-TYPE
    SYNTAX       CucsSwFcSanPcTransport
    MAX-ACCESS   read-only
    STATUS       current
    DESCRIPTION
        "Cisco UCS sw:FcSanPc:transport managed object property"
    ::= { cucsSwFcSanPcEntry 15 }

cucsSwFcSanPcType OBJECT-TYPE
    SYNTAX       CucsSwSanPcType
    MAX-ACCESS   read-only
    STATUS       current
    DESCRIPTION
        "Cisco UCS sw:FcSanPc:type managed object property"
    ::= { cucsSwFcSanPcEntry 16 }

cucsSwFcSanPcMonTrafDir OBJECT-TYPE
    SYNTAX       CucsFabricTrafficDirection
    MAX-ACCESS   read-only
    STATUS       current
    DESCRIPTION
        "Cisco UCS sw:FcSanPc:monTrafDir managed object property"
    ::= { cucsSwFcSanPcEntry 17 }

cucsSwFcSanPcAdminSpeed OBJECT-TYPE
    SYNTAX       CucsPortSpeed
    MAX-ACCESS   read-only
    STATUS       current
    DESCRIPTION
        "Cisco UCS sw:FcSanPc:adminSpeed managed object property"
    ::= { cucsSwFcSanPcEntry 18 }

cucsSwFcServerZoneGroupTable OBJECT-TYPE
    SYNTAX           SEQUENCE OF CucsSwFcServerZoneGroupEntry
    MAX-ACCESS       not-accessible
    STATUS           current
    DESCRIPTION
        "Cisco UCS sw:FcServerZoneGroup managed object table"
    ::= { cucsSwObjects 56 }

cucsSwFcServerZoneGroupEntry OBJECT-TYPE
    SYNTAX           CucsSwFcServerZoneGroupEntry
    MAX-ACCESS       not-accessible
    STATUS           current
    DESCRIPTION
        "Entry for the cucsSwFcServerZoneGroupTable table."
    INDEX { cucsSwFcServerZoneGroupInstanceId }
    ::= { cucsSwFcServerZoneGroupTable 1 }

CucsSwFcServerZoneGroupEntry ::= SEQUENCE {
    cucsSwFcServerZoneGroupInstanceId                                CucsManagedObjectId,
    cucsSwFcServerZoneGroupDn                                        CucsManagedObjectDn,
    cucsSwFcServerZoneGroupRn                                        SnmpAdminString,
    cucsSwFcServerZoneGroupEpDn                                      SnmpAdminString,
    cucsSwFcServerZoneGroupId                                        Gauge32,
    cucsSwFcServerZoneGroupLc                                        CucsSwFcServerZoneGroupLc,
    cucsSwFcServerZoneGroupName                                      SnmpAdminString,
    cucsSwFcServerZoneGroupPeerDn                                    SnmpAdminString,
    cucsSwFcServerZoneGroupServerDn                                  SnmpAdminString
}

cucsSwFcServerZoneGroupInstanceId OBJECT-TYPE
    SYNTAX       CucsManagedObjectId
    MAX-ACCESS   not-accessible
    STATUS       current
    DESCRIPTION
        "Instance identifier of the managed object."
    ::= { cucsSwFcServerZoneGroupEntry 1 }

cucsSwFcServerZoneGroupDn OBJECT-TYPE
    SYNTAX       CucsManagedObjectDn
    MAX-ACCESS   read-only
    STATUS       current
    DESCRIPTION
        "Cisco UCS sw:FcServerZoneGroup:dn managed object property"
    ::= { cucsSwFcServerZoneGroupEntry 2 }

cucsSwFcServerZoneGroupRn OBJECT-TYPE
    SYNTAX       SnmpAdminString
    MAX-ACCESS   read-only
    STATUS       current
    DESCRIPTION
        "Cisco UCS sw:FcServerZoneGroup:rn managed object property"
    ::= { cucsSwFcServerZoneGroupEntry 3 }

cucsSwFcServerZoneGroupEpDn OBJECT-TYPE
    SYNTAX       SnmpAdminString
    MAX-ACCESS   read-only
    STATUS       current
    DESCRIPTION
        "Cisco UCS sw:FcServerZoneGroup:epDn managed object property"
    ::= { cucsSwFcServerZoneGroupEntry 4 }

cucsSwFcServerZoneGroupId OBJECT-TYPE
    SYNTAX       Gauge32
    MAX-ACCESS   read-only
    STATUS       current
    DESCRIPTION
        "Cisco UCS sw:FcServerZoneGroup:id managed object property"
    ::= { cucsSwFcServerZoneGroupEntry 5 }

cucsSwFcServerZoneGroupLc OBJECT-TYPE
    SYNTAX       CucsSwFcServerZoneGroupLc
    MAX-ACCESS   read-only
    STATUS       current
    DESCRIPTION
        "Cisco UCS sw:FcServerZoneGroup:lc managed object property"
    ::= { cucsSwFcServerZoneGroupEntry 6 }

cucsSwFcServerZoneGroupName OBJECT-TYPE
    SYNTAX       SnmpAdminString
    MAX-ACCESS   read-only
    STATUS       current
    DESCRIPTION
        "Cisco UCS sw:FcServerZoneGroup:name managed object property"
    ::= { cucsSwFcServerZoneGroupEntry 7 }

cucsSwFcServerZoneGroupPeerDn OBJECT-TYPE
    SYNTAX       SnmpAdminString
    MAX-ACCESS   read-only
    STATUS       current
    DESCRIPTION
        "Cisco UCS sw:FcServerZoneGroup:peerDn managed object property"
    ::= { cucsSwFcServerZoneGroupEntry 8 }

cucsSwFcServerZoneGroupServerDn OBJECT-TYPE
    SYNTAX       SnmpAdminString
    MAX-ACCESS   read-only
    STATUS       current
    DESCRIPTION
        "Cisco UCS sw:FcServerZoneGroup:serverDn managed object property"
    ::= { cucsSwFcServerZoneGroupEntry 9 }

cucsSwFcUserZoneTable OBJECT-TYPE
    SYNTAX           SEQUENCE OF CucsSwFcUserZoneEntry
    MAX-ACCESS       not-accessible
    STATUS           current
    DESCRIPTION
        "Cisco UCS sw:FcUserZone managed object table"
    ::= { cucsSwObjects 90 }

cucsSwFcUserZoneEntry OBJECT-TYPE
    SYNTAX           CucsSwFcUserZoneEntry
    MAX-ACCESS       not-accessible
    STATUS           current
    DESCRIPTION
        "Entry for the cucsSwFcUserZoneTable table."
    INDEX { cucsSwFcUserZoneInstanceId }
    ::= { cucsSwFcUserZoneTable 1 }

CucsSwFcUserZoneEntry ::= SEQUENCE {
    cucsSwFcUserZoneInstanceId                                       CucsManagedObjectId,
    cucsSwFcUserZoneDn                                               CucsManagedObjectDn,
    cucsSwFcUserZoneRn                                               SnmpAdminString,
    cucsSwFcUserZoneId                                               Gauge32,
    cucsSwFcUserZoneLc                                               CucsSwFcUserZoneLc,
    cucsSwFcUserZoneName                                             SnmpAdminString,
    cucsSwFcUserZoneOperState                                        CucsLsFcZoneState,
    cucsSwFcUserZonePeerDn                                           SnmpAdminString
}

cucsSwFcUserZoneInstanceId OBJECT-TYPE
    SYNTAX       CucsManagedObjectId
    MAX-ACCESS   not-accessible
    STATUS       current
    DESCRIPTION
        "Instance identifier of the managed object."
    ::= { cucsSwFcUserZoneEntry 1 }

cucsSwFcUserZoneDn OBJECT-TYPE
    SYNTAX       CucsManagedObjectDn
    MAX-ACCESS   read-only
    STATUS       current
    DESCRIPTION
        "Cisco UCS sw:FcUserZone:dn managed object property"
    ::= { cucsSwFcUserZoneEntry 2 }

cucsSwFcUserZoneRn OBJECT-TYPE
    SYNTAX       SnmpAdminString
    MAX-ACCESS   read-only
    STATUS       current
    DESCRIPTION
        "Cisco UCS sw:FcUserZone:rn managed object property"
    ::= { cucsSwFcUserZoneEntry 3 }

cucsSwFcUserZoneId OBJECT-TYPE
    SYNTAX       Gauge32
    MAX-ACCESS   read-only
    STATUS       current
    DESCRIPTION
        "Cisco UCS sw:FcUserZone:id managed object property"
    ::= { cucsSwFcUserZoneEntry 4 }

cucsSwFcUserZoneLc OBJECT-TYPE
    SYNTAX       CucsSwFcUserZoneLc
    MAX-ACCESS   read-only
    STATUS       current
    DESCRIPTION
        "Cisco UCS sw:FcUserZone:lc managed object property"
    ::= { cucsSwFcUserZoneEntry 5 }

cucsSwFcUserZoneName OBJECT-TYPE
    SYNTAX       SnmpAdminString
    MAX-ACCESS   read-only
    STATUS       current
    DESCRIPTION
        "Cisco UCS sw:FcUserZone:name managed object property"
    ::= { cucsSwFcUserZoneEntry 6 }

cucsSwFcUserZoneOperState OBJECT-TYPE
    SYNTAX       CucsLsFcZoneState
    MAX-ACCESS   read-only
    STATUS       current
    DESCRIPTION
        "Cisco UCS sw:FcUserZone:operState managed object property"
    ::= { cucsSwFcUserZoneEntry 7 }

cucsSwFcUserZonePeerDn OBJECT-TYPE
    SYNTAX       SnmpAdminString
    MAX-ACCESS   read-only
    STATUS       current
    DESCRIPTION
        "Cisco UCS sw:FcUserZone:peerDn managed object property"
    ::= { cucsSwFcUserZoneEntry 8 }

cucsSwFcUserZoneGroupTable OBJECT-TYPE
    SYNTAX           SEQUENCE OF CucsSwFcUserZoneGroupEntry
    MAX-ACCESS       not-accessible
    STATUS           current
    DESCRIPTION
        "Cisco UCS sw:FcUserZoneGroup managed object table"
    ::= { cucsSwObjects 91 }

cucsSwFcUserZoneGroupEntry OBJECT-TYPE
    SYNTAX           CucsSwFcUserZoneGroupEntry
    MAX-ACCESS       not-accessible
    STATUS           current
    DESCRIPTION
        "Entry for the cucsSwFcUserZoneGroupTable table."
    INDEX { cucsSwFcUserZoneGroupInstanceId }
    ::= { cucsSwFcUserZoneGroupTable 1 }

CucsSwFcUserZoneGroupEntry ::= SEQUENCE {
    cucsSwFcUserZoneGroupInstanceId                                  CucsManagedObjectId,
    cucsSwFcUserZoneGroupDn                                          CucsManagedObjectDn,
    cucsSwFcUserZoneGroupRn                                          SnmpAdminString,
    cucsSwFcUserZoneGroupId                                          Gauge32,
    cucsSwFcUserZoneGroupLc                                          CucsSwFcUserZoneGroupLc,
    cucsSwFcUserZoneGroupName                                        SnmpAdminString,
    cucsSwFcUserZoneGroupPeerDn                                      SnmpAdminString
}

cucsSwFcUserZoneGroupInstanceId OBJECT-TYPE
    SYNTAX       CucsManagedObjectId
    MAX-ACCESS   not-accessible
    STATUS       current
    DESCRIPTION
        "Instance identifier of the managed object."
    ::= { cucsSwFcUserZoneGroupEntry 1 }

cucsSwFcUserZoneGroupDn OBJECT-TYPE
    SYNTAX       CucsManagedObjectDn
    MAX-ACCESS   read-only
    STATUS       current
    DESCRIPTION
        "Cisco UCS sw:FcUserZoneGroup:dn managed object property"
    ::= { cucsSwFcUserZoneGroupEntry 2 }

cucsSwFcUserZoneGroupRn OBJECT-TYPE
    SYNTAX       SnmpAdminString
    MAX-ACCESS   read-only
    STATUS       current
    DESCRIPTION
        "Cisco UCS sw:FcUserZoneGroup:rn managed object property"
    ::= { cucsSwFcUserZoneGroupEntry 3 }

cucsSwFcUserZoneGroupId OBJECT-TYPE
    SYNTAX       Gauge32
    MAX-ACCESS   read-only
    STATUS       current
    DESCRIPTION
        "Cisco UCS sw:FcUserZoneGroup:id managed object property"
    ::= { cucsSwFcUserZoneGroupEntry 4 }

cucsSwFcUserZoneGroupLc OBJECT-TYPE
    SYNTAX       CucsSwFcUserZoneGroupLc
    MAX-ACCESS   read-only
    STATUS       current
    DESCRIPTION
        "Cisco UCS sw:FcUserZoneGroup:lc managed object property"
    ::= { cucsSwFcUserZoneGroupEntry 5 }

cucsSwFcUserZoneGroupName OBJECT-TYPE
    SYNTAX       SnmpAdminString
    MAX-ACCESS   read-only
    STATUS       current
    DESCRIPTION
        "Cisco UCS sw:FcUserZoneGroup:name managed object property"
    ::= { cucsSwFcUserZoneGroupEntry 6 }

cucsSwFcUserZoneGroupPeerDn OBJECT-TYPE
    SYNTAX       SnmpAdminString
    MAX-ACCESS   read-only
    STATUS       current
    DESCRIPTION
        "Cisco UCS sw:FcUserZoneGroup:peerDn managed object property"
    ::= { cucsSwFcUserZoneGroupEntry 7 }

cucsSwFcZoneTable OBJECT-TYPE
    SYNTAX           SEQUENCE OF CucsSwFcZoneEntry
    MAX-ACCESS       not-accessible
    STATUS           current
    DESCRIPTION
        "Cisco UCS sw:FcZone managed object table"
    ::= { cucsSwObjects 57 }

cucsSwFcZoneEntry OBJECT-TYPE
    SYNTAX           CucsSwFcZoneEntry
    MAX-ACCESS       not-accessible
    STATUS           current
    DESCRIPTION
        "Entry for the cucsSwFcZoneTable table."
    INDEX { cucsSwFcZoneInstanceId }
    ::= { cucsSwFcZoneTable 1 }

CucsSwFcZoneEntry ::= SEQUENCE {
    cucsSwFcZoneInstanceId                                           CucsManagedObjectId,
    cucsSwFcZoneDn                                                   CucsManagedObjectDn,
    cucsSwFcZoneRn                                                   SnmpAdminString,
    cucsSwFcZoneId                                                   Gauge32,
    cucsSwFcZoneIdentity                                             SnmpAdminString,
    cucsSwFcZoneLc                                                   CucsSwFcZoneLc,
    cucsSwFcZoneName                                                 SnmpAdminString,
    cucsSwFcZoneOperState                                            CucsLsFcZoneState,
    cucsSwFcZonePeerDn                                               SnmpAdminString
}

cucsSwFcZoneInstanceId OBJECT-TYPE
    SYNTAX       CucsManagedObjectId
    MAX-ACCESS   not-accessible
    STATUS       current
    DESCRIPTION
        "Instance identifier of the managed object."
    ::= { cucsSwFcZoneEntry 1 }

cucsSwFcZoneDn OBJECT-TYPE
    SYNTAX       CucsManagedObjectDn
    MAX-ACCESS   read-only
    STATUS       current
    DESCRIPTION
        "Cisco UCS sw:FcZone:dn managed object property"
    ::= { cucsSwFcZoneEntry 2 }

cucsSwFcZoneRn OBJECT-TYPE
    SYNTAX       SnmpAdminString
    MAX-ACCESS   read-only
    STATUS       current
    DESCRIPTION
        "Cisco UCS sw:FcZone:rn managed object property"
    ::= { cucsSwFcZoneEntry 3 }

cucsSwFcZoneId OBJECT-TYPE
    SYNTAX       Gauge32
    MAX-ACCESS   read-only
    STATUS       current
    DESCRIPTION
        "Cisco UCS sw:FcZone:id managed object property"
    ::= { cucsSwFcZoneEntry 4 }

cucsSwFcZoneIdentity OBJECT-TYPE
    SYNTAX       SnmpAdminString
    MAX-ACCESS   read-only
    STATUS       current
    DESCRIPTION
        "Cisco UCS sw:FcZone:identity managed object property"
    ::= { cucsSwFcZoneEntry 5 }

cucsSwFcZoneLc OBJECT-TYPE
    SYNTAX       CucsSwFcZoneLc
    MAX-ACCESS   read-only
    STATUS       current
    DESCRIPTION
        "Cisco UCS sw:FcZone:lc managed object property"
    ::= { cucsSwFcZoneEntry 6 }

cucsSwFcZoneName OBJECT-TYPE
    SYNTAX       SnmpAdminString
    MAX-ACCESS   read-only
    STATUS       current
    DESCRIPTION
        "Cisco UCS sw:FcZone:name managed object property"
    ::= { cucsSwFcZoneEntry 7 }

cucsSwFcZoneOperState OBJECT-TYPE
    SYNTAX       CucsLsFcZoneState
    MAX-ACCESS   read-only
    STATUS       current
    DESCRIPTION
        "Cisco UCS sw:FcZone:operState managed object property"
    ::= { cucsSwFcZoneEntry 8 }

cucsSwFcZonePeerDn OBJECT-TYPE
    SYNTAX       SnmpAdminString
    MAX-ACCESS   read-only
    STATUS       current
    DESCRIPTION
        "Cisco UCS sw:FcZone:peerDn managed object property"
    ::= { cucsSwFcZoneEntry 9 }

cucsSwFcZoneSetTable OBJECT-TYPE
    SYNTAX           SEQUENCE OF CucsSwFcZoneSetEntry
    MAX-ACCESS       not-accessible
    STATUS           current
    DESCRIPTION
        "Cisco UCS sw:FcZoneSet managed object table"
    ::= { cucsSwObjects 58 }

cucsSwFcZoneSetEntry OBJECT-TYPE
    SYNTAX           CucsSwFcZoneSetEntry
    MAX-ACCESS       not-accessible
    STATUS           current
    DESCRIPTION
        "Entry for the cucsSwFcZoneSetTable table."
    INDEX { cucsSwFcZoneSetInstanceId }
    ::= { cucsSwFcZoneSetTable 1 }

CucsSwFcZoneSetEntry ::= SEQUENCE {
    cucsSwFcZoneSetInstanceId                                        CucsManagedObjectId,
    cucsSwFcZoneSetDn                                                CucsManagedObjectDn,
    cucsSwFcZoneSetRn                                                SnmpAdminString,
    cucsSwFcZoneSetCurrentZonePrefix                                 SnmpAdminString,
    cucsSwFcZoneSetLc                                                CucsSwFcZoneSetLc,
    cucsSwFcZoneSetName                                              SnmpAdminString,
    cucsSwFcZoneSetOldZonePrefix                                     SnmpAdminString
}

cucsSwFcZoneSetInstanceId OBJECT-TYPE
    SYNTAX       CucsManagedObjectId
    MAX-ACCESS   not-accessible
    STATUS       current
    DESCRIPTION
        "Instance identifier of the managed object."
    ::= { cucsSwFcZoneSetEntry 1 }

cucsSwFcZoneSetDn OBJECT-TYPE
    SYNTAX       CucsManagedObjectDn
    MAX-ACCESS   read-only
    STATUS       current
    DESCRIPTION
        "Cisco UCS sw:FcZoneSet:dn managed object property"
    ::= { cucsSwFcZoneSetEntry 2 }

cucsSwFcZoneSetRn OBJECT-TYPE
    SYNTAX       SnmpAdminString
    MAX-ACCESS   read-only
    STATUS       current
    DESCRIPTION
        "Cisco UCS sw:FcZoneSet:rn managed object property"
    ::= { cucsSwFcZoneSetEntry 3 }

cucsSwFcZoneSetCurrentZonePrefix OBJECT-TYPE
    SYNTAX       SnmpAdminString
    MAX-ACCESS   read-only
    STATUS       current
    DESCRIPTION
        "Cisco UCS sw:FcZoneSet:currentZonePrefix managed object property"
    ::= { cucsSwFcZoneSetEntry 4 }

cucsSwFcZoneSetLc OBJECT-TYPE
    SYNTAX       CucsSwFcZoneSetLc
    MAX-ACCESS   read-only
    STATUS       current
    DESCRIPTION
        "Cisco UCS sw:FcZoneSet:lc managed object property"
    ::= { cucsSwFcZoneSetEntry 5 }

cucsSwFcZoneSetName OBJECT-TYPE
    SYNTAX       SnmpAdminString
    MAX-ACCESS   read-only
    STATUS       current
    DESCRIPTION
        "Cisco UCS sw:FcZoneSet:name managed object property"
    ::= { cucsSwFcZoneSetEntry 6 }

cucsSwFcZoneSetOldZonePrefix OBJECT-TYPE
    SYNTAX       SnmpAdminString
    MAX-ACCESS   read-only
    STATUS       current
    DESCRIPTION
        "Cisco UCS sw:FcZoneSet:oldZonePrefix managed object property"
    ::= { cucsSwFcZoneSetEntry 7 }

cucsSwFcoeEstcEpTable OBJECT-TYPE
    SYNTAX           SEQUENCE OF CucsSwFcoeEstcEpEntry
    MAX-ACCESS       not-accessible
    STATUS           current
    DESCRIPTION
        "Cisco UCS sw:FcoeEstcEp managed object table"
    ::= { cucsSwObjects 27 }

cucsSwFcoeEstcEpEntry OBJECT-TYPE
    SYNTAX           CucsSwFcoeEstcEpEntry
    MAX-ACCESS       not-accessible
    STATUS           current
    DESCRIPTION
        "Entry for the cucsSwFcoeEstcEpTable table."
    INDEX { cucsSwFcoeEstcEpInstanceId }
    ::= { cucsSwFcoeEstcEpTable 1 }

CucsSwFcoeEstcEpEntry ::= SEQUENCE {
    cucsSwFcoeEstcEpInstanceId                                       CucsManagedObjectId,
    cucsSwFcoeEstcEpDn                                               CucsManagedObjectDn,
    cucsSwFcoeEstcEpRn                                               SnmpAdminString,
    cucsSwFcoeEstcEpAdminState                                       CucsFabricAdminState,
    cucsSwFcoeEstcEpChassisId                                        Gauge32,
    cucsSwFcoeEstcEpEpDn                                             SnmpAdminString,
    cucsSwFcoeEstcEpIfRole                                           CucsNetworkPortRole,
    cucsSwFcoeEstcEpIfType                                           CucsSwPIoEpIfType,
    cucsSwFcoeEstcEpLocale                                           CucsSwEstcEpLocale,
    cucsSwFcoeEstcEpName                                             SnmpAdminString,
    cucsSwFcoeEstcEpPeerDn                                           SnmpAdminString,
    cucsSwFcoeEstcEpPeerPortId                                       Gauge32,
    cucsSwFcoeEstcEpPeerSlotId                                       Gauge32,
    cucsSwFcoeEstcEpPortId                                           Gauge32,
    cucsSwFcoeEstcEpSlotId                                           Gauge32,
    cucsSwFcoeEstcEpSwitchId                                         CucsNetworkSwitchId,
    cucsSwFcoeEstcEpTransport                                        CucsSwFcoeEstcEpTransport,
    cucsSwFcoeEstcEpType                                             CucsNetworkConnectionType,
    cucsSwFcoeEstcEpPeerChassisId                                    Gauge32,
    cucsSwFcoeEstcEpLc                                               CucsSwPIoEpLc,
    cucsSwFcoeEstcEpPeerState                                        CucsSwPeerStatus,
    cucsSwFcoeEstcEpAggrPortId                                       Gauge32,
    cucsSwFcoeEstcEpPeerAggrPortId                                   Gauge32
}

cucsSwFcoeEstcEpInstanceId OBJECT-TYPE
    SYNTAX       CucsManagedObjectId
    MAX-ACCESS   not-accessible
    STATUS       current
    DESCRIPTION
        "Instance identifier of the managed object."
    ::= { cucsSwFcoeEstcEpEntry 1 }

cucsSwFcoeEstcEpDn OBJECT-TYPE
    SYNTAX       CucsManagedObjectDn
    MAX-ACCESS   read-only
    STATUS       current
    DESCRIPTION
        "Cisco UCS sw:FcoeEstcEp:dn managed object property"
    ::= { cucsSwFcoeEstcEpEntry 2 }

cucsSwFcoeEstcEpRn OBJECT-TYPE
    SYNTAX       SnmpAdminString
    MAX-ACCESS   read-only
    STATUS       current
    DESCRIPTION
        "Cisco UCS sw:FcoeEstcEp:rn managed object property"
    ::= { cucsSwFcoeEstcEpEntry 3 }

cucsSwFcoeEstcEpAdminState OBJECT-TYPE
    SYNTAX       CucsFabricAdminState
    MAX-ACCESS   read-only
    STATUS       current
    DESCRIPTION
        "Cisco UCS sw:FcoeEstcEp:adminState managed object property"
    ::= { cucsSwFcoeEstcEpEntry 4 }

cucsSwFcoeEstcEpChassisId OBJECT-TYPE
    SYNTAX       Gauge32
    MAX-ACCESS   read-only
    STATUS       current
    DESCRIPTION
        "Cisco UCS sw:FcoeEstcEp:chassisId managed object property"
    ::= { cucsSwFcoeEstcEpEntry 5 }

cucsSwFcoeEstcEpEpDn OBJECT-TYPE
    SYNTAX       SnmpAdminString
    MAX-ACCESS   read-only
    STATUS       current
    DESCRIPTION
        "Cisco UCS sw:FcoeEstcEp:epDn managed object property"
    ::= { cucsSwFcoeEstcEpEntry 6 }

cucsSwFcoeEstcEpIfRole OBJECT-TYPE
    SYNTAX       CucsNetworkPortRole
    MAX-ACCESS   read-only
    STATUS       current
    DESCRIPTION
        "Cisco UCS sw:FcoeEstcEp:ifRole managed object property"
    ::= { cucsSwFcoeEstcEpEntry 7 }

cucsSwFcoeEstcEpIfType OBJECT-TYPE
    SYNTAX       CucsSwPIoEpIfType
    MAX-ACCESS   read-only
    STATUS       current
    DESCRIPTION
        "Cisco UCS sw:FcoeEstcEp:ifType managed object property"
    ::= { cucsSwFcoeEstcEpEntry 8 }

cucsSwFcoeEstcEpLocale OBJECT-TYPE
    SYNTAX       CucsSwEstcEpLocale
    MAX-ACCESS   read-only
    STATUS       current
    DESCRIPTION
        "Cisco UCS sw:FcoeEstcEp:locale managed object property"
    ::= { cucsSwFcoeEstcEpEntry 9 }

cucsSwFcoeEstcEpName OBJECT-TYPE
    SYNTAX       SnmpAdminString
    MAX-ACCESS   read-only
    STATUS       current
    DESCRIPTION
        "Cisco UCS sw:FcoeEstcEp:name managed object property"
    ::= { cucsSwFcoeEstcEpEntry 10 }

cucsSwFcoeEstcEpPeerDn OBJECT-TYPE
    SYNTAX       SnmpAdminString
    MAX-ACCESS   read-only
    STATUS       current
    DESCRIPTION
        "Cisco UCS sw:FcoeEstcEp:peerDn managed object property"
    ::= { cucsSwFcoeEstcEpEntry 11 }

cucsSwFcoeEstcEpPeerPortId OBJECT-TYPE
    SYNTAX       Gauge32
    MAX-ACCESS   read-only
    STATUS       current
    DESCRIPTION
        "Cisco UCS sw:FcoeEstcEp:peerPortId managed object property"
    ::= { cucsSwFcoeEstcEpEntry 12 }

cucsSwFcoeEstcEpPeerSlotId OBJECT-TYPE
    SYNTAX       Gauge32
    MAX-ACCESS   read-only
    STATUS       current
    DESCRIPTION
        "Cisco UCS sw:FcoeEstcEp:peerSlotId managed object property"
    ::= { cucsSwFcoeEstcEpEntry 13 }

cucsSwFcoeEstcEpPortId OBJECT-TYPE
    SYNTAX       Gauge32
    MAX-ACCESS   read-only
    STATUS       current
    DESCRIPTION
        "Cisco UCS sw:FcoeEstcEp:portId managed object property"
    ::= { cucsSwFcoeEstcEpEntry 14 }

cucsSwFcoeEstcEpSlotId OBJECT-TYPE
    SYNTAX       Gauge32
    MAX-ACCESS   read-only
    STATUS       current
    DESCRIPTION
        "Cisco UCS sw:FcoeEstcEp:slotId managed object property"
    ::= { cucsSwFcoeEstcEpEntry 15 }

cucsSwFcoeEstcEpSwitchId OBJECT-TYPE
    SYNTAX       CucsNetworkSwitchId
    MAX-ACCESS   read-only
    STATUS       current
    DESCRIPTION
        "Cisco UCS sw:FcoeEstcEp:switchId managed object property"
    ::= { cucsSwFcoeEstcEpEntry 16 }

cucsSwFcoeEstcEpTransport OBJECT-TYPE
    SYNTAX       CucsSwFcoeEstcEpTransport
    MAX-ACCESS   read-only
    STATUS       current
    DESCRIPTION
        "Cisco UCS sw:FcoeEstcEp:transport managed object property"
    ::= { cucsSwFcoeEstcEpEntry 17 }

cucsSwFcoeEstcEpType OBJECT-TYPE
    SYNTAX       CucsNetworkConnectionType
    MAX-ACCESS   read-only
    STATUS       current
    DESCRIPTION
        "Cisco UCS sw:FcoeEstcEp:type managed object property"
    ::= { cucsSwFcoeEstcEpEntry 18 }

cucsSwFcoeEstcEpPeerChassisId OBJECT-TYPE
    SYNTAX       Gauge32
    MAX-ACCESS   read-only
    STATUS       current
    DESCRIPTION
        "Cisco UCS sw:FcoeEstcEp:peerChassisId managed object property"
    ::= { cucsSwFcoeEstcEpEntry 19 }

cucsSwFcoeEstcEpLc OBJECT-TYPE
    SYNTAX       CucsSwPIoEpLc
    MAX-ACCESS   read-only
    STATUS       current
    DESCRIPTION
        "Cisco UCS sw:FcoeEstcEp:lc managed object property"
    ::= { cucsSwFcoeEstcEpEntry 20 }

cucsSwFcoeEstcEpPeerState OBJECT-TYPE
    SYNTAX       CucsSwPeerStatus
    MAX-ACCESS   read-only
    STATUS       current
    DESCRIPTION
        "Cisco UCS sw:FcoeEstcEp:peerState managed object property"
    ::= { cucsSwFcoeEstcEpEntry 21 }

cucsSwFcoeEstcEpAggrPortId OBJECT-TYPE
    SYNTAX       Gauge32
    MAX-ACCESS   read-only
    STATUS       current
    DESCRIPTION
        "Cisco UCS sw:FcoeEstcEp:aggrPortId managed object property"
    ::= { cucsSwFcoeEstcEpEntry 22 }

cucsSwFcoeEstcEpPeerAggrPortId OBJECT-TYPE
    SYNTAX       Gauge32
    MAX-ACCESS   read-only
    STATUS       current
    DESCRIPTION
        "Cisco UCS sw:FcoeEstcEp:peerAggrPortId managed object property"
    ::= { cucsSwFcoeEstcEpEntry 23 }

cucsSwFcoeSanEpTable OBJECT-TYPE
    SYNTAX           SEQUENCE OF CucsSwFcoeSanEpEntry
    MAX-ACCESS       not-accessible
    STATUS           current
    DESCRIPTION
        "Cisco UCS sw:FcoeSanEp managed object table"
    ::= { cucsSwObjects 59 }

cucsSwFcoeSanEpEntry OBJECT-TYPE
    SYNTAX           CucsSwFcoeSanEpEntry
    MAX-ACCESS       not-accessible
    STATUS           current
    DESCRIPTION
        "Entry for the cucsSwFcoeSanEpTable table."
    INDEX { cucsSwFcoeSanEpInstanceId }
    ::= { cucsSwFcoeSanEpTable 1 }

CucsSwFcoeSanEpEntry ::= SEQUENCE {
    cucsSwFcoeSanEpInstanceId                                        CucsManagedObjectId,
    cucsSwFcoeSanEpDn                                                CucsManagedObjectDn,
    cucsSwFcoeSanEpRn                                                SnmpAdminString,
    cucsSwFcoeSanEpAdminSpeed                                        CucsPortEthAdminSpeed,
    cucsSwFcoeSanEpAdminState                                        CucsFabricAdminState,
    cucsSwFcoeSanEpChassisId                                         Gauge32,
    cucsSwFcoeSanEpEpDn                                              SnmpAdminString,
    cucsSwFcoeSanEpIfRole                                            CucsSwSanEpIfRole,
    cucsSwFcoeSanEpIfType                                            CucsSwPIoEpIfType,
    cucsSwFcoeSanEpLc                                                CucsSwPIoEpLc,
    cucsSwFcoeSanEpLocale                                            CucsSwBorderEpLocale,
    cucsSwFcoeSanEpName                                              SnmpAdminString,
    cucsSwFcoeSanEpPcId                                              Gauge32,
    cucsSwFcoeSanEpPeerChassisId                                     Gauge32,
    cucsSwFcoeSanEpPeerDn                                            SnmpAdminString,
    cucsSwFcoeSanEpPeerPortId                                        Gauge32,
    cucsSwFcoeSanEpPeerSlotId                                        Gauge32,
    cucsSwFcoeSanEpPeerState                                         CucsSwPeerStatus,
    cucsSwFcoeSanEpPortId                                            Gauge32,
    cucsSwFcoeSanEpPortVsanId                                        Gauge32,
    cucsSwFcoeSanEpSlotId                                            Gauge32,
    cucsSwFcoeSanEpSwitchId                                          CucsNetworkSwitchId,
    cucsSwFcoeSanEpTransport                                         CucsSwFcoeSanEpTransport,
    cucsSwFcoeSanEpType                                              CucsSwSanEpType,
    cucsSwFcoeSanEpUdldAdminState                                    CucsSwFcoeSanEpUdldAdminState,
    cucsSwFcoeSanEpUdldMode                                          CucsSwFcoeSanEpUdldMode,
    cucsSwFcoeSanEpAggrPortId                                        Gauge32,
    cucsSwFcoeSanEpPeerAggrPortId                                    Gauge32
}

cucsSwFcoeSanEpInstanceId OBJECT-TYPE
    SYNTAX       CucsManagedObjectId
    MAX-ACCESS   not-accessible
    STATUS       current
    DESCRIPTION
        "Instance identifier of the managed object."
    ::= { cucsSwFcoeSanEpEntry 1 }

cucsSwFcoeSanEpDn OBJECT-TYPE
    SYNTAX       CucsManagedObjectDn
    MAX-ACCESS   read-only
    STATUS       current
    DESCRIPTION
        "Cisco UCS sw:FcoeSanEp:dn managed object property"
    ::= { cucsSwFcoeSanEpEntry 2 }

cucsSwFcoeSanEpRn OBJECT-TYPE
    SYNTAX       SnmpAdminString
    MAX-ACCESS   read-only
    STATUS       current
    DESCRIPTION
        "Cisco UCS sw:FcoeSanEp:rn managed object property"
    ::= { cucsSwFcoeSanEpEntry 3 }

cucsSwFcoeSanEpAdminSpeed OBJECT-TYPE
    SYNTAX       CucsPortEthAdminSpeed
    MAX-ACCESS   read-only
    STATUS       current
    DESCRIPTION
        "Cisco UCS sw:FcoeSanEp:adminSpeed managed object property"
    ::= { cucsSwFcoeSanEpEntry 4 }

cucsSwFcoeSanEpAdminState OBJECT-TYPE
    SYNTAX       CucsFabricAdminState
    MAX-ACCESS   read-only
    STATUS       current
    DESCRIPTION
        "Cisco UCS sw:FcoeSanEp:adminState managed object property"
    ::= { cucsSwFcoeSanEpEntry 5 }

cucsSwFcoeSanEpChassisId OBJECT-TYPE
    SYNTAX       Gauge32
    MAX-ACCESS   read-only
    STATUS       current
    DESCRIPTION
        "Cisco UCS sw:FcoeSanEp:chassisId managed object property"
    ::= { cucsSwFcoeSanEpEntry 6 }

cucsSwFcoeSanEpEpDn OBJECT-TYPE
    SYNTAX       SnmpAdminString
    MAX-ACCESS   read-only
    STATUS       current
    DESCRIPTION
        "Cisco UCS sw:FcoeSanEp:epDn managed object property"
    ::= { cucsSwFcoeSanEpEntry 7 }

cucsSwFcoeSanEpIfRole OBJECT-TYPE
    SYNTAX       CucsSwSanEpIfRole
    MAX-ACCESS   read-only
    STATUS       current
    DESCRIPTION
        "Cisco UCS sw:FcoeSanEp:ifRole managed object property"
    ::= { cucsSwFcoeSanEpEntry 8 }

cucsSwFcoeSanEpIfType OBJECT-TYPE
    SYNTAX       CucsSwPIoEpIfType
    MAX-ACCESS   read-only
    STATUS       current
    DESCRIPTION
        "Cisco UCS sw:FcoeSanEp:ifType managed object property"
    ::= { cucsSwFcoeSanEpEntry 9 }

cucsSwFcoeSanEpLc OBJECT-TYPE
    SYNTAX       CucsSwPIoEpLc
    MAX-ACCESS   read-only
    STATUS       current
    DESCRIPTION
        "Cisco UCS sw:FcoeSanEp:lc managed object property"
    ::= { cucsSwFcoeSanEpEntry 10 }

cucsSwFcoeSanEpLocale OBJECT-TYPE
    SYNTAX       CucsSwBorderEpLocale
    MAX-ACCESS   read-only
    STATUS       current
    DESCRIPTION
        "Cisco UCS sw:FcoeSanEp:locale managed object property"
    ::= { cucsSwFcoeSanEpEntry 11 }

cucsSwFcoeSanEpName OBJECT-TYPE
    SYNTAX       SnmpAdminString
    MAX-ACCESS   read-only
    STATUS       current
    DESCRIPTION
        "Cisco UCS sw:FcoeSanEp:name managed object property"
    ::= { cucsSwFcoeSanEpEntry 12 }

cucsSwFcoeSanEpPcId OBJECT-TYPE
    SYNTAX       Gauge32
    MAX-ACCESS   read-only
    STATUS       current
    DESCRIPTION
        "Cisco UCS sw:FcoeSanEp:pcId managed object property"
    ::= { cucsSwFcoeSanEpEntry 13 }

cucsSwFcoeSanEpPeerChassisId OBJECT-TYPE
    SYNTAX       Gauge32
    MAX-ACCESS   read-only
    STATUS       current
    DESCRIPTION
        "Cisco UCS sw:FcoeSanEp:peerChassisId managed object property"
    ::= { cucsSwFcoeSanEpEntry 14 }

cucsSwFcoeSanEpPeerDn OBJECT-TYPE
    SYNTAX       SnmpAdminString
    MAX-ACCESS   read-only
    STATUS       current
    DESCRIPTION
        "Cisco UCS sw:FcoeSanEp:peerDn managed object property"
    ::= { cucsSwFcoeSanEpEntry 15 }

cucsSwFcoeSanEpPeerPortId OBJECT-TYPE
    SYNTAX       Gauge32
    MAX-ACCESS   read-only
    STATUS       current
    DESCRIPTION
        "Cisco UCS sw:FcoeSanEp:peerPortId managed object property"
    ::= { cucsSwFcoeSanEpEntry 16 }

cucsSwFcoeSanEpPeerSlotId OBJECT-TYPE
    SYNTAX       Gauge32
    MAX-ACCESS   read-only
    STATUS       current
    DESCRIPTION
        "Cisco UCS sw:FcoeSanEp:peerSlotId managed object property"
    ::= { cucsSwFcoeSanEpEntry 17 }

cucsSwFcoeSanEpPeerState OBJECT-TYPE
    SYNTAX       CucsSwPeerStatus
    MAX-ACCESS   read-only
    STATUS       current
    DESCRIPTION
        "Cisco UCS sw:FcoeSanEp:peerState managed object property"
    ::= { cucsSwFcoeSanEpEntry 18 }

cucsSwFcoeSanEpPortId OBJECT-TYPE
    SYNTAX       Gauge32
    MAX-ACCESS   read-only
    STATUS       current
    DESCRIPTION
        "Cisco UCS sw:FcoeSanEp:portId managed object property"
    ::= { cucsSwFcoeSanEpEntry 19 }

cucsSwFcoeSanEpPortVsanId OBJECT-TYPE
    SYNTAX       Gauge32
    MAX-ACCESS   read-only
    STATUS       current
    DESCRIPTION
        "Cisco UCS sw:FcoeSanEp:portVsanId managed object property"
    ::= { cucsSwFcoeSanEpEntry 20 }

cucsSwFcoeSanEpSlotId OBJECT-TYPE
    SYNTAX       Gauge32
    MAX-ACCESS   read-only
    STATUS       current
    DESCRIPTION
        "Cisco UCS sw:FcoeSanEp:slotId managed object property"
    ::= { cucsSwFcoeSanEpEntry 21 }

cucsSwFcoeSanEpSwitchId OBJECT-TYPE
    SYNTAX       CucsNetworkSwitchId
    MAX-ACCESS   read-only
    STATUS       current
    DESCRIPTION
        "Cisco UCS sw:FcoeSanEp:switchId managed object property"
    ::= { cucsSwFcoeSanEpEntry 22 }

cucsSwFcoeSanEpTransport OBJECT-TYPE
    SYNTAX       CucsSwFcoeSanEpTransport
    MAX-ACCESS   read-only
    STATUS       current
    DESCRIPTION
        "Cisco UCS sw:FcoeSanEp:transport managed object property"
    ::= { cucsSwFcoeSanEpEntry 23 }

cucsSwFcoeSanEpType OBJECT-TYPE
    SYNTAX       CucsSwSanEpType
    MAX-ACCESS   read-only
    STATUS       current
    DESCRIPTION
        "Cisco UCS sw:FcoeSanEp:type managed object property"
    ::= { cucsSwFcoeSanEpEntry 24 }

cucsSwFcoeSanEpUdldAdminState OBJECT-TYPE
    SYNTAX       CucsSwFcoeSanEpUdldAdminState
    MAX-ACCESS   read-only
    STATUS       current
    DESCRIPTION
        "Cisco UCS sw:FcoeSanEp:udldAdminState managed object property"
    ::= { cucsSwFcoeSanEpEntry 25 }

cucsSwFcoeSanEpUdldMode OBJECT-TYPE
    SYNTAX       CucsSwFcoeSanEpUdldMode
    MAX-ACCESS   read-only
    STATUS       current
    DESCRIPTION
        "Cisco UCS sw:FcoeSanEp:udldMode managed object property"
    ::= { cucsSwFcoeSanEpEntry 26 }

cucsSwFcoeSanEpAggrPortId OBJECT-TYPE
    SYNTAX       Gauge32
    MAX-ACCESS   read-only
    STATUS       current
    DESCRIPTION
        "Cisco UCS sw:FcoeSanEp:aggrPortId managed object property"
    ::= { cucsSwFcoeSanEpEntry 27 }

cucsSwFcoeSanEpPeerAggrPortId OBJECT-TYPE
    SYNTAX       Gauge32
    MAX-ACCESS   read-only
    STATUS       current
    DESCRIPTION
        "Cisco UCS sw:FcoeSanEp:peerAggrPortId managed object property"
    ::= { cucsSwFcoeSanEpEntry 28 }

cucsSwFcoeSanPcTable OBJECT-TYPE
    SYNTAX           SEQUENCE OF CucsSwFcoeSanPcEntry
    MAX-ACCESS       not-accessible
    STATUS           current
    DESCRIPTION
        "Cisco UCS sw:FcoeSanPc managed object table"
    ::= { cucsSwObjects 60 }

cucsSwFcoeSanPcEntry OBJECT-TYPE
    SYNTAX           CucsSwFcoeSanPcEntry
    MAX-ACCESS       not-accessible
    STATUS           current
    DESCRIPTION
        "Entry for the cucsSwFcoeSanPcTable table."
    INDEX { cucsSwFcoeSanPcInstanceId }
    ::= { cucsSwFcoeSanPcTable 1 }

CucsSwFcoeSanPcEntry ::= SEQUENCE {
    cucsSwFcoeSanPcInstanceId                                        CucsManagedObjectId,
    cucsSwFcoeSanPcDn                                                CucsManagedObjectDn,
    cucsSwFcoeSanPcRn                                                SnmpAdminString,
    cucsSwFcoeSanPcAdminState                                        CucsFabricAdminState,
    cucsSwFcoeSanPcEpDn                                              SnmpAdminString,
    cucsSwFcoeSanPcIfRole                                            CucsSwSanPcIfRole,
    cucsSwFcoeSanPcIfType                                            CucsSwCIoEpIfType,
    cucsSwFcoeSanPcLocale                                            CucsSwBorderPcLocale,
    cucsSwFcoeSanPcMonTrafDir                                        CucsFabricTrafficDirection,
    cucsSwFcoeSanPcName                                              SnmpAdminString,
    cucsSwFcoeSanPcPcId                                              Gauge32,
    cucsSwFcoeSanPcPeerDn                                            SnmpAdminString,
    cucsSwFcoeSanPcPeerState                                         CucsSwPeerStatus,
    cucsSwFcoeSanPcPortId                                            Gauge32,
    cucsSwFcoeSanPcPortVsanId                                        Gauge32,
    cucsSwFcoeSanPcSwitchId                                          CucsNetworkSwitchId,
    cucsSwFcoeSanPcTransport                                         CucsSwFcoeSanPcTransport,
    cucsSwFcoeSanPcType                                              CucsSwSanPcType,
    cucsSwFcoeSanPcLacpFastTimer                                     TruthValue,
    cucsSwFcoeSanPcLacpSuspendIndividual                             TruthValue,
    cucsSwFcoeSanPcAdminSpeed                                        CucsPortEthAdminSpeed
}

cucsSwFcoeSanPcInstanceId OBJECT-TYPE
    SYNTAX       CucsManagedObjectId
    MAX-ACCESS   not-accessible
    STATUS       current
    DESCRIPTION
        "Instance identifier of the managed object."
    ::= { cucsSwFcoeSanPcEntry 1 }

cucsSwFcoeSanPcDn OBJECT-TYPE
    SYNTAX       CucsManagedObjectDn
    MAX-ACCESS   read-only
    STATUS       current
    DESCRIPTION
        "Cisco UCS sw:FcoeSanPc:dn managed object property"
    ::= { cucsSwFcoeSanPcEntry 2 }

cucsSwFcoeSanPcRn OBJECT-TYPE
    SYNTAX       SnmpAdminString
    MAX-ACCESS   read-only
    STATUS       current
    DESCRIPTION
        "Cisco UCS sw:FcoeSanPc:rn managed object property"
    ::= { cucsSwFcoeSanPcEntry 3 }

cucsSwFcoeSanPcAdminState OBJECT-TYPE
    SYNTAX       CucsFabricAdminState
    MAX-ACCESS   read-only
    STATUS       current
    DESCRIPTION
        "Cisco UCS sw:FcoeSanPc:adminState managed object property"
    ::= { cucsSwFcoeSanPcEntry 4 }

cucsSwFcoeSanPcEpDn OBJECT-TYPE
    SYNTAX       SnmpAdminString
    MAX-ACCESS   read-only
    STATUS       current
    DESCRIPTION
        "Cisco UCS sw:FcoeSanPc:epDn managed object property"
    ::= { cucsSwFcoeSanPcEntry 5 }

cucsSwFcoeSanPcIfRole OBJECT-TYPE
    SYNTAX       CucsSwSanPcIfRole
    MAX-ACCESS   read-only
    STATUS       current
    DESCRIPTION
        "Cisco UCS sw:FcoeSanPc:ifRole managed object property"
    ::= { cucsSwFcoeSanPcEntry 6 }

cucsSwFcoeSanPcIfType OBJECT-TYPE
    SYNTAX       CucsSwCIoEpIfType
    MAX-ACCESS   read-only
    STATUS       current
    DESCRIPTION
        "Cisco UCS sw:FcoeSanPc:ifType managed object property"
    ::= { cucsSwFcoeSanPcEntry 7 }

cucsSwFcoeSanPcLocale OBJECT-TYPE
    SYNTAX       CucsSwBorderPcLocale
    MAX-ACCESS   read-only
    STATUS       current
    DESCRIPTION
        "Cisco UCS sw:FcoeSanPc:locale managed object property"
    ::= { cucsSwFcoeSanPcEntry 8 }

cucsSwFcoeSanPcMonTrafDir OBJECT-TYPE
    SYNTAX       CucsFabricTrafficDirection
    MAX-ACCESS   read-only
    STATUS       current
    DESCRIPTION
        "Cisco UCS sw:FcoeSanPc:monTrafDir managed object property"
    ::= { cucsSwFcoeSanPcEntry 9 }

cucsSwFcoeSanPcName OBJECT-TYPE
    SYNTAX       SnmpAdminString
    MAX-ACCESS   read-only
    STATUS       current
    DESCRIPTION
        "Cisco UCS sw:FcoeSanPc:name managed object property"
    ::= { cucsSwFcoeSanPcEntry 10 }

cucsSwFcoeSanPcPcId OBJECT-TYPE
    SYNTAX       Gauge32
    MAX-ACCESS   read-only
    STATUS       current
    DESCRIPTION
        "Cisco UCS sw:FcoeSanPc:pcId managed object property"
    ::= { cucsSwFcoeSanPcEntry 11 }

cucsSwFcoeSanPcPeerDn OBJECT-TYPE
    SYNTAX       SnmpAdminString
    MAX-ACCESS   read-only
    STATUS       current
    DESCRIPTION
        "Cisco UCS sw:FcoeSanPc:peerDn managed object property"
    ::= { cucsSwFcoeSanPcEntry 12 }

cucsSwFcoeSanPcPeerState OBJECT-TYPE
    SYNTAX       CucsSwPeerStatus
    MAX-ACCESS   read-only
    STATUS       current
    DESCRIPTION
        "Cisco UCS sw:FcoeSanPc:peerState managed object property"
    ::= { cucsSwFcoeSanPcEntry 13 }

cucsSwFcoeSanPcPortId OBJECT-TYPE
    SYNTAX       Gauge32
    MAX-ACCESS   read-only
    STATUS       current
    DESCRIPTION
        "Cisco UCS sw:FcoeSanPc:portId managed object property"
    ::= { cucsSwFcoeSanPcEntry 14 }

cucsSwFcoeSanPcPortVsanId OBJECT-TYPE
    SYNTAX       Gauge32
    MAX-ACCESS   read-only
    STATUS       current
    DESCRIPTION
        "Cisco UCS sw:FcoeSanPc:portVsanId managed object property"
    ::= { cucsSwFcoeSanPcEntry 15 }

cucsSwFcoeSanPcSwitchId OBJECT-TYPE
    SYNTAX       CucsNetworkSwitchId
    MAX-ACCESS   read-only
    STATUS       current
    DESCRIPTION
        "Cisco UCS sw:FcoeSanPc:switchId managed object property"
    ::= { cucsSwFcoeSanPcEntry 16 }

cucsSwFcoeSanPcTransport OBJECT-TYPE
    SYNTAX       CucsSwFcoeSanPcTransport
    MAX-ACCESS   read-only
    STATUS       current
    DESCRIPTION
        "Cisco UCS sw:FcoeSanPc:transport managed object property"
    ::= { cucsSwFcoeSanPcEntry 17 }

cucsSwFcoeSanPcType OBJECT-TYPE
    SYNTAX       CucsSwSanPcType
    MAX-ACCESS   read-only
    STATUS       current
    DESCRIPTION
        "Cisco UCS sw:FcoeSanPc:type managed object property"
    ::= { cucsSwFcoeSanPcEntry 18 }

cucsSwFcoeSanPcLacpFastTimer OBJECT-TYPE
    SYNTAX       TruthValue
    MAX-ACCESS   read-only
    STATUS       current
    DESCRIPTION
        "Cisco UCS sw:FcoeSanPc:lacpFastTimer managed object property"
    ::= { cucsSwFcoeSanPcEntry 19 }

cucsSwFcoeSanPcLacpSuspendIndividual OBJECT-TYPE
    SYNTAX       TruthValue
    MAX-ACCESS   read-only
    STATUS       current
    DESCRIPTION
        "Cisco UCS sw:FcoeSanPc:lacpSuspendIndividual managed
        object property"
    ::= { cucsSwFcoeSanPcEntry 20 }

cucsSwFcoeSanPcAdminSpeed OBJECT-TYPE
    SYNTAX       CucsPortEthAdminSpeed
    MAX-ACCESS   read-only
    STATUS       current
    DESCRIPTION
        "Cisco UCS sw:FcoeSanPc:adminSpeed managed object property"
    ::= { cucsSwFcoeSanPcEntry 21 }

cucsSwIpRouteTable OBJECT-TYPE
    SYNTAX           SEQUENCE OF CucsSwIpRouteEntry
    MAX-ACCESS       not-accessible
    STATUS           current
    DESCRIPTION
        "Cisco UCS sw:IpRoute managed object table"
    ::= { cucsSwObjects 74 }

cucsSwIpRouteEntry OBJECT-TYPE
    SYNTAX           CucsSwIpRouteEntry
    MAX-ACCESS       not-accessible
    STATUS           current
    DESCRIPTION
        "Entry for the cucsSwIpRouteTable table."
    INDEX { cucsSwIpRouteInstanceId }
    ::= { cucsSwIpRouteTable 1 }

CucsSwIpRouteEntry ::= SEQUENCE {
    cucsSwIpRouteInstanceId                                          CucsManagedObjectId,
    cucsSwIpRouteDn                                                  CucsManagedObjectDn,
    cucsSwIpRouteRn                                                  SnmpAdminString,
    cucsSwIpRouteDestinationIp                                       InetAddressIPv4,
    cucsSwIpRouteDestinationNetmask                                  InetAddressIPv4,
    cucsSwIpRouteName                                                SnmpAdminString,
    cucsSwIpRoutePeerDn                                              SnmpAdminString,
    cucsSwIpRoutePrefix                                              Gauge32,
    cucsSwIpRouteRouteIP                                             InetAddressIPv4,
    cucsSwIpRouteSwitchId                                            CucsNetworkSwitchId
}

cucsSwIpRouteInstanceId OBJECT-TYPE
    SYNTAX       CucsManagedObjectId
    MAX-ACCESS   not-accessible
    STATUS       current
    DESCRIPTION
        "Instance identifier of the managed object."
    ::= { cucsSwIpRouteEntry 1 }

cucsSwIpRouteDn OBJECT-TYPE
    SYNTAX       CucsManagedObjectDn
    MAX-ACCESS   read-only
    STATUS       current
    DESCRIPTION
        "Cisco UCS sw:IpRoute:dn managed object property"
    ::= { cucsSwIpRouteEntry 2 }

cucsSwIpRouteRn OBJECT-TYPE
    SYNTAX       SnmpAdminString
    MAX-ACCESS   read-only
    STATUS       current
    DESCRIPTION
        "Cisco UCS sw:IpRoute:rn managed object property"
    ::= { cucsSwIpRouteEntry 3 }

cucsSwIpRouteDestinationIp OBJECT-TYPE
    SYNTAX       InetAddressIPv4
    MAX-ACCESS   read-only
    STATUS       current
    DESCRIPTION
        "Cisco UCS sw:IpRoute:destinationIp managed object property"
    ::= { cucsSwIpRouteEntry 4 }

cucsSwIpRouteDestinationNetmask OBJECT-TYPE
    SYNTAX       InetAddressIPv4
    MAX-ACCESS   read-only
    STATUS       current
    DESCRIPTION
        "Cisco UCS sw:IpRoute:destinationNetmask managed object property"
    ::= { cucsSwIpRouteEntry 5 }

cucsSwIpRouteName OBJECT-TYPE
    SYNTAX       SnmpAdminString
    MAX-ACCESS   read-only
    STATUS       current
    DESCRIPTION
        "Cisco UCS sw:IpRoute:name managed object property"
    ::= { cucsSwIpRouteEntry 6 }

cucsSwIpRoutePeerDn OBJECT-TYPE
    SYNTAX       SnmpAdminString
    MAX-ACCESS   read-only
    STATUS       current
    DESCRIPTION
        "Cisco UCS sw:IpRoute:peerDn managed object property"
    ::= { cucsSwIpRouteEntry 7 }

cucsSwIpRoutePrefix OBJECT-TYPE
    SYNTAX       Gauge32
    MAX-ACCESS   read-only
    STATUS       current
    DESCRIPTION
        "Cisco UCS sw:IpRoute:prefix managed object property"
    ::= { cucsSwIpRouteEntry 8 }

cucsSwIpRouteRouteIP OBJECT-TYPE
    SYNTAX       InetAddressIPv4
    MAX-ACCESS   read-only
    STATUS       current
    DESCRIPTION
        "Cisco UCS sw:IpRoute:routeIP managed object property"
    ::= { cucsSwIpRouteEntry 9 }

cucsSwIpRouteSwitchId OBJECT-TYPE
    SYNTAX       CucsNetworkSwitchId
    MAX-ACCESS   read-only
    STATUS       current
    DESCRIPTION
        "Cisco UCS sw:IpRoute:switchId managed object property"
    ::= { cucsSwIpRouteEntry 10 }

cucsSwNFExporterRefTable OBJECT-TYPE
    SYNTAX           SEQUENCE OF CucsSwNFExporterRefEntry
    MAX-ACCESS       not-accessible
    STATUS           current
    DESCRIPTION
        "Cisco UCS sw:NFExporterRef managed object table"
    ::= { cucsSwObjects 75 }

cucsSwNFExporterRefEntry OBJECT-TYPE
    SYNTAX           CucsSwNFExporterRefEntry
    MAX-ACCESS       not-accessible
    STATUS           current
    DESCRIPTION
        "Entry for the cucsSwNFExporterRefTable table."
    INDEX { cucsSwNFExporterRefInstanceId }
    ::= { cucsSwNFExporterRefTable 1 }

CucsSwNFExporterRefEntry ::= SEQUENCE {
    cucsSwNFExporterRefInstanceId                                    CucsManagedObjectId,
    cucsSwNFExporterRefDn                                            CucsManagedObjectDn,
    cucsSwNFExporterRefRn                                            SnmpAdminString,
    cucsSwNFExporterRefName                                          SnmpAdminString,
    cucsSwNFExporterRefPeerDn                                        SnmpAdminString
}

cucsSwNFExporterRefInstanceId OBJECT-TYPE
    SYNTAX       CucsManagedObjectId
    MAX-ACCESS   not-accessible
    STATUS       current
    DESCRIPTION
        "Instance identifier of the managed object."
    ::= { cucsSwNFExporterRefEntry 1 }

cucsSwNFExporterRefDn OBJECT-TYPE
    SYNTAX       CucsManagedObjectDn
    MAX-ACCESS   read-only
    STATUS       current
    DESCRIPTION
        "Cisco UCS sw:NFExporterRef:dn managed object property"
    ::= { cucsSwNFExporterRefEntry 2 }

cucsSwNFExporterRefRn OBJECT-TYPE
    SYNTAX       SnmpAdminString
    MAX-ACCESS   read-only
    STATUS       current
    DESCRIPTION
        "Cisco UCS sw:NFExporterRef:rn managed object property"
    ::= { cucsSwNFExporterRefEntry 3 }

cucsSwNFExporterRefName OBJECT-TYPE
    SYNTAX       SnmpAdminString
    MAX-ACCESS   read-only
    STATUS       current
    DESCRIPTION
        "Cisco UCS sw:NFExporterRef:name managed object property"
    ::= { cucsSwNFExporterRefEntry 4 }

cucsSwNFExporterRefPeerDn OBJECT-TYPE
    SYNTAX       SnmpAdminString
    MAX-ACCESS   read-only
    STATUS       current
    DESCRIPTION
        "Cisco UCS sw:NFExporterRef:peerDn managed object property"
    ::= { cucsSwNFExporterRefEntry 5 }

cucsSwNetflowExporterTable OBJECT-TYPE
    SYNTAX           SEQUENCE OF CucsSwNetflowExporterEntry
    MAX-ACCESS       not-accessible
    STATUS           current
    DESCRIPTION
        "Cisco UCS sw:NetflowExporter managed object table"
    ::= { cucsSwObjects 76 }

cucsSwNetflowExporterEntry OBJECT-TYPE
    SYNTAX           CucsSwNetflowExporterEntry
    MAX-ACCESS       not-accessible
    STATUS           current
    DESCRIPTION
        "Entry for the cucsSwNetflowExporterTable table."
    INDEX { cucsSwNetflowExporterInstanceId }
    ::= { cucsSwNetflowExporterTable 1 }

CucsSwNetflowExporterEntry ::= SEQUENCE {
    cucsSwNetflowExporterInstanceId                                  CucsManagedObjectId,
    cucsSwNetflowExporterDn                                          CucsManagedObjectDn,
    cucsSwNetflowExporterRn                                          SnmpAdminString,
    cucsSwNetflowExporterDestinationIpAddress                        InetAddressIPv4,
    cucsSwNetflowExporterDestinationPort                             Gauge32,
    cucsSwNetflowExporterDscp                                        Gauge32,
    cucsSwNetflowExporterExportInternal                              Gauge32,
    cucsSwNetflowExporterExporterStatsTimeout                        Gauge32,
    cucsSwNetflowExporterInterfaceTableTimeout                       Gauge32,
    cucsSwNetflowExporterIsValidConfig                               CucsSwNFConfigStatus,
    cucsSwNetflowExporterLifeCycle                                   CucsSwMonLifeCycle,
    cucsSwNetflowExporterName                                        SnmpAdminString,
    cucsSwNetflowExporterPeerDn                                      SnmpAdminString,
    cucsSwNetflowExporterProtocol                                    CucsSwNetflowExporterProtocol,
    cucsSwNetflowExporterSourceVlan                                  Gauge32,
    cucsSwNetflowExporterSwitchId                                    CucsNetworkSwitchId,
    cucsSwNetflowExporterTemplateDataTimeout                         Gauge32,
    cucsSwNetflowExporterTransport                                   CucsSwEthLanFlowMonExporterTransport,
    cucsSwNetflowExporterTransportProtocol                           CucsFabricNFTransport,
    cucsSwNetflowExporterType                                        CucsSwEthLanFlowMonExporterType,
    cucsSwNetflowExporterVersion                                     CucsFabricNFExporterVersion
}

cucsSwNetflowExporterInstanceId OBJECT-TYPE
    SYNTAX       CucsManagedObjectId
    MAX-ACCESS   not-accessible
    STATUS       current
    DESCRIPTION
        "Instance identifier of the managed object."
    ::= { cucsSwNetflowExporterEntry 1 }

cucsSwNetflowExporterDn OBJECT-TYPE
    SYNTAX       CucsManagedObjectDn
    MAX-ACCESS   read-only
    STATUS       current
    DESCRIPTION
        "Cisco UCS sw:NetflowExporter:dn managed object property"
    ::= { cucsSwNetflowExporterEntry 2 }

cucsSwNetflowExporterRn OBJECT-TYPE
    SYNTAX       SnmpAdminString
    MAX-ACCESS   read-only
    STATUS       current
    DESCRIPTION
        "Cisco UCS sw:NetflowExporter:rn managed object property"
    ::= { cucsSwNetflowExporterEntry 3 }

cucsSwNetflowExporterDestinationIpAddress OBJECT-TYPE
    SYNTAX       InetAddressIPv4
    MAX-ACCESS   read-only
    STATUS       current
    DESCRIPTION
        "Cisco UCS sw:NetflowExporter:destinationIpAddress
        managed object property"
    ::= { cucsSwNetflowExporterEntry 4 }

cucsSwNetflowExporterDestinationPort OBJECT-TYPE
    SYNTAX       Gauge32
    MAX-ACCESS   read-only
    STATUS       current
    DESCRIPTION
        "Cisco UCS sw:NetflowExporter:destinationPort managed
        object property"
    ::= { cucsSwNetflowExporterEntry 5 }

cucsSwNetflowExporterDscp OBJECT-TYPE
    SYNTAX       Gauge32
    MAX-ACCESS   read-only
    STATUS       current
    DESCRIPTION
        "Cisco UCS sw:NetflowExporter:dscp managed object property"
    ::= { cucsSwNetflowExporterEntry 6 }

cucsSwNetflowExporterExportInternal OBJECT-TYPE
    SYNTAX       Gauge32
    MAX-ACCESS   read-only
    STATUS       current
    DESCRIPTION
        "Cisco UCS sw:NetflowExporter:exportInternal managed
        object property"
    ::= { cucsSwNetflowExporterEntry 7 }

cucsSwNetflowExporterExporterStatsTimeout OBJECT-TYPE
    SYNTAX       Gauge32
    MAX-ACCESS   read-only
    STATUS       current
    DESCRIPTION
        "Cisco UCS sw:NetflowExporter:exporterStatsTimeout
        managed object property"
    ::= { cucsSwNetflowExporterEntry 8 }

cucsSwNetflowExporterInterfaceTableTimeout OBJECT-TYPE
    SYNTAX       Gauge32
    MAX-ACCESS   read-only
    STATUS       current
    DESCRIPTION
        "Cisco UCS sw:NetflowExporter:interfaceTableTimeout
        managed object property"
    ::= { cucsSwNetflowExporterEntry 9 }

cucsSwNetflowExporterIsValidConfig OBJECT-TYPE
    SYNTAX       CucsSwNFConfigStatus
    MAX-ACCESS   read-only
    STATUS       current
    DESCRIPTION
        "Cisco UCS sw:NetflowExporter:isValidConfig managed
        object property"
    ::= { cucsSwNetflowExporterEntry 10 }

cucsSwNetflowExporterLifeCycle OBJECT-TYPE
    SYNTAX       CucsSwMonLifeCycle
    MAX-ACCESS   read-only
    STATUS       current
    DESCRIPTION
        "Cisco UCS sw:NetflowExporter:lifeCycle managed object property"
    ::= { cucsSwNetflowExporterEntry 11 }

cucsSwNetflowExporterName OBJECT-TYPE
    SYNTAX       SnmpAdminString
    MAX-ACCESS   read-only
    STATUS       current
    DESCRIPTION
        "Cisco UCS sw:NetflowExporter:name managed object property"
    ::= { cucsSwNetflowExporterEntry 12 }

cucsSwNetflowExporterPeerDn OBJECT-TYPE
    SYNTAX       SnmpAdminString
    MAX-ACCESS   read-only
    STATUS       current
    DESCRIPTION
        "Cisco UCS sw:NetflowExporter:peerDn managed object property"
    ::= { cucsSwNetflowExporterEntry 13 }

cucsSwNetflowExporterProtocol OBJECT-TYPE
    SYNTAX       CucsSwNetflowExporterProtocol
    MAX-ACCESS   read-only
    STATUS       current
    DESCRIPTION
        "Cisco UCS sw:NetflowExporter:protocol managed object property"
    ::= { cucsSwNetflowExporterEntry 14 }

cucsSwNetflowExporterSourceVlan OBJECT-TYPE
    SYNTAX       Gauge32
    MAX-ACCESS   read-only
    STATUS       current
    DESCRIPTION
        "Cisco UCS sw:NetflowExporter:sourceVlan managed object property"
    ::= { cucsSwNetflowExporterEntry 15 }

cucsSwNetflowExporterSwitchId OBJECT-TYPE
    SYNTAX       CucsNetworkSwitchId
    MAX-ACCESS   read-only
    STATUS       current
    DESCRIPTION
        "Cisco UCS sw:NetflowExporter:switchId managed object property"
    ::= { cucsSwNetflowExporterEntry 16 }

cucsSwNetflowExporterTemplateDataTimeout OBJECT-TYPE
    SYNTAX       Gauge32
    MAX-ACCESS   read-only
    STATUS       current
    DESCRIPTION
        "Cisco UCS sw:NetflowExporter:templateDataTimeout
        managed object property"
    ::= { cucsSwNetflowExporterEntry 17 }

cucsSwNetflowExporterTransport OBJECT-TYPE
    SYNTAX       CucsSwEthLanFlowMonExporterTransport
    MAX-ACCESS   read-only
    STATUS       current
    DESCRIPTION
        "Cisco UCS sw:NetflowExporter:transport managed object property"
    ::= { cucsSwNetflowExporterEntry 18 }

cucsSwNetflowExporterTransportProtocol OBJECT-TYPE
    SYNTAX       CucsFabricNFTransport
    MAX-ACCESS   read-only
    STATUS       current
    DESCRIPTION
        "Cisco UCS sw:NetflowExporter:transportProtocol
        managed object property"
    ::= { cucsSwNetflowExporterEntry 19 }

cucsSwNetflowExporterType OBJECT-TYPE
    SYNTAX       CucsSwEthLanFlowMonExporterType
    MAX-ACCESS   read-only
    STATUS       current
    DESCRIPTION
        "Cisco UCS sw:NetflowExporter:type managed object property"
    ::= { cucsSwNetflowExporterEntry 20 }

cucsSwNetflowExporterVersion OBJECT-TYPE
    SYNTAX       CucsFabricNFExporterVersion
    MAX-ACCESS   read-only
    STATUS       current
    DESCRIPTION
        "Cisco UCS sw:NetflowExporter:version managed object property"
    ::= { cucsSwNetflowExporterEntry 21 }

cucsSwNetflowMonSessionTable OBJECT-TYPE
    SYNTAX           SEQUENCE OF CucsSwNetflowMonSessionEntry
    MAX-ACCESS       not-accessible
    STATUS           current
    DESCRIPTION
        "Cisco UCS sw:NetflowMonSession managed object table"
    ::= { cucsSwObjects 77 }

cucsSwNetflowMonSessionEntry OBJECT-TYPE
    SYNTAX           CucsSwNetflowMonSessionEntry
    MAX-ACCESS       not-accessible
    STATUS           current
    DESCRIPTION
        "Entry for the cucsSwNetflowMonSessionTable table."
    INDEX { cucsSwNetflowMonSessionInstanceId }
    ::= { cucsSwNetflowMonSessionTable 1 }

CucsSwNetflowMonSessionEntry ::= SEQUENCE {
    cucsSwNetflowMonSessionInstanceId                                CucsManagedObjectId,
    cucsSwNetflowMonSessionDn                                        CucsManagedObjectDn,
    cucsSwNetflowMonSessionRn                                        SnmpAdminString,
    cucsSwNetflowMonSessionAdminState                                CucsSwMonAdminState,
    cucsSwNetflowMonSessionHasLastDest                               TruthValue,
    cucsSwNetflowMonSessionLifeCycle                                 CucsSwMonLifeCycle,
    cucsSwNetflowMonSessionName                                      SnmpAdminString,
    cucsSwNetflowMonSessionPeerDn                                    SnmpAdminString,
    cucsSwNetflowMonSessionProtocol                                  CucsSwNetflowMonSessionProtocol,
    cucsSwNetflowMonSessionSession                                   Gauge32,
    cucsSwNetflowMonSessionSwitchId                                  CucsNetworkSwitchId,
    cucsSwNetflowMonSessionTransport                                 CucsSwEthFlowMonSessionTransport,
    cucsSwNetflowMonSessionType                                      CucsSwEthFlowMonSessionType
}

cucsSwNetflowMonSessionInstanceId OBJECT-TYPE
    SYNTAX       CucsManagedObjectId
    MAX-ACCESS   not-accessible
    STATUS       current
    DESCRIPTION
        "Instance identifier of the managed object."
    ::= { cucsSwNetflowMonSessionEntry 1 }

cucsSwNetflowMonSessionDn OBJECT-TYPE
    SYNTAX       CucsManagedObjectDn
    MAX-ACCESS   read-only
    STATUS       current
    DESCRIPTION
        "Cisco UCS sw:NetflowMonSession:dn managed object property"
    ::= { cucsSwNetflowMonSessionEntry 2 }

cucsSwNetflowMonSessionRn OBJECT-TYPE
    SYNTAX       SnmpAdminString
    MAX-ACCESS   read-only
    STATUS       current
    DESCRIPTION
        "Cisco UCS sw:NetflowMonSession:rn managed object property"
    ::= { cucsSwNetflowMonSessionEntry 3 }

cucsSwNetflowMonSessionAdminState OBJECT-TYPE
    SYNTAX       CucsSwMonAdminState
    MAX-ACCESS   read-only
    STATUS       current
    DESCRIPTION
        "Cisco UCS sw:NetflowMonSession:adminState managed
        object property"
    ::= { cucsSwNetflowMonSessionEntry 4 }

cucsSwNetflowMonSessionHasLastDest OBJECT-TYPE
    SYNTAX       TruthValue
    MAX-ACCESS   read-only
    STATUS       current
    DESCRIPTION
        "Cisco UCS sw:NetflowMonSession:hasLastDest managed
        object property"
    ::= { cucsSwNetflowMonSessionEntry 5 }

cucsSwNetflowMonSessionLifeCycle OBJECT-TYPE
    SYNTAX       CucsSwMonLifeCycle
    MAX-ACCESS   read-only
    STATUS       current
    DESCRIPTION
        "Cisco UCS sw:NetflowMonSession:lifeCycle managed object property"
    ::= { cucsSwNetflowMonSessionEntry 6 }

cucsSwNetflowMonSessionName OBJECT-TYPE
    SYNTAX       SnmpAdminString
    MAX-ACCESS   read-only
    STATUS       current
    DESCRIPTION
        "Cisco UCS sw:NetflowMonSession:name managed object property"
    ::= { cucsSwNetflowMonSessionEntry 7 }

cucsSwNetflowMonSessionPeerDn OBJECT-TYPE
    SYNTAX       SnmpAdminString
    MAX-ACCESS   read-only
    STATUS       current
    DESCRIPTION
        "Cisco UCS sw:NetflowMonSession:peerDn managed object property"
    ::= { cucsSwNetflowMonSessionEntry 8 }

cucsSwNetflowMonSessionProtocol OBJECT-TYPE
    SYNTAX       CucsSwNetflowMonSessionProtocol
    MAX-ACCESS   read-only
    STATUS       current
    DESCRIPTION
        "Cisco UCS sw:NetflowMonSession:protocol managed object property"
    ::= { cucsSwNetflowMonSessionEntry 9 }

cucsSwNetflowMonSessionSession OBJECT-TYPE
    SYNTAX       Gauge32
    MAX-ACCESS   read-only
    STATUS       current
    DESCRIPTION
        "Cisco UCS sw:NetflowMonSession:session managed object property"
    ::= { cucsSwNetflowMonSessionEntry 10 }

cucsSwNetflowMonSessionSwitchId OBJECT-TYPE
    SYNTAX       CucsNetworkSwitchId
    MAX-ACCESS   read-only
    STATUS       current
    DESCRIPTION
        "Cisco UCS sw:NetflowMonSession:switchId managed object property"
    ::= { cucsSwNetflowMonSessionEntry 11 }

cucsSwNetflowMonSessionTransport OBJECT-TYPE
    SYNTAX       CucsSwEthFlowMonSessionTransport
    MAX-ACCESS   read-only
    STATUS       current
    DESCRIPTION
        "Cisco UCS sw:NetflowMonSession:transport managed object property"
    ::= { cucsSwNetflowMonSessionEntry 12 }

cucsSwNetflowMonSessionType OBJECT-TYPE
    SYNTAX       CucsSwEthFlowMonSessionType
    MAX-ACCESS   read-only
    STATUS       current
    DESCRIPTION
        "Cisco UCS sw:NetflowMonSession:type managed object property"
    ::= { cucsSwNetflowMonSessionEntry 13 }

cucsSwNetflowMonitorTable OBJECT-TYPE
    SYNTAX           SEQUENCE OF CucsSwNetflowMonitorEntry
    MAX-ACCESS       not-accessible
    STATUS           current
    DESCRIPTION
        "Cisco UCS sw:NetflowMonitor managed object table"
    ::= { cucsSwObjects 78 }

cucsSwNetflowMonitorEntry OBJECT-TYPE
    SYNTAX           CucsSwNetflowMonitorEntry
    MAX-ACCESS       not-accessible
    STATUS           current
    DESCRIPTION
        "Entry for the cucsSwNetflowMonitorTable table."
    INDEX { cucsSwNetflowMonitorInstanceId }
    ::= { cucsSwNetflowMonitorTable 1 }

CucsSwNetflowMonitorEntry ::= SEQUENCE {
    cucsSwNetflowMonitorInstanceId                                   CucsManagedObjectId,
    cucsSwNetflowMonitorDn                                           CucsManagedObjectDn,
    cucsSwNetflowMonitorRn                                           SnmpAdminString,
    cucsSwNetflowMonitorActiveTimeout                                Gauge32,
    cucsSwNetflowMonitorAdminState                                   CucsSwFlowMonitorAdminState,
    cucsSwNetflowMonitorFlowRecordDefName                            SnmpAdminString,
    cucsSwNetflowMonitorInactiveTimeout                              Gauge32,
    cucsSwNetflowMonitorIsValidConfig                                CucsSwNFConfigStatus,
    cucsSwNetflowMonitorLifeCycle                                    CucsSwMonLifeCycle,
    cucsSwNetflowMonitorName                                         SnmpAdminString,
    cucsSwNetflowMonitorPeerDn                                       SnmpAdminString,
    cucsSwNetflowMonitorProtocol                                     CucsSwNetflowMonitorProtocol,
    cucsSwNetflowMonitorSwitchId                                     CucsNetworkSwitchId,
    cucsSwNetflowMonitorTransport                                    CucsSwEthLanFlowMonitorTransport,
    cucsSwNetflowMonitorType                                         CucsSwEthLanFlowMonitorType
}

cucsSwNetflowMonitorInstanceId OBJECT-TYPE
    SYNTAX       CucsManagedObjectId
    MAX-ACCESS   not-accessible
    STATUS       current
    DESCRIPTION
        "Instance identifier of the managed object."
    ::= { cucsSwNetflowMonitorEntry 1 }

cucsSwNetflowMonitorDn OBJECT-TYPE
    SYNTAX       CucsManagedObjectDn
    MAX-ACCESS   read-only
    STATUS       current
    DESCRIPTION
        "Cisco UCS sw:NetflowMonitor:dn managed object property"
    ::= { cucsSwNetflowMonitorEntry 2 }

cucsSwNetflowMonitorRn OBJECT-TYPE
    SYNTAX       SnmpAdminString
    MAX-ACCESS   read-only
    STATUS       current
    DESCRIPTION
        "Cisco UCS sw:NetflowMonitor:rn managed object property"
    ::= { cucsSwNetflowMonitorEntry 3 }

cucsSwNetflowMonitorActiveTimeout OBJECT-TYPE
    SYNTAX       Gauge32
    MAX-ACCESS   read-only
    STATUS       current
    DESCRIPTION
        "Cisco UCS sw:NetflowMonitor:activeTimeout managed
        object property"
    ::= { cucsSwNetflowMonitorEntry 4 }

cucsSwNetflowMonitorAdminState OBJECT-TYPE
    SYNTAX       CucsSwFlowMonitorAdminState
    MAX-ACCESS   read-only
    STATUS       current
    DESCRIPTION
        "Cisco UCS sw:NetflowMonitor:adminState managed object property"
    ::= { cucsSwNetflowMonitorEntry 5 }

cucsSwNetflowMonitorFlowRecordDefName OBJECT-TYPE
    SYNTAX       SnmpAdminString
    MAX-ACCESS   read-only
    STATUS       current
    DESCRIPTION
        "Cisco UCS sw:NetflowMonitor:flowRecordDefName
        managed object property"
    ::= { cucsSwNetflowMonitorEntry 6 }

cucsSwNetflowMonitorInactiveTimeout OBJECT-TYPE
    SYNTAX       Gauge32
    MAX-ACCESS   read-only
    STATUS       current
    DESCRIPTION
        "Cisco UCS sw:NetflowMonitor:inactiveTimeout managed
        object property"
    ::= { cucsSwNetflowMonitorEntry 7 }

cucsSwNetflowMonitorIsValidConfig OBJECT-TYPE
    SYNTAX       CucsSwNFConfigStatus
    MAX-ACCESS   read-only
    STATUS       current
    DESCRIPTION
        "Cisco UCS sw:NetflowMonitor:isValidConfig managed
        object property"
    ::= { cucsSwNetflowMonitorEntry 8 }

cucsSwNetflowMonitorLifeCycle OBJECT-TYPE
    SYNTAX       CucsSwMonLifeCycle
    MAX-ACCESS   read-only
    STATUS       current
    DESCRIPTION
        "Cisco UCS sw:NetflowMonitor:lifeCycle managed object property"
    ::= { cucsSwNetflowMonitorEntry 9 }

cucsSwNetflowMonitorName OBJECT-TYPE
    SYNTAX       SnmpAdminString
    MAX-ACCESS   read-only
    STATUS       current
    DESCRIPTION
        "Cisco UCS sw:NetflowMonitor:name managed object property"
    ::= { cucsSwNetflowMonitorEntry 10 }

cucsSwNetflowMonitorPeerDn OBJECT-TYPE
    SYNTAX       SnmpAdminString
    MAX-ACCESS   read-only
    STATUS       current
    DESCRIPTION
        "Cisco UCS sw:NetflowMonitor:peerDn managed object property"
    ::= { cucsSwNetflowMonitorEntry 11 }

cucsSwNetflowMonitorProtocol OBJECT-TYPE
    SYNTAX       CucsSwNetflowMonitorProtocol
    MAX-ACCESS   read-only
    STATUS       current
    DESCRIPTION
        "Cisco UCS sw:NetflowMonitor:protocol managed object property"
    ::= { cucsSwNetflowMonitorEntry 12 }

cucsSwNetflowMonitorSwitchId OBJECT-TYPE
    SYNTAX       CucsNetworkSwitchId
    MAX-ACCESS   read-only
    STATUS       current
    DESCRIPTION
        "Cisco UCS sw:NetflowMonitor:switchId managed object property"
    ::= { cucsSwNetflowMonitorEntry 13 }

cucsSwNetflowMonitorTransport OBJECT-TYPE
    SYNTAX       CucsSwEthLanFlowMonitorTransport
    MAX-ACCESS   read-only
    STATUS       current
    DESCRIPTION
        "Cisco UCS sw:NetflowMonitor:transport managed object property"
    ::= { cucsSwNetflowMonitorEntry 14 }

cucsSwNetflowMonitorType OBJECT-TYPE
    SYNTAX       CucsSwEthLanFlowMonitorType
    MAX-ACCESS   read-only
    STATUS       current
    DESCRIPTION
        "Cisco UCS sw:NetflowMonitor:type managed object property"
    ::= { cucsSwNetflowMonitorEntry 15 }

cucsSwNetflowMonitorRefTable OBJECT-TYPE
    SYNTAX           SEQUENCE OF CucsSwNetflowMonitorRefEntry
    MAX-ACCESS       not-accessible
    STATUS           current
    DESCRIPTION
        "Cisco UCS sw:NetflowMonitorRef managed object table"
    ::= { cucsSwObjects 79 }

cucsSwNetflowMonitorRefEntry OBJECT-TYPE
    SYNTAX           CucsSwNetflowMonitorRefEntry
    MAX-ACCESS       not-accessible
    STATUS           current
    DESCRIPTION
        "Entry for the cucsSwNetflowMonitorRefTable table."
    INDEX { cucsSwNetflowMonitorRefInstanceId }
    ::= { cucsSwNetflowMonitorRefTable 1 }

CucsSwNetflowMonitorRefEntry ::= SEQUENCE {
    cucsSwNetflowMonitorRefInstanceId                                CucsManagedObjectId,
    cucsSwNetflowMonitorRefDn                                        CucsManagedObjectDn,
    cucsSwNetflowMonitorRefRn                                        SnmpAdminString,
    cucsSwNetflowMonitorRefDirection                                 CucsFabricDirection,
    cucsSwNetflowMonitorRefKeyType                                   CucsFabricFlowMonKeyType,
    cucsSwNetflowMonitorRefName                                      SnmpAdminString,
    cucsSwNetflowMonitorRefSourceDn                                  SnmpAdminString
}

cucsSwNetflowMonitorRefInstanceId OBJECT-TYPE
    SYNTAX       CucsManagedObjectId
    MAX-ACCESS   not-accessible
    STATUS       current
    DESCRIPTION
        "Instance identifier of the managed object."
    ::= { cucsSwNetflowMonitorRefEntry 1 }

cucsSwNetflowMonitorRefDn OBJECT-TYPE
    SYNTAX       CucsManagedObjectDn
    MAX-ACCESS   read-only
    STATUS       current
    DESCRIPTION
        "Cisco UCS sw:NetflowMonitorRef:dn managed object property"
    ::= { cucsSwNetflowMonitorRefEntry 2 }

cucsSwNetflowMonitorRefRn OBJECT-TYPE
    SYNTAX       SnmpAdminString
    MAX-ACCESS   read-only
    STATUS       current
    DESCRIPTION
        "Cisco UCS sw:NetflowMonitorRef:rn managed object property"
    ::= { cucsSwNetflowMonitorRefEntry 3 }

cucsSwNetflowMonitorRefDirection OBJECT-TYPE
    SYNTAX       CucsFabricDirection
    MAX-ACCESS   read-only
    STATUS       current
    DESCRIPTION
        "Cisco UCS sw:NetflowMonitorRef:direction managed object property"
    ::= { cucsSwNetflowMonitorRefEntry 4 }

cucsSwNetflowMonitorRefKeyType OBJECT-TYPE
    SYNTAX       CucsFabricFlowMonKeyType
    MAX-ACCESS   read-only
    STATUS       current
    DESCRIPTION
        "Cisco UCS sw:NetflowMonitorRef:keyType managed object property"
    ::= { cucsSwNetflowMonitorRefEntry 5 }

cucsSwNetflowMonitorRefName OBJECT-TYPE
    SYNTAX       SnmpAdminString
    MAX-ACCESS   read-only
    STATUS       current
    DESCRIPTION
        "Cisco UCS sw:NetflowMonitorRef:name managed object property"
    ::= { cucsSwNetflowMonitorRefEntry 6 }

cucsSwNetflowMonitorRefSourceDn OBJECT-TYPE
    SYNTAX       SnmpAdminString
    MAX-ACCESS   read-only
    STATUS       current
    DESCRIPTION
        "Cisco UCS sw:NetflowMonitorRef:sourceDn managed object property"
    ::= { cucsSwNetflowMonitorRefEntry 7 }

cucsSwNetflowRecordDefTable OBJECT-TYPE
    SYNTAX           SEQUENCE OF CucsSwNetflowRecordDefEntry
    MAX-ACCESS       not-accessible
    STATUS           current
    DESCRIPTION
        "Cisco UCS sw:NetflowRecordDef managed object table"
    ::= { cucsSwObjects 80 }

cucsSwNetflowRecordDefEntry OBJECT-TYPE
    SYNTAX           CucsSwNetflowRecordDefEntry
    MAX-ACCESS       not-accessible
    STATUS           current
    DESCRIPTION
        "Entry for the cucsSwNetflowRecordDefTable table."
    INDEX { cucsSwNetflowRecordDefInstanceId }
    ::= { cucsSwNetflowRecordDefTable 1 }

CucsSwNetflowRecordDefEntry ::= SEQUENCE {
    cucsSwNetflowRecordDefInstanceId                                 CucsManagedObjectId,
    cucsSwNetflowRecordDefDn                                         CucsManagedObjectDn,
    cucsSwNetflowRecordDefRn                                         SnmpAdminString,
    cucsSwNetflowRecordDefIpv4keys                                   CucsFabricFlowMonIpv4Keys,
    cucsSwNetflowRecordDefIpv6keys                                   CucsFabricFlowMonIpv6Keys,
    cucsSwNetflowRecordDefKeyType                                    CucsFabricFlowMonKeyType,
    cucsSwNetflowRecordDefL2keys                                     CucsFabricFlowMonL2Keys,
    cucsSwNetflowRecordDefLifeCycle                                  CucsSwMonLifeCycle,
    cucsSwNetflowRecordDefName                                       SnmpAdminString,
    cucsSwNetflowRecordDefNonkeys                                    CucsFabricFlowMonNonKeys,
    cucsSwNetflowRecordDefPeerDn                                     SnmpAdminString,
    cucsSwNetflowRecordDefProtocol                                   CucsSwNetflowRecordDefProtocol,
    cucsSwNetflowRecordDefSwitchId                                   CucsNetworkSwitchId,
    cucsSwNetflowRecordDefTransport                                  CucsSwEthLanFlowRecordDefTransport,
    cucsSwNetflowRecordDefType                                       CucsSwEthLanFlowRecordDefType
}

cucsSwNetflowRecordDefInstanceId OBJECT-TYPE
    SYNTAX       CucsManagedObjectId
    MAX-ACCESS   not-accessible
    STATUS       current
    DESCRIPTION
        "Instance identifier of the managed object."
    ::= { cucsSwNetflowRecordDefEntry 1 }

cucsSwNetflowRecordDefDn OBJECT-TYPE
    SYNTAX       CucsManagedObjectDn
    MAX-ACCESS   read-only
    STATUS       current
    DESCRIPTION
        "Cisco UCS sw:NetflowRecordDef:dn managed object property"
    ::= { cucsSwNetflowRecordDefEntry 2 }

cucsSwNetflowRecordDefRn OBJECT-TYPE
    SYNTAX       SnmpAdminString
    MAX-ACCESS   read-only
    STATUS       current
    DESCRIPTION
        "Cisco UCS sw:NetflowRecordDef:rn managed object property"
    ::= { cucsSwNetflowRecordDefEntry 3 }

cucsSwNetflowRecordDefIpv4keys OBJECT-TYPE
    SYNTAX       CucsFabricFlowMonIpv4Keys
    MAX-ACCESS   read-only
    STATUS       current
    DESCRIPTION
        "Cisco UCS sw:NetflowRecordDef:ipv4keys managed object property"
    ::= { cucsSwNetflowRecordDefEntry 4 }

cucsSwNetflowRecordDefIpv6keys OBJECT-TYPE
    SYNTAX       CucsFabricFlowMonIpv6Keys
    MAX-ACCESS   read-only
    STATUS       current
    DESCRIPTION
        "Cisco UCS sw:NetflowRecordDef:ipv6keys managed object property"
    ::= { cucsSwNetflowRecordDefEntry 5 }

cucsSwNetflowRecordDefKeyType OBJECT-TYPE
    SYNTAX       CucsFabricFlowMonKeyType
    MAX-ACCESS   read-only
    STATUS       current
    DESCRIPTION
        "Cisco UCS sw:NetflowRecordDef:keyType managed object property"
    ::= { cucsSwNetflowRecordDefEntry 6 }

cucsSwNetflowRecordDefL2keys OBJECT-TYPE
    SYNTAX       CucsFabricFlowMonL2Keys
    MAX-ACCESS   read-only
    STATUS       current
    DESCRIPTION
        "Cisco UCS sw:NetflowRecordDef:l2keys managed object property"
    ::= { cucsSwNetflowRecordDefEntry 7 }

cucsSwNetflowRecordDefLifeCycle OBJECT-TYPE
    SYNTAX       CucsSwMonLifeCycle
    MAX-ACCESS   read-only
    STATUS       current
    DESCRIPTION
        "Cisco UCS sw:NetflowRecordDef:lifeCycle managed object property"
    ::= { cucsSwNetflowRecordDefEntry 8 }

cucsSwNetflowRecordDefName OBJECT-TYPE
    SYNTAX       SnmpAdminString
    MAX-ACCESS   read-only
    STATUS       current
    DESCRIPTION
        "Cisco UCS sw:NetflowRecordDef:name managed object property"
    ::= { cucsSwNetflowRecordDefEntry 9 }

cucsSwNetflowRecordDefNonkeys OBJECT-TYPE
    SYNTAX       CucsFabricFlowMonNonKeys
    MAX-ACCESS   read-only
    STATUS       current
    DESCRIPTION
        "Cisco UCS sw:NetflowRecordDef:nonkeys managed object property"
    ::= { cucsSwNetflowRecordDefEntry 10 }

cucsSwNetflowRecordDefPeerDn OBJECT-TYPE
    SYNTAX       SnmpAdminString
    MAX-ACCESS   read-only
    STATUS       current
    DESCRIPTION
        "Cisco UCS sw:NetflowRecordDef:peerDn managed object property"
    ::= { cucsSwNetflowRecordDefEntry 11 }

cucsSwNetflowRecordDefProtocol OBJECT-TYPE
    SYNTAX       CucsSwNetflowRecordDefProtocol
    MAX-ACCESS   read-only
    STATUS       current
    DESCRIPTION
        "Cisco UCS sw:NetflowRecordDef:protocol managed object property"
    ::= { cucsSwNetflowRecordDefEntry 12 }

cucsSwNetflowRecordDefSwitchId OBJECT-TYPE
    SYNTAX       CucsNetworkSwitchId
    MAX-ACCESS   read-only
    STATUS       current
    DESCRIPTION
        "Cisco UCS sw:NetflowRecordDef:switchId managed object property"
    ::= { cucsSwNetflowRecordDefEntry 13 }

cucsSwNetflowRecordDefTransport OBJECT-TYPE
    SYNTAX       CucsSwEthLanFlowRecordDefTransport
    MAX-ACCESS   read-only
    STATUS       current
    DESCRIPTION
        "Cisco UCS sw:NetflowRecordDef:transport managed object property"
    ::= { cucsSwNetflowRecordDefEntry 14 }

cucsSwNetflowRecordDefType OBJECT-TYPE
    SYNTAX       CucsSwEthLanFlowRecordDefType
    MAX-ACCESS   read-only
    STATUS       current
    DESCRIPTION
        "Cisco UCS sw:NetflowRecordDef:type managed object property"
    ::= { cucsSwNetflowRecordDefEntry 15 }

cucsSwPhysTable OBJECT-TYPE
    SYNTAX           SEQUENCE OF CucsSwPhysEntry
    MAX-ACCESS       not-accessible
    STATUS           current
    DESCRIPTION
        "Cisco UCS sw:Phys managed object table"
    ::= { cucsSwObjects 38 }

cucsSwPhysEntry OBJECT-TYPE
    SYNTAX           CucsSwPhysEntry
    MAX-ACCESS       not-accessible
    STATUS           current
    DESCRIPTION
        "Entry for the cucsSwPhysTable table."
    INDEX { cucsSwPhysInstanceId }
    ::= { cucsSwPhysTable 1 }

CucsSwPhysEntry ::= SEQUENCE {
    cucsSwPhysInstanceId                                             CucsManagedObjectId,
    cucsSwPhysDn                                                     CucsManagedObjectDn,
    cucsSwPhysRn                                                     SnmpAdminString,
    cucsSwPhysConfMode                                               CucsSwConfMode,
    cucsSwPhysFsmDescr                                               SnmpAdminString,
    cucsSwPhysFsmPrev                                                SnmpAdminString,
    cucsSwPhysFsmProgr                                               Gauge32,
    cucsSwPhysFsmRmtInvErrCode                                       Gauge32,
    cucsSwPhysFsmRmtInvErrDescr                                      SnmpAdminString,
    cucsSwPhysFsmRmtInvRslt                                          CucsConditionRemoteInvRslt,
    cucsSwPhysFsmStageDescr                                          SnmpAdminString,
    cucsSwPhysFsmStamp                                               DateAndTime,
    cucsSwPhysFsmStatus                                              SnmpAdminString,
    cucsSwPhysFsmTry                                                 Gauge32
}

cucsSwPhysInstanceId OBJECT-TYPE
    SYNTAX       CucsManagedObjectId
    MAX-ACCESS   not-accessible
    STATUS       current
    DESCRIPTION
        "Instance identifier of the managed object."
    ::= { cucsSwPhysEntry 1 }

cucsSwPhysDn OBJECT-TYPE
    SYNTAX       CucsManagedObjectDn
    MAX-ACCESS   read-only
    STATUS       current
    DESCRIPTION
        "Cisco UCS sw:Phys:dn managed object property"
    ::= { cucsSwPhysEntry 2 }

cucsSwPhysRn OBJECT-TYPE
    SYNTAX       SnmpAdminString
    MAX-ACCESS   read-only
    STATUS       current
    DESCRIPTION
        "Cisco UCS sw:Phys:rn managed object property"
    ::= { cucsSwPhysEntry 3 }

cucsSwPhysConfMode OBJECT-TYPE
    SYNTAX       CucsSwConfMode
    MAX-ACCESS   read-only
    STATUS       current
    DESCRIPTION
        "Cisco UCS sw:Phys:confMode managed object property"
    ::= { cucsSwPhysEntry 4 }

cucsSwPhysFsmDescr OBJECT-TYPE
    SYNTAX       SnmpAdminString
    MAX-ACCESS   read-only
    STATUS       current
    DESCRIPTION
        "Cisco UCS sw:Phys:fsmDescr managed object property"
    ::= { cucsSwPhysEntry 5 }

cucsSwPhysFsmPrev OBJECT-TYPE
    SYNTAX       SnmpAdminString
    MAX-ACCESS   read-only
    STATUS       current
    DESCRIPTION
        "Cisco UCS sw:Phys:fsmPrev managed object property"
    ::= { cucsSwPhysEntry 6 }

cucsSwPhysFsmProgr OBJECT-TYPE
    SYNTAX       Gauge32
    MAX-ACCESS   read-only
    STATUS       current
    DESCRIPTION
        "Cisco UCS sw:Phys:fsmProgr managed object property"
    ::= { cucsSwPhysEntry 7 }

cucsSwPhysFsmRmtInvErrCode OBJECT-TYPE
    SYNTAX       Gauge32
    MAX-ACCESS   read-only
    STATUS       current
    DESCRIPTION
        "Cisco UCS sw:Phys:fsmRmtInvErrCode managed object property"
    ::= { cucsSwPhysEntry 8 }

cucsSwPhysFsmRmtInvErrDescr OBJECT-TYPE
    SYNTAX       SnmpAdminString
    MAX-ACCESS   read-only
    STATUS       current
    DESCRIPTION
        "Cisco UCS sw:Phys:fsmRmtInvErrDescr managed object property"
    ::= { cucsSwPhysEntry 9 }

cucsSwPhysFsmRmtInvRslt OBJECT-TYPE
    SYNTAX       CucsConditionRemoteInvRslt
    MAX-ACCESS   read-only
    STATUS       current
    DESCRIPTION
        "Cisco UCS sw:Phys:fsmRmtInvRslt managed object property"
    ::= { cucsSwPhysEntry 10 }

cucsSwPhysFsmStageDescr OBJECT-TYPE
    SYNTAX       SnmpAdminString
    MAX-ACCESS   read-only
    STATUS       current
    DESCRIPTION
        "Cisco UCS sw:Phys:fsmStageDescr managed object property"
    ::= { cucsSwPhysEntry 11 }

cucsSwPhysFsmStamp OBJECT-TYPE
    SYNTAX       DateAndTime
    MAX-ACCESS   read-only
    STATUS       current
    DESCRIPTION
        "Cisco UCS sw:Phys:fsmStamp managed object property"
    ::= { cucsSwPhysEntry 12 }

cucsSwPhysFsmStatus OBJECT-TYPE
    SYNTAX       SnmpAdminString
    MAX-ACCESS   read-only
    STATUS       current
    DESCRIPTION
        "Cisco UCS sw:Phys:fsmStatus managed object property"
    ::= { cucsSwPhysEntry 13 }

cucsSwPhysFsmTry OBJECT-TYPE
    SYNTAX       Gauge32
    MAX-ACCESS   read-only
    STATUS       current
    DESCRIPTION
        "Cisco UCS sw:Phys:fsmTry managed object property"
    ::= { cucsSwPhysEntry 14 }

cucsSwPhysEtherEpTable OBJECT-TYPE
    SYNTAX           SEQUENCE OF CucsSwPhysEtherEpEntry
    MAX-ACCESS       not-accessible
    STATUS           current
    DESCRIPTION
        "Cisco UCS sw:PhysEtherEp managed object table"
    ::= { cucsSwObjects 39 }

cucsSwPhysEtherEpEntry OBJECT-TYPE
    SYNTAX           CucsSwPhysEtherEpEntry
    MAX-ACCESS       not-accessible
    STATUS           current
    DESCRIPTION
        "Entry for the cucsSwPhysEtherEpTable table."
    INDEX { cucsSwPhysEtherEpInstanceId }
    ::= { cucsSwPhysEtherEpTable 1 }

CucsSwPhysEtherEpEntry ::= SEQUENCE {
    cucsSwPhysEtherEpInstanceId                                      CucsManagedObjectId,
    cucsSwPhysEtherEpDn                                              CucsManagedObjectDn,
    cucsSwPhysEtherEpRn                                              SnmpAdminString,
    cucsSwPhysEtherEpAdminState                                      CucsFabricAdminState,
    cucsSwPhysEtherEpChassisId                                       Gauge32,
    cucsSwPhysEtherEpEpDn                                            SnmpAdminString,
    cucsSwPhysEtherEpIfRole                                          CucsNetworkPortRole,
    cucsSwPhysEtherEpIfType                                          CucsSwPIoEpIfType,
    cucsSwPhysEtherEpLc                                              CucsSwPIoEpLc,
    cucsSwPhysEtherEpLocale                                          CucsNetworkLocale,
    cucsSwPhysEtherEpName                                            SnmpAdminString,
    cucsSwPhysEtherEpPeerChassisId                                   Gauge32,
    cucsSwPhysEtherEpPeerDn                                          SnmpAdminString,
    cucsSwPhysEtherEpPeerPortId                                      Gauge32,
    cucsSwPhysEtherEpPeerSlotId                                      Gauge32,
    cucsSwPhysEtherEpPortId                                          Gauge32,
    cucsSwPhysEtherEpSlotId                                          Gauge32,
    cucsSwPhysEtherEpSwitchId                                        CucsNetworkSwitchId,
    cucsSwPhysEtherEpTransport                                       CucsNetworkTransport,
    cucsSwPhysEtherEpType                                            CucsNetworkConnectionType,
    cucsSwPhysEtherEpAggrPortId                                      Gauge32,
    cucsSwPhysEtherEpPeerAggrPortId                                  Gauge32
}

cucsSwPhysEtherEpInstanceId OBJECT-TYPE
    SYNTAX       CucsManagedObjectId
    MAX-ACCESS   not-accessible
    STATUS       current
    DESCRIPTION
        "Instance identifier of the managed object."
    ::= { cucsSwPhysEtherEpEntry 1 }

cucsSwPhysEtherEpDn OBJECT-TYPE
    SYNTAX       CucsManagedObjectDn
    MAX-ACCESS   read-only
    STATUS       current
    DESCRIPTION
        "Cisco UCS sw:PhysEtherEp:dn managed object property"
    ::= { cucsSwPhysEtherEpEntry 2 }

cucsSwPhysEtherEpRn OBJECT-TYPE
    SYNTAX       SnmpAdminString
    MAX-ACCESS   read-only
    STATUS       current
    DESCRIPTION
        "Cisco UCS sw:PhysEtherEp:rn managed object property"
    ::= { cucsSwPhysEtherEpEntry 3 }

cucsSwPhysEtherEpAdminState OBJECT-TYPE
    SYNTAX       CucsFabricAdminState
    MAX-ACCESS   read-only
    STATUS       current
    DESCRIPTION
        "Cisco UCS sw:PhysEtherEp:adminState managed object property"
    ::= { cucsSwPhysEtherEpEntry 4 }

cucsSwPhysEtherEpChassisId OBJECT-TYPE
    SYNTAX       Gauge32
    MAX-ACCESS   read-only
    STATUS       current
    DESCRIPTION
        "Cisco UCS sw:PhysEtherEp:chassisId managed object property"
    ::= { cucsSwPhysEtherEpEntry 5 }

cucsSwPhysEtherEpEpDn OBJECT-TYPE
    SYNTAX       SnmpAdminString
    MAX-ACCESS   read-only
    STATUS       current
    DESCRIPTION
        "Cisco UCS sw:PhysEtherEp:epDn managed object property"
    ::= { cucsSwPhysEtherEpEntry 6 }

cucsSwPhysEtherEpIfRole OBJECT-TYPE
    SYNTAX       CucsNetworkPortRole
    MAX-ACCESS   read-only
    STATUS       current
    DESCRIPTION
        "Cisco UCS sw:PhysEtherEp:ifRole managed object property"
    ::= { cucsSwPhysEtherEpEntry 7 }

cucsSwPhysEtherEpIfType OBJECT-TYPE
    SYNTAX       CucsSwPIoEpIfType
    MAX-ACCESS   read-only
    STATUS       current
    DESCRIPTION
        "Cisco UCS sw:PhysEtherEp:ifType managed object property"
    ::= { cucsSwPhysEtherEpEntry 8 }

cucsSwPhysEtherEpLc OBJECT-TYPE
    SYNTAX       CucsSwPIoEpLc
    MAX-ACCESS   read-only
    STATUS       current
    DESCRIPTION
        "Cisco UCS sw:PhysEtherEp:lc managed object property"
    ::= { cucsSwPhysEtherEpEntry 9 }

cucsSwPhysEtherEpLocale OBJECT-TYPE
    SYNTAX       CucsNetworkLocale
    MAX-ACCESS   read-only
    STATUS       current
    DESCRIPTION
        "Cisco UCS sw:PhysEtherEp:locale managed object property"
    ::= { cucsSwPhysEtherEpEntry 10 }

cucsSwPhysEtherEpName OBJECT-TYPE
    SYNTAX       SnmpAdminString
    MAX-ACCESS   read-only
    STATUS       current
    DESCRIPTION
        "Cisco UCS sw:PhysEtherEp:name managed object property"
    ::= { cucsSwPhysEtherEpEntry 11 }

cucsSwPhysEtherEpPeerChassisId OBJECT-TYPE
    SYNTAX       Gauge32
    MAX-ACCESS   read-only
    STATUS       current
    DESCRIPTION
        "Cisco UCS sw:PhysEtherEp:peerChassisId managed object property"
    ::= { cucsSwPhysEtherEpEntry 12 }

cucsSwPhysEtherEpPeerDn OBJECT-TYPE
    SYNTAX       SnmpAdminString
    MAX-ACCESS   read-only
    STATUS       current
    DESCRIPTION
        "Cisco UCS sw:PhysEtherEp:peerDn managed object property"
    ::= { cucsSwPhysEtherEpEntry 13 }

cucsSwPhysEtherEpPeerPortId OBJECT-TYPE
    SYNTAX       Gauge32
    MAX-ACCESS   read-only
    STATUS       current
    DESCRIPTION
        "Cisco UCS sw:PhysEtherEp:peerPortId managed object property"
    ::= { cucsSwPhysEtherEpEntry 14 }

cucsSwPhysEtherEpPeerSlotId OBJECT-TYPE
    SYNTAX       Gauge32
    MAX-ACCESS   read-only
    STATUS       current
    DESCRIPTION
        "Cisco UCS sw:PhysEtherEp:peerSlotId managed object property"
    ::= { cucsSwPhysEtherEpEntry 15 }

cucsSwPhysEtherEpPortId OBJECT-TYPE
    SYNTAX       Gauge32
    MAX-ACCESS   read-only
    STATUS       current
    DESCRIPTION
        "Cisco UCS sw:PhysEtherEp:portId managed object property"
    ::= { cucsSwPhysEtherEpEntry 16 }

cucsSwPhysEtherEpSlotId OBJECT-TYPE
    SYNTAX       Gauge32
    MAX-ACCESS   read-only
    STATUS       current
    DESCRIPTION
        "Cisco UCS sw:PhysEtherEp:slotId managed object property"
    ::= { cucsSwPhysEtherEpEntry 17 }

cucsSwPhysEtherEpSwitchId OBJECT-TYPE
    SYNTAX       CucsNetworkSwitchId
    MAX-ACCESS   read-only
    STATUS       current
    DESCRIPTION
        "Cisco UCS sw:PhysEtherEp:switchId managed object property"
    ::= { cucsSwPhysEtherEpEntry 18 }

cucsSwPhysEtherEpTransport OBJECT-TYPE
    SYNTAX       CucsNetworkTransport
    MAX-ACCESS   read-only
    STATUS       current
    DESCRIPTION
        "Cisco UCS sw:PhysEtherEp:transport managed object property"
    ::= { cucsSwPhysEtherEpEntry 19 }

cucsSwPhysEtherEpType OBJECT-TYPE
    SYNTAX       CucsNetworkConnectionType
    MAX-ACCESS   read-only
    STATUS       current
    DESCRIPTION
        "Cisco UCS sw:PhysEtherEp:type managed object property"
    ::= { cucsSwPhysEtherEpEntry 20 }

cucsSwPhysEtherEpAggrPortId OBJECT-TYPE
    SYNTAX       Gauge32
    MAX-ACCESS   read-only
    STATUS       current
    DESCRIPTION
        "Cisco UCS sw:PhysEtherEp:aggrPortId managed object property"
    ::= { cucsSwPhysEtherEpEntry 21 }

cucsSwPhysEtherEpPeerAggrPortId OBJECT-TYPE
    SYNTAX       Gauge32
    MAX-ACCESS   read-only
    STATUS       current
    DESCRIPTION
        "Cisco UCS sw:PhysEtherEp:peerAggrPortId managed object property"
    ::= { cucsSwPhysEtherEpEntry 22 }

cucsSwPhysFcEpTable OBJECT-TYPE
    SYNTAX           SEQUENCE OF CucsSwPhysFcEpEntry
    MAX-ACCESS       not-accessible
    STATUS           current
    DESCRIPTION
        "Cisco UCS sw:PhysFcEp managed object table"
    ::= { cucsSwObjects 40 }

cucsSwPhysFcEpEntry OBJECT-TYPE
    SYNTAX           CucsSwPhysFcEpEntry
    MAX-ACCESS       not-accessible
    STATUS           current
    DESCRIPTION
        "Entry for the cucsSwPhysFcEpTable table."
    INDEX { cucsSwPhysFcEpInstanceId }
    ::= { cucsSwPhysFcEpTable 1 }

CucsSwPhysFcEpEntry ::= SEQUENCE {
    cucsSwPhysFcEpInstanceId                                         CucsManagedObjectId,
    cucsSwPhysFcEpDn                                                 CucsManagedObjectDn,
    cucsSwPhysFcEpRn                                                 SnmpAdminString,
    cucsSwPhysFcEpAdminState                                         CucsFabricAdminState,
    cucsSwPhysFcEpChassisId                                          Gauge32,
    cucsSwPhysFcEpEpDn                                               SnmpAdminString,
    cucsSwPhysFcEpIfRole                                             CucsNetworkPortRole,
    cucsSwPhysFcEpIfType                                             CucsSwPIoEpIfType,
    cucsSwPhysFcEpLc                                                 CucsSwPIoEpLc,
    cucsSwPhysFcEpLocale                                             CucsNetworkLocale,
    cucsSwPhysFcEpName                                               SnmpAdminString,
    cucsSwPhysFcEpPeerChassisId                                      Gauge32,
    cucsSwPhysFcEpPeerDn                                             SnmpAdminString,
    cucsSwPhysFcEpPeerPortId                                         Gauge32,
    cucsSwPhysFcEpPeerSlotId                                         Gauge32,
    cucsSwPhysFcEpPortId                                             Gauge32,
    cucsSwPhysFcEpSlotId                                             Gauge32,
    cucsSwPhysFcEpSwitchId                                           CucsNetworkSwitchId,
    cucsSwPhysFcEpTransport                                          CucsNetworkTransport,
    cucsSwPhysFcEpType                                               CucsNetworkConnectionType,
    cucsSwPhysFcEpAggrPortId                                         Gauge32,
    cucsSwPhysFcEpPeerAggrPortId                                     Gauge32
}

cucsSwPhysFcEpInstanceId OBJECT-TYPE
    SYNTAX       CucsManagedObjectId
    MAX-ACCESS   not-accessible
    STATUS       current
    DESCRIPTION
        "Instance identifier of the managed object."
    ::= { cucsSwPhysFcEpEntry 1 }

cucsSwPhysFcEpDn OBJECT-TYPE
    SYNTAX       CucsManagedObjectDn
    MAX-ACCESS   read-only
    STATUS       current
    DESCRIPTION
        "Cisco UCS sw:PhysFcEp:dn managed object property"
    ::= { cucsSwPhysFcEpEntry 2 }

cucsSwPhysFcEpRn OBJECT-TYPE
    SYNTAX       SnmpAdminString
    MAX-ACCESS   read-only
    STATUS       current
    DESCRIPTION
        "Cisco UCS sw:PhysFcEp:rn managed object property"
    ::= { cucsSwPhysFcEpEntry 3 }

cucsSwPhysFcEpAdminState OBJECT-TYPE
    SYNTAX       CucsFabricAdminState
    MAX-ACCESS   read-only
    STATUS       current
    DESCRIPTION
        "Cisco UCS sw:PhysFcEp:adminState managed object property"
    ::= { cucsSwPhysFcEpEntry 4 }

cucsSwPhysFcEpChassisId OBJECT-TYPE
    SYNTAX       Gauge32
    MAX-ACCESS   read-only
    STATUS       current
    DESCRIPTION
        "Cisco UCS sw:PhysFcEp:chassisId managed object property"
    ::= { cucsSwPhysFcEpEntry 5 }

cucsSwPhysFcEpEpDn OBJECT-TYPE
    SYNTAX       SnmpAdminString
    MAX-ACCESS   read-only
    STATUS       current
    DESCRIPTION
        "Cisco UCS sw:PhysFcEp:epDn managed object property"
    ::= { cucsSwPhysFcEpEntry 6 }

cucsSwPhysFcEpIfRole OBJECT-TYPE
    SYNTAX       CucsNetworkPortRole
    MAX-ACCESS   read-only
    STATUS       current
    DESCRIPTION
        "Cisco UCS sw:PhysFcEp:ifRole managed object property"
    ::= { cucsSwPhysFcEpEntry 7 }

cucsSwPhysFcEpIfType OBJECT-TYPE
    SYNTAX       CucsSwPIoEpIfType
    MAX-ACCESS   read-only
    STATUS       current
    DESCRIPTION
        "Cisco UCS sw:PhysFcEp:ifType managed object property"
    ::= { cucsSwPhysFcEpEntry 8 }

cucsSwPhysFcEpLc OBJECT-TYPE
    SYNTAX       CucsSwPIoEpLc
    MAX-ACCESS   read-only
    STATUS       current
    DESCRIPTION
        "Cisco UCS sw:PhysFcEp:lc managed object property"
    ::= { cucsSwPhysFcEpEntry 9 }

cucsSwPhysFcEpLocale OBJECT-TYPE
    SYNTAX       CucsNetworkLocale
    MAX-ACCESS   read-only
    STATUS       current
    DESCRIPTION
        "Cisco UCS sw:PhysFcEp:locale managed object property"
    ::= { cucsSwPhysFcEpEntry 10 }

cucsSwPhysFcEpName OBJECT-TYPE
    SYNTAX       SnmpAdminString
    MAX-ACCESS   read-only
    STATUS       current
    DESCRIPTION
        "Cisco UCS sw:PhysFcEp:name managed object property"
    ::= { cucsSwPhysFcEpEntry 11 }

cucsSwPhysFcEpPeerChassisId OBJECT-TYPE
    SYNTAX       Gauge32
    MAX-ACCESS   read-only
    STATUS       current
    DESCRIPTION
        "Cisco UCS sw:PhysFcEp:peerChassisId managed object property"
    ::= { cucsSwPhysFcEpEntry 12 }

cucsSwPhysFcEpPeerDn OBJECT-TYPE
    SYNTAX       SnmpAdminString
    MAX-ACCESS   read-only
    STATUS       current
    DESCRIPTION
        "Cisco UCS sw:PhysFcEp:peerDn managed object property"
    ::= { cucsSwPhysFcEpEntry 13 }

cucsSwPhysFcEpPeerPortId OBJECT-TYPE
    SYNTAX       Gauge32
    MAX-ACCESS   read-only
    STATUS       current
    DESCRIPTION
        "Cisco UCS sw:PhysFcEp:peerPortId managed object property"
    ::= { cucsSwPhysFcEpEntry 14 }

cucsSwPhysFcEpPeerSlotId OBJECT-TYPE
    SYNTAX       Gauge32
    MAX-ACCESS   read-only
    STATUS       current
    DESCRIPTION
        "Cisco UCS sw:PhysFcEp:peerSlotId managed object property"
    ::= { cucsSwPhysFcEpEntry 15 }

cucsSwPhysFcEpPortId OBJECT-TYPE
    SYNTAX       Gauge32
    MAX-ACCESS   read-only
    STATUS       current
    DESCRIPTION
        "Cisco UCS sw:PhysFcEp:portId managed object property"
    ::= { cucsSwPhysFcEpEntry 16 }

cucsSwPhysFcEpSlotId OBJECT-TYPE
    SYNTAX       Gauge32
    MAX-ACCESS   read-only
    STATUS       current
    DESCRIPTION
        "Cisco UCS sw:PhysFcEp:slotId managed object property"
    ::= { cucsSwPhysFcEpEntry 17 }

cucsSwPhysFcEpSwitchId OBJECT-TYPE
    SYNTAX       CucsNetworkSwitchId
    MAX-ACCESS   read-only
    STATUS       current
    DESCRIPTION
        "Cisco UCS sw:PhysFcEp:switchId managed object property"
    ::= { cucsSwPhysFcEpEntry 18 }

cucsSwPhysFcEpTransport OBJECT-TYPE
    SYNTAX       CucsNetworkTransport
    MAX-ACCESS   read-only
    STATUS       current
    DESCRIPTION
        "Cisco UCS sw:PhysFcEp:transport managed object property"
    ::= { cucsSwPhysFcEpEntry 19 }

cucsSwPhysFcEpType OBJECT-TYPE
    SYNTAX       CucsNetworkConnectionType
    MAX-ACCESS   read-only
    STATUS       current
    DESCRIPTION
        "Cisco UCS sw:PhysFcEp:type managed object property"
    ::= { cucsSwPhysFcEpEntry 20 }

cucsSwPhysFcEpAggrPortId OBJECT-TYPE
    SYNTAX       Gauge32
    MAX-ACCESS   read-only
    STATUS       current
    DESCRIPTION
        "Cisco UCS sw:PhysFcEp:aggrPortId managed object property"
    ::= { cucsSwPhysFcEpEntry 21 }

cucsSwPhysFcEpPeerAggrPortId OBJECT-TYPE
    SYNTAX       Gauge32
    MAX-ACCESS   read-only
    STATUS       current
    DESCRIPTION
        "Cisco UCS sw:PhysFcEp:peerAggrPortId managed object property"
    ::= { cucsSwPhysFcEpEntry 22 }

cucsSwPhysFsmTable OBJECT-TYPE
    SYNTAX           SEQUENCE OF CucsSwPhysFsmEntry
    MAX-ACCESS       not-accessible
    STATUS           current
    DESCRIPTION
        "Cisco UCS sw:PhysFsm managed object table"
    ::= { cucsSwObjects 61 }

cucsSwPhysFsmEntry OBJECT-TYPE
    SYNTAX           CucsSwPhysFsmEntry
    MAX-ACCESS       not-accessible
    STATUS           current
    DESCRIPTION
        "Entry for the cucsSwPhysFsmTable table."
    INDEX { cucsSwPhysFsmInstanceId }
    ::= { cucsSwPhysFsmTable 1 }

CucsSwPhysFsmEntry ::= SEQUENCE {
    cucsSwPhysFsmInstanceId                                          CucsManagedObjectId,
    cucsSwPhysFsmDn                                                  CucsManagedObjectDn,
    cucsSwPhysFsmRn                                                  SnmpAdminString,
    cucsSwPhysFsmCompletionTime                                      DateAndTime,
    cucsSwPhysFsmCurrentFsm                                          CucsSwPhysFsmCurrentFsm,
    cucsSwPhysFsmDescrData                                           SnmpAdminString,
    cucsSwPhysFsmFsmStatus                                           CucsFsmFsmStageStatus,
    cucsSwPhysFsmProgress                                            Gauge32,
    cucsSwPhysFsmRmtErrCode                                          Gauge32,
    cucsSwPhysFsmRmtErrDescr                                         SnmpAdminString,
    cucsSwPhysFsmRmtRslt                                             CucsConditionRemoteInvRslt
}

cucsSwPhysFsmInstanceId OBJECT-TYPE
    SYNTAX       CucsManagedObjectId
    MAX-ACCESS   not-accessible
    STATUS       current
    DESCRIPTION
        "Instance identifier of the managed object."
    ::= { cucsSwPhysFsmEntry 1 }

cucsSwPhysFsmDn OBJECT-TYPE
    SYNTAX       CucsManagedObjectDn
    MAX-ACCESS   read-only
    STATUS       current
    DESCRIPTION
        "Cisco UCS sw:PhysFsm:dn managed object property"
    ::= { cucsSwPhysFsmEntry 2 }

cucsSwPhysFsmRn OBJECT-TYPE
    SYNTAX       SnmpAdminString
    MAX-ACCESS   read-only
    STATUS       current
    DESCRIPTION
        "Cisco UCS sw:PhysFsm:rn managed object property"
    ::= { cucsSwPhysFsmEntry 3 }

cucsSwPhysFsmCompletionTime OBJECT-TYPE
    SYNTAX       DateAndTime
    MAX-ACCESS   read-only
    STATUS       current
    DESCRIPTION
        "Cisco UCS sw:PhysFsm:completionTime managed object property"
    ::= { cucsSwPhysFsmEntry 4 }

cucsSwPhysFsmCurrentFsm OBJECT-TYPE
    SYNTAX       CucsSwPhysFsmCurrentFsm
    MAX-ACCESS   read-only
    STATUS       current
    DESCRIPTION
        "Cisco UCS sw:PhysFsm:currentFsm managed object property"
    ::= { cucsSwPhysFsmEntry 5 }

cucsSwPhysFsmDescrData OBJECT-TYPE
    SYNTAX       SnmpAdminString
    MAX-ACCESS   read-only
    STATUS       current
    DESCRIPTION
        "Cisco UCS sw:PhysFsm:descr managed object property"
    ::= { cucsSwPhysFsmEntry 6 }

cucsSwPhysFsmFsmStatus OBJECT-TYPE
    SYNTAX       CucsFsmFsmStageStatus
    MAX-ACCESS   read-only
    STATUS       current
    DESCRIPTION
        "Cisco UCS sw:PhysFsm:fsmStatus managed object property"
    ::= { cucsSwPhysFsmEntry 7 }

cucsSwPhysFsmProgress OBJECT-TYPE
    SYNTAX       Gauge32
    MAX-ACCESS   read-only
    STATUS       current
    DESCRIPTION
        "Cisco UCS sw:PhysFsm:progress managed object property"
    ::= { cucsSwPhysFsmEntry 8 }

cucsSwPhysFsmRmtErrCode OBJECT-TYPE
    SYNTAX       Gauge32
    MAX-ACCESS   read-only
    STATUS       current
    DESCRIPTION
        "Cisco UCS sw:PhysFsm:rmtErrCode managed object property"
    ::= { cucsSwPhysFsmEntry 9 }

cucsSwPhysFsmRmtErrDescr OBJECT-TYPE
    SYNTAX       SnmpAdminString
    MAX-ACCESS   read-only
    STATUS       current
    DESCRIPTION
        "Cisco UCS sw:PhysFsm:rmtErrDescr managed object property"
    ::= { cucsSwPhysFsmEntry 10 }

cucsSwPhysFsmRmtRslt OBJECT-TYPE
    SYNTAX       CucsConditionRemoteInvRslt
    MAX-ACCESS   read-only
    STATUS       current
    DESCRIPTION
        "Cisco UCS sw:PhysFsm:rmtRslt managed object property"
    ::= { cucsSwPhysFsmEntry 11 }

cucsSwPhysFsmStageTable OBJECT-TYPE
    SYNTAX           SEQUENCE OF CucsSwPhysFsmStageEntry
    MAX-ACCESS       not-accessible
    STATUS           current
    DESCRIPTION
        "Cisco UCS sw:PhysFsmStage managed object table"
    ::= { cucsSwObjects 62 }

cucsSwPhysFsmStageEntry OBJECT-TYPE
    SYNTAX           CucsSwPhysFsmStageEntry
    MAX-ACCESS       not-accessible
    STATUS           current
    DESCRIPTION
        "Entry for the cucsSwPhysFsmStageTable table."
    INDEX { cucsSwPhysFsmStageInstanceId }
    ::= { cucsSwPhysFsmStageTable 1 }

CucsSwPhysFsmStageEntry ::= SEQUENCE {
    cucsSwPhysFsmStageInstanceId                                     CucsManagedObjectId,
    cucsSwPhysFsmStageDn                                             CucsManagedObjectDn,
    cucsSwPhysFsmStageRn                                             SnmpAdminString,
    cucsSwPhysFsmStageDescrData                                      SnmpAdminString,
    cucsSwPhysFsmStageLastUpdateTime                                 DateAndTime,
    cucsSwPhysFsmStageName                                           CucsSwPhysFsmStageName,
    cucsSwPhysFsmStageOrder                                          Gauge32,
    cucsSwPhysFsmStageRetry                                          Gauge32,
    cucsSwPhysFsmStageStageStatus                                    CucsFsmFsmStageStatus
}

cucsSwPhysFsmStageInstanceId OBJECT-TYPE
    SYNTAX       CucsManagedObjectId
    MAX-ACCESS   not-accessible
    STATUS       current
    DESCRIPTION
        "Instance identifier of the managed object."
    ::= { cucsSwPhysFsmStageEntry 1 }

cucsSwPhysFsmStageDn OBJECT-TYPE
    SYNTAX       CucsManagedObjectDn
    MAX-ACCESS   read-only
    STATUS       current
    DESCRIPTION
        "Cisco UCS sw:PhysFsmStage:dn managed object property"
    ::= { cucsSwPhysFsmStageEntry 2 }

cucsSwPhysFsmStageRn OBJECT-TYPE
    SYNTAX       SnmpAdminString
    MAX-ACCESS   read-only
    STATUS       current
    DESCRIPTION
        "Cisco UCS sw:PhysFsmStage:rn managed object property"
    ::= { cucsSwPhysFsmStageEntry 3 }

cucsSwPhysFsmStageDescrData OBJECT-TYPE
    SYNTAX       SnmpAdminString
    MAX-ACCESS   read-only
    STATUS       current
    DESCRIPTION
        "Cisco UCS sw:PhysFsmStage:descr managed object property"
    ::= { cucsSwPhysFsmStageEntry 4 }

cucsSwPhysFsmStageLastUpdateTime OBJECT-TYPE
    SYNTAX       DateAndTime
    MAX-ACCESS   read-only
    STATUS       current
    DESCRIPTION
        "Cisco UCS sw:PhysFsmStage:lastUpdateTime managed object property"
    ::= { cucsSwPhysFsmStageEntry 5 }

cucsSwPhysFsmStageName OBJECT-TYPE
    SYNTAX       CucsSwPhysFsmStageName
    MAX-ACCESS   read-only
    STATUS       current
    DESCRIPTION
        "Cisco UCS sw:PhysFsmStage:name managed object property"
    ::= { cucsSwPhysFsmStageEntry 6 }

cucsSwPhysFsmStageOrder OBJECT-TYPE
    SYNTAX       Gauge32
    MAX-ACCESS   read-only
    STATUS       current
    DESCRIPTION
        "Cisco UCS sw:PhysFsmStage:order managed object property"
    ::= { cucsSwPhysFsmStageEntry 7 }

cucsSwPhysFsmStageRetry OBJECT-TYPE
    SYNTAX       Gauge32
    MAX-ACCESS   read-only
    STATUS       current
    DESCRIPTION
        "Cisco UCS sw:PhysFsmStage:retry managed object property"
    ::= { cucsSwPhysFsmStageEntry 8 }

cucsSwPhysFsmStageStageStatus OBJECT-TYPE
    SYNTAX       CucsFsmFsmStageStatus
    MAX-ACCESS   read-only
    STATUS       current
    DESCRIPTION
        "Cisco UCS sw:PhysFsmStage:stageStatus managed object property"
    ::= { cucsSwPhysFsmStageEntry 9 }

cucsSwPhysFsmTaskTable OBJECT-TYPE
    SYNTAX           SEQUENCE OF CucsSwPhysFsmTaskEntry
    MAX-ACCESS       not-accessible
    STATUS           current
    DESCRIPTION
        "Cisco UCS sw:PhysFsmTask managed object table"
    ::= { cucsSwObjects 41 }

cucsSwPhysFsmTaskEntry OBJECT-TYPE
    SYNTAX           CucsSwPhysFsmTaskEntry
    MAX-ACCESS       not-accessible
    STATUS           current
    DESCRIPTION
        "Entry for the cucsSwPhysFsmTaskTable table."
    INDEX { cucsSwPhysFsmTaskInstanceId }
    ::= { cucsSwPhysFsmTaskTable 1 }

CucsSwPhysFsmTaskEntry ::= SEQUENCE {
    cucsSwPhysFsmTaskInstanceId                                      CucsManagedObjectId,
    cucsSwPhysFsmTaskDn                                              CucsManagedObjectDn,
    cucsSwPhysFsmTaskRn                                              SnmpAdminString,
    cucsSwPhysFsmTaskCompletion                                      CucsFsmCompletion,
    cucsSwPhysFsmTaskFlags                                           CucsFsmFlags,
    cucsSwPhysFsmTaskItem                                            CucsSwPhysFsmTaskItem,
    cucsSwPhysFsmTaskSeqId                                           Gauge32
}

cucsSwPhysFsmTaskInstanceId OBJECT-TYPE
    SYNTAX       CucsManagedObjectId
    MAX-ACCESS   not-accessible
    STATUS       current
    DESCRIPTION
        "Instance identifier of the managed object."
    ::= { cucsSwPhysFsmTaskEntry 1 }

cucsSwPhysFsmTaskDn OBJECT-TYPE
    SYNTAX       CucsManagedObjectDn
    MAX-ACCESS   read-only
    STATUS       current
    DESCRIPTION
        "Cisco UCS sw:PhysFsmTask:dn managed object property"
    ::= { cucsSwPhysFsmTaskEntry 2 }

cucsSwPhysFsmTaskRn OBJECT-TYPE
    SYNTAX       SnmpAdminString
    MAX-ACCESS   read-only
    STATUS       current
    DESCRIPTION
        "Cisco UCS sw:PhysFsmTask:rn managed object property"
    ::= { cucsSwPhysFsmTaskEntry 3 }

cucsSwPhysFsmTaskCompletion OBJECT-TYPE
    SYNTAX       CucsFsmCompletion
    MAX-ACCESS   read-only
    STATUS       current
    DESCRIPTION
        "Cisco UCS sw:PhysFsmTask:completion managed object property"
    ::= { cucsSwPhysFsmTaskEntry 4 }

cucsSwPhysFsmTaskFlags OBJECT-TYPE
    SYNTAX       CucsFsmFlags
    MAX-ACCESS   read-only
    STATUS       current
    DESCRIPTION
        "Cisco UCS sw:PhysFsmTask:flags managed object property"
    ::= { cucsSwPhysFsmTaskEntry 5 }

cucsSwPhysFsmTaskItem OBJECT-TYPE
    SYNTAX       CucsSwPhysFsmTaskItem
    MAX-ACCESS   read-only
    STATUS       current
    DESCRIPTION
        "Cisco UCS sw:PhysFsmTask:item managed object property"
    ::= { cucsSwPhysFsmTaskEntry 6 }

cucsSwPhysFsmTaskSeqId OBJECT-TYPE
    SYNTAX       Gauge32
    MAX-ACCESS   read-only
    STATUS       current
    DESCRIPTION
        "Cisco UCS sw:PhysFsmTask:seqId managed object property"
    ::= { cucsSwPhysFsmTaskEntry 7 }

cucsSwPortBreakoutTable OBJECT-TYPE
    SYNTAX           SEQUENCE OF CucsSwPortBreakoutEntry
    MAX-ACCESS       not-accessible
    STATUS           current
    DESCRIPTION
        "Cisco UCS sw:PortBreakout managed object table"
    ::= { cucsSwObjects 87 }

cucsSwPortBreakoutEntry OBJECT-TYPE
    SYNTAX           CucsSwPortBreakoutEntry
    MAX-ACCESS       not-accessible
    STATUS           current
    DESCRIPTION
        "Entry for the cucsSwPortBreakoutTable table."
    INDEX { cucsSwPortBreakoutInstanceId }
    ::= { cucsSwPortBreakoutTable 1 }

CucsSwPortBreakoutEntry ::= SEQUENCE {
    cucsSwPortBreakoutInstanceId                                     CucsManagedObjectId,
    cucsSwPortBreakoutDn                                             CucsManagedObjectDn,
    cucsSwPortBreakoutRn                                             SnmpAdminString,
    cucsSwPortBreakoutBreakoutType                                   CucsSwBreakoutType,
    cucsSwPortBreakoutPortId                                         CucsSwPortBreakoutPortId,
    cucsSwPortBreakoutSlotId                                         CucsSwPortBreakoutSlotId
}

cucsSwPortBreakoutInstanceId OBJECT-TYPE
    SYNTAX       CucsManagedObjectId
    MAX-ACCESS   not-accessible
    STATUS       current
    DESCRIPTION
        "Instance identifier of the managed object."
    ::= { cucsSwPortBreakoutEntry 1 }

cucsSwPortBreakoutDn OBJECT-TYPE
    SYNTAX       CucsManagedObjectDn
    MAX-ACCESS   read-only
    STATUS       current
    DESCRIPTION
        "Cisco UCS sw:PortBreakout:dn managed object property"
    ::= { cucsSwPortBreakoutEntry 2 }

cucsSwPortBreakoutRn OBJECT-TYPE
    SYNTAX       SnmpAdminString
    MAX-ACCESS   read-only
    STATUS       current
    DESCRIPTION
        "Cisco UCS sw:PortBreakout:rn managed object property"
    ::= { cucsSwPortBreakoutEntry 3 }

cucsSwPortBreakoutBreakoutType OBJECT-TYPE
    SYNTAX       CucsSwBreakoutType
    MAX-ACCESS   read-only
    STATUS       current
    DESCRIPTION
        "Cisco UCS sw:PortBreakout:breakoutType managed object property"
    ::= { cucsSwPortBreakoutEntry 4 }

cucsSwPortBreakoutPortId OBJECT-TYPE
    SYNTAX       CucsSwPortBreakoutPortId
    MAX-ACCESS   read-only
    STATUS       current
    DESCRIPTION
        "Cisco UCS sw:PortBreakout:portId managed object property"
    ::= { cucsSwPortBreakoutEntry 5 }

cucsSwPortBreakoutSlotId OBJECT-TYPE
    SYNTAX       CucsSwPortBreakoutSlotId
    MAX-ACCESS   read-only
    STATUS       current
    DESCRIPTION
        "Cisco UCS sw:PortBreakout:slotId managed object property"
    ::= { cucsSwPortBreakoutEntry 6 }

cucsSwPortDiscoverTable OBJECT-TYPE
    SYNTAX           SEQUENCE OF CucsSwPortDiscoverEntry
    MAX-ACCESS       not-accessible
    STATUS           current
    DESCRIPTION
        "Cisco UCS sw:PortDiscover managed object table"
    ::= { cucsSwObjects 93 }

cucsSwPortDiscoverEntry OBJECT-TYPE
    SYNTAX           CucsSwPortDiscoverEntry
    MAX-ACCESS       not-accessible
    STATUS           current
    DESCRIPTION
        "Entry for the cucsSwPortDiscoverTable table."
    INDEX { cucsSwPortDiscoverInstanceId }
    ::= { cucsSwPortDiscoverTable 1 }

CucsSwPortDiscoverEntry ::= SEQUENCE {
    cucsSwPortDiscoverInstanceId                                     CucsManagedObjectId,
    cucsSwPortDiscoverDn                                             CucsManagedObjectDn,
    cucsSwPortDiscoverRn                                             SnmpAdminString,
    cucsSwPortDiscoverConfMode                                       CucsSwConfMode,
    cucsSwPortDiscoverFsmDescr                                       SnmpAdminString,
    cucsSwPortDiscoverFsmPrev                                        SnmpAdminString,
    cucsSwPortDiscoverFsmProgr                                       Gauge32,
    cucsSwPortDiscoverFsmRmtInvErrCode                               Gauge32,
    cucsSwPortDiscoverFsmRmtInvErrDescr                              SnmpAdminString,
    cucsSwPortDiscoverFsmRmtInvRslt                                  CucsConditionRemoteInvRslt,
    cucsSwPortDiscoverFsmStageDescr                                  SnmpAdminString,
    cucsSwPortDiscoverFsmStamp                                       DateAndTime,
    cucsSwPortDiscoverFsmStatus                                      SnmpAdminString,
    cucsSwPortDiscoverFsmTry                                         Gauge32,
    cucsSwPortDiscoverSwitchId                                       CucsNetworkSwitchId
}

cucsSwPortDiscoverInstanceId OBJECT-TYPE
    SYNTAX       CucsManagedObjectId
    MAX-ACCESS   not-accessible
    STATUS       current
    DESCRIPTION
        "Instance identifier of the managed object."
    ::= { cucsSwPortDiscoverEntry 1 }

cucsSwPortDiscoverDn OBJECT-TYPE
    SYNTAX       CucsManagedObjectDn
    MAX-ACCESS   read-only
    STATUS       current
    DESCRIPTION
        "Cisco UCS sw:PortDiscover:dn managed object property"
    ::= { cucsSwPortDiscoverEntry 2 }

cucsSwPortDiscoverRn OBJECT-TYPE
    SYNTAX       SnmpAdminString
    MAX-ACCESS   read-only
    STATUS       current
    DESCRIPTION
        "Cisco UCS sw:PortDiscover:rn managed object property"
    ::= { cucsSwPortDiscoverEntry 3 }

cucsSwPortDiscoverConfMode OBJECT-TYPE
    SYNTAX       CucsSwConfMode
    MAX-ACCESS   read-only
    STATUS       current
    DESCRIPTION
        "Cisco UCS sw:PortDiscover:confMode managed object property"
    ::= { cucsSwPortDiscoverEntry 4 }

cucsSwPortDiscoverFsmDescr OBJECT-TYPE
    SYNTAX       SnmpAdminString
    MAX-ACCESS   read-only
    STATUS       current
    DESCRIPTION
        "Cisco UCS sw:PortDiscover:fsmDescr managed object property"
    ::= { cucsSwPortDiscoverEntry 5 }

cucsSwPortDiscoverFsmPrev OBJECT-TYPE
    SYNTAX       SnmpAdminString
    MAX-ACCESS   read-only
    STATUS       current
    DESCRIPTION
        "Cisco UCS sw:PortDiscover:fsmPrev managed object property"
    ::= { cucsSwPortDiscoverEntry 6 }

cucsSwPortDiscoverFsmProgr OBJECT-TYPE
    SYNTAX       Gauge32
    MAX-ACCESS   read-only
    STATUS       current
    DESCRIPTION
        "Cisco UCS sw:PortDiscover:fsmProgr managed object property"
    ::= { cucsSwPortDiscoverEntry 7 }

cucsSwPortDiscoverFsmRmtInvErrCode OBJECT-TYPE
    SYNTAX       Gauge32
    MAX-ACCESS   read-only
    STATUS       current
    DESCRIPTION
        "Cisco UCS sw:PortDiscover:fsmRmtInvErrCode managed
        object property"
    ::= { cucsSwPortDiscoverEntry 8 }

cucsSwPortDiscoverFsmRmtInvErrDescr OBJECT-TYPE
    SYNTAX       SnmpAdminString
    MAX-ACCESS   read-only
    STATUS       current
    DESCRIPTION
        "Cisco UCS sw:PortDiscover:fsmRmtInvErrDescr managed
        object property"
    ::= { cucsSwPortDiscoverEntry 9 }

cucsSwPortDiscoverFsmRmtInvRslt OBJECT-TYPE
    SYNTAX       CucsConditionRemoteInvRslt
    MAX-ACCESS   read-only
    STATUS       current
    DESCRIPTION
        "Cisco UCS sw:PortDiscover:fsmRmtInvRslt managed object property"
    ::= { cucsSwPortDiscoverEntry 10 }

cucsSwPortDiscoverFsmStageDescr OBJECT-TYPE
    SYNTAX       SnmpAdminString
    MAX-ACCESS   read-only
    STATUS       current
    DESCRIPTION
        "Cisco UCS sw:PortDiscover:fsmStageDescr managed object property"
    ::= { cucsSwPortDiscoverEntry 11 }

cucsSwPortDiscoverFsmStamp OBJECT-TYPE
    SYNTAX       DateAndTime
    MAX-ACCESS   read-only
    STATUS       current
    DESCRIPTION
        "Cisco UCS sw:PortDiscover:fsmStamp managed object property"
    ::= { cucsSwPortDiscoverEntry 12 }

cucsSwPortDiscoverFsmStatus OBJECT-TYPE
    SYNTAX       SnmpAdminString
    MAX-ACCESS   read-only
    STATUS       current
    DESCRIPTION
        "Cisco UCS sw:PortDiscover:fsmStatus managed object property"
    ::= { cucsSwPortDiscoverEntry 13 }

cucsSwPortDiscoverFsmTry OBJECT-TYPE
    SYNTAX       Gauge32
    MAX-ACCESS   read-only
    STATUS       current
    DESCRIPTION
        "Cisco UCS sw:PortDiscover:fsmTry managed object property"
    ::= { cucsSwPortDiscoverEntry 14 }

cucsSwPortDiscoverSwitchId OBJECT-TYPE
    SYNTAX       CucsNetworkSwitchId
    MAX-ACCESS   read-only
    STATUS       current
    DESCRIPTION
        "Cisco UCS sw:PortDiscover:switchId managed object property"
    ::= { cucsSwPortDiscoverEntry 15 }

cucsSwPortDiscoverFsmTable OBJECT-TYPE
    SYNTAX           SEQUENCE OF CucsSwPortDiscoverFsmEntry
    MAX-ACCESS       not-accessible
    STATUS           current
    DESCRIPTION
        "Cisco UCS sw:PortDiscoverFsm managed object table"
    ::= { cucsSwObjects 94 }

cucsSwPortDiscoverFsmEntry OBJECT-TYPE
    SYNTAX           CucsSwPortDiscoverFsmEntry
    MAX-ACCESS       not-accessible
    STATUS           current
    DESCRIPTION
        "Entry for the cucsSwPortDiscoverFsmTable table."
    INDEX { cucsSwPortDiscoverFsmInstanceId }
    ::= { cucsSwPortDiscoverFsmTable 1 }

CucsSwPortDiscoverFsmEntry ::= SEQUENCE {
    cucsSwPortDiscoverFsmInstanceId                                  CucsManagedObjectId,
    cucsSwPortDiscoverFsmDn                                          CucsManagedObjectDn,
    cucsSwPortDiscoverFsmRn                                          SnmpAdminString,
    cucsSwPortDiscoverFsmCompletionTime                              DateAndTime,
    cucsSwPortDiscoverFsmCurrentFsm                                  CucsSwPortDiscoverFsmCurrentFsm,
    cucsSwPortDiscoverFsmDescrData                                   SnmpAdminString,
    cucsSwPortDiscoverFsmFsmStatus                                   CucsFsmFsmStageStatus,
    cucsSwPortDiscoverFsmProgress                                    Gauge32,
    cucsSwPortDiscoverFsmRmtErrCode                                  Gauge32,
    cucsSwPortDiscoverFsmRmtErrDescr                                 SnmpAdminString,
    cucsSwPortDiscoverFsmRmtRslt                                     CucsConditionRemoteInvRslt
}

cucsSwPortDiscoverFsmInstanceId OBJECT-TYPE
    SYNTAX       CucsManagedObjectId
    MAX-ACCESS   not-accessible
    STATUS       current
    DESCRIPTION
        "Instance identifier of the managed object."
    ::= { cucsSwPortDiscoverFsmEntry 1 }

cucsSwPortDiscoverFsmDn OBJECT-TYPE
    SYNTAX       CucsManagedObjectDn
    MAX-ACCESS   read-only
    STATUS       current
    DESCRIPTION
        "Cisco UCS sw:PortDiscoverFsm:dn managed object property"
    ::= { cucsSwPortDiscoverFsmEntry 2 }

cucsSwPortDiscoverFsmRn OBJECT-TYPE
    SYNTAX       SnmpAdminString
    MAX-ACCESS   read-only
    STATUS       current
    DESCRIPTION
        "Cisco UCS sw:PortDiscoverFsm:rn managed object property"
    ::= { cucsSwPortDiscoverFsmEntry 3 }

cucsSwPortDiscoverFsmCompletionTime OBJECT-TYPE
    SYNTAX       DateAndTime
    MAX-ACCESS   read-only
    STATUS       current
    DESCRIPTION
        "Cisco UCS sw:PortDiscoverFsm:completionTime managed
        object property"
    ::= { cucsSwPortDiscoverFsmEntry 4 }

cucsSwPortDiscoverFsmCurrentFsm OBJECT-TYPE
    SYNTAX       CucsSwPortDiscoverFsmCurrentFsm
    MAX-ACCESS   read-only
    STATUS       current
    DESCRIPTION
        "Cisco UCS sw:PortDiscoverFsm:currentFsm managed object property"
    ::= { cucsSwPortDiscoverFsmEntry 5 }

cucsSwPortDiscoverFsmDescrData OBJECT-TYPE
    SYNTAX       SnmpAdminString
    MAX-ACCESS   read-only
    STATUS       current
    DESCRIPTION
        "Cisco UCS sw:PortDiscoverFsm:descr managed object property"
    ::= { cucsSwPortDiscoverFsmEntry 6 }

cucsSwPortDiscoverFsmFsmStatus OBJECT-TYPE
    SYNTAX       CucsFsmFsmStageStatus
    MAX-ACCESS   read-only
    STATUS       current
    DESCRIPTION
        "Cisco UCS sw:PortDiscoverFsm:fsmStatus managed object property"
    ::= { cucsSwPortDiscoverFsmEntry 7 }

cucsSwPortDiscoverFsmProgress OBJECT-TYPE
    SYNTAX       Gauge32
    MAX-ACCESS   read-only
    STATUS       current
    DESCRIPTION
        "Cisco UCS sw:PortDiscoverFsm:progress managed object property"
    ::= { cucsSwPortDiscoverFsmEntry 8 }

cucsSwPortDiscoverFsmRmtErrCode OBJECT-TYPE
    SYNTAX       Gauge32
    MAX-ACCESS   read-only
    STATUS       current
    DESCRIPTION
        "Cisco UCS sw:PortDiscoverFsm:rmtErrCode managed object property"
    ::= { cucsSwPortDiscoverFsmEntry 9 }

cucsSwPortDiscoverFsmRmtErrDescr OBJECT-TYPE
    SYNTAX       SnmpAdminString
    MAX-ACCESS   read-only
    STATUS       current
    DESCRIPTION
        "Cisco UCS sw:PortDiscoverFsm:rmtErrDescr managed object property"
    ::= { cucsSwPortDiscoverFsmEntry 10 }

cucsSwPortDiscoverFsmRmtRslt OBJECT-TYPE
    SYNTAX       CucsConditionRemoteInvRslt
    MAX-ACCESS   read-only
    STATUS       current
    DESCRIPTION
        "Cisco UCS sw:PortDiscoverFsm:rmtRslt managed object property"
    ::= { cucsSwPortDiscoverFsmEntry 11 }

cucsSwPortDiscoverFsmStageTable OBJECT-TYPE
    SYNTAX           SEQUENCE OF CucsSwPortDiscoverFsmStageEntry
    MAX-ACCESS       not-accessible
    STATUS           current
    DESCRIPTION
        "Cisco UCS sw:PortDiscoverFsmStage managed object table"
    ::= { cucsSwObjects 95 }

cucsSwPortDiscoverFsmStageEntry OBJECT-TYPE
    SYNTAX           CucsSwPortDiscoverFsmStageEntry
    MAX-ACCESS       not-accessible
    STATUS           current
    DESCRIPTION
        "Entry for the cucsSwPortDiscoverFsmStageTable table."
    INDEX { cucsSwPortDiscoverFsmStageInstanceId }
    ::= { cucsSwPortDiscoverFsmStageTable 1 }

CucsSwPortDiscoverFsmStageEntry ::= SEQUENCE {
    cucsSwPortDiscoverFsmStageInstanceId                             CucsManagedObjectId,
    cucsSwPortDiscoverFsmStageDn                                     CucsManagedObjectDn,
    cucsSwPortDiscoverFsmStageRn                                     SnmpAdminString,
    cucsSwPortDiscoverFsmStageDescrData                              SnmpAdminString,
    cucsSwPortDiscoverFsmStageLastUpdateTime                         DateAndTime,
    cucsSwPortDiscoverFsmStageName                                   CucsSwPortDiscoverFsmStageName,
    cucsSwPortDiscoverFsmStageOrder                                  Gauge32,
    cucsSwPortDiscoverFsmStageRetry                                  Gauge32,
    cucsSwPortDiscoverFsmStageStageStatus                            CucsFsmFsmStageStatus
}

cucsSwPortDiscoverFsmStageInstanceId OBJECT-TYPE
    SYNTAX       CucsManagedObjectId
    MAX-ACCESS   not-accessible
    STATUS       current
    DESCRIPTION
        "Instance identifier of the managed object."
    ::= { cucsSwPortDiscoverFsmStageEntry 1 }

cucsSwPortDiscoverFsmStageDn OBJECT-TYPE
    SYNTAX       CucsManagedObjectDn
    MAX-ACCESS   read-only
    STATUS       current
    DESCRIPTION
        "Cisco UCS sw:PortDiscoverFsmStage:dn managed object property"
    ::= { cucsSwPortDiscoverFsmStageEntry 2 }

cucsSwPortDiscoverFsmStageRn OBJECT-TYPE
    SYNTAX       SnmpAdminString
    MAX-ACCESS   read-only
    STATUS       current
    DESCRIPTION
        "Cisco UCS sw:PortDiscoverFsmStage:rn managed object property"
    ::= { cucsSwPortDiscoverFsmStageEntry 3 }

cucsSwPortDiscoverFsmStageDescrData OBJECT-TYPE
    SYNTAX       SnmpAdminString
    MAX-ACCESS   read-only
    STATUS       current
    DESCRIPTION
        "Cisco UCS sw:PortDiscoverFsmStage:descr managed object property"
    ::= { cucsSwPortDiscoverFsmStageEntry 4 }

cucsSwPortDiscoverFsmStageLastUpdateTime OBJECT-TYPE
    SYNTAX       DateAndTime
    MAX-ACCESS   read-only
    STATUS       current
    DESCRIPTION
        "Cisco UCS sw:PortDiscoverFsmStage:lastUpdateTime
        managed object property"
    ::= { cucsSwPortDiscoverFsmStageEntry 5 }

cucsSwPortDiscoverFsmStageName OBJECT-TYPE
    SYNTAX       CucsSwPortDiscoverFsmStageName
    MAX-ACCESS   read-only
    STATUS       current
    DESCRIPTION
        "Cisco UCS sw:PortDiscoverFsmStage:name managed object property"
    ::= { cucsSwPortDiscoverFsmStageEntry 6 }

cucsSwPortDiscoverFsmStageOrder OBJECT-TYPE
    SYNTAX       Gauge32
    MAX-ACCESS   read-only
    STATUS       current
    DESCRIPTION
        "Cisco UCS sw:PortDiscoverFsmStage:order managed object property"
    ::= { cucsSwPortDiscoverFsmStageEntry 7 }

cucsSwPortDiscoverFsmStageRetry OBJECT-TYPE
    SYNTAX       Gauge32
    MAX-ACCESS   read-only
    STATUS       current
    DESCRIPTION
        "Cisco UCS sw:PortDiscoverFsmStage:retry managed object property"
    ::= { cucsSwPortDiscoverFsmStageEntry 8 }

cucsSwPortDiscoverFsmStageStageStatus OBJECT-TYPE
    SYNTAX       CucsFsmFsmStageStatus
    MAX-ACCESS   read-only
    STATUS       current
    DESCRIPTION
        "Cisco UCS sw:PortDiscoverFsmStage:stageStatus
        managed object property"
    ::= { cucsSwPortDiscoverFsmStageEntry 9 }

cucsSwPortDiscoverFsmTaskTable OBJECT-TYPE
    SYNTAX           SEQUENCE OF CucsSwPortDiscoverFsmTaskEntry
    MAX-ACCESS       not-accessible
    STATUS           current
    DESCRIPTION
        "Cisco UCS sw:PortDiscoverFsmTask managed object table"
    ::= { cucsSwObjects 96 }

cucsSwPortDiscoverFsmTaskEntry OBJECT-TYPE
    SYNTAX           CucsSwPortDiscoverFsmTaskEntry
    MAX-ACCESS       not-accessible
    STATUS           current
    DESCRIPTION
        "Entry for the cucsSwPortDiscoverFsmTaskTable table."
    INDEX { cucsSwPortDiscoverFsmTaskInstanceId }
    ::= { cucsSwPortDiscoverFsmTaskTable 1 }

CucsSwPortDiscoverFsmTaskEntry ::= SEQUENCE {
    cucsSwPortDiscoverFsmTaskInstanceId                              CucsManagedObjectId,
    cucsSwPortDiscoverFsmTaskDn                                      CucsManagedObjectDn,
    cucsSwPortDiscoverFsmTaskRn                                      SnmpAdminString,
    cucsSwPortDiscoverFsmTaskCompletion                              CucsFsmCompletion,
    cucsSwPortDiscoverFsmTaskFlags                                   CucsFsmFlags,
    cucsSwPortDiscoverFsmTaskItem                                    CucsSwPortDiscoverFsmTaskItem,
    cucsSwPortDiscoverFsmTaskSeqId                                   Gauge32
}

cucsSwPortDiscoverFsmTaskInstanceId OBJECT-TYPE
    SYNTAX       CucsManagedObjectId
    MAX-ACCESS   not-accessible
    STATUS       current
    DESCRIPTION
        "Instance identifier of the managed object."
    ::= { cucsSwPortDiscoverFsmTaskEntry 1 }

cucsSwPortDiscoverFsmTaskDn OBJECT-TYPE
    SYNTAX       CucsManagedObjectDn
    MAX-ACCESS   read-only
    STATUS       current
    DESCRIPTION
        "Cisco UCS sw:PortDiscoverFsmTask:dn managed object property"
    ::= { cucsSwPortDiscoverFsmTaskEntry 2 }

cucsSwPortDiscoverFsmTaskRn OBJECT-TYPE
    SYNTAX       SnmpAdminString
    MAX-ACCESS   read-only
    STATUS       current
    DESCRIPTION
        "Cisco UCS sw:PortDiscoverFsmTask:rn managed object property"
    ::= { cucsSwPortDiscoverFsmTaskEntry 3 }

cucsSwPortDiscoverFsmTaskCompletion OBJECT-TYPE
    SYNTAX       CucsFsmCompletion
    MAX-ACCESS   read-only
    STATUS       current
    DESCRIPTION
        "Cisco UCS sw:PortDiscoverFsmTask:completion managed
        object property"
    ::= { cucsSwPortDiscoverFsmTaskEntry 4 }

cucsSwPortDiscoverFsmTaskFlags OBJECT-TYPE
    SYNTAX       CucsFsmFlags
    MAX-ACCESS   read-only
    STATUS       current
    DESCRIPTION
        "Cisco UCS sw:PortDiscoverFsmTask:flags managed object property"
    ::= { cucsSwPortDiscoverFsmTaskEntry 5 }

cucsSwPortDiscoverFsmTaskItem OBJECT-TYPE
    SYNTAX       CucsSwPortDiscoverFsmTaskItem
    MAX-ACCESS   read-only
    STATUS       current
    DESCRIPTION
        "Cisco UCS sw:PortDiscoverFsmTask:item managed object property"
    ::= { cucsSwPortDiscoverFsmTaskEntry 6 }

cucsSwPortDiscoverFsmTaskSeqId OBJECT-TYPE
    SYNTAX       Gauge32
    MAX-ACCESS   read-only
    STATUS       current
    DESCRIPTION
        "Cisco UCS sw:PortDiscoverFsmTask:seqId managed object property"
    ::= { cucsSwPortDiscoverFsmTaskEntry 7 }

cucsSwSubGroupTable OBJECT-TYPE
    SYNTAX           SEQUENCE OF CucsSwSubGroupEntry
    MAX-ACCESS       not-accessible
    STATUS           current
    DESCRIPTION
        "Cisco UCS sw:SubGroup managed object table"
    ::= { cucsSwObjects 82 }

cucsSwSubGroupEntry OBJECT-TYPE
    SYNTAX           CucsSwSubGroupEntry
    MAX-ACCESS       not-accessible
    STATUS           current
    DESCRIPTION
        "Entry for the cucsSwSubGroupTable table."
    INDEX { cucsSwSubGroupInstanceId }
    ::= { cucsSwSubGroupTable 1 }

CucsSwSubGroupEntry ::= SEQUENCE {
    cucsSwSubGroupInstanceId                                         CucsManagedObjectId,
    cucsSwSubGroupDn                                                 CucsManagedObjectDn,
    cucsSwSubGroupRn                                                 SnmpAdminString,
    cucsSwSubGroupAggrPortId                                         CucsSwSubGroupAggrPortId,
    cucsSwSubGroupLicGP                                              Unsigned64,
    cucsSwSubGroupLicState                                           CucsLicenseState,
    cucsSwSubGroupLocale                                             CucsNetworkLocale,
    cucsSwSubGroupName                                               SnmpAdminString,
    cucsSwSubGroupSlotId                                             CucsSwSubGroupSlotId,
    cucsSwSubGroupSwitchId                                           CucsNetworkSwitchId,
    cucsSwSubGroupTransport                                          CucsNetworkTransport,
    cucsSwSubGroupType                                               CucsNetworkConnectionType
}

cucsSwSubGroupInstanceId OBJECT-TYPE
    SYNTAX       CucsManagedObjectId
    MAX-ACCESS   not-accessible
    STATUS       current
    DESCRIPTION
        "Instance identifier of the managed object."
    ::= { cucsSwSubGroupEntry 1 }

cucsSwSubGroupDn OBJECT-TYPE
    SYNTAX       CucsManagedObjectDn
    MAX-ACCESS   read-only
    STATUS       current
    DESCRIPTION
        "Cisco UCS sw:SubGroup:dn managed object property"
    ::= { cucsSwSubGroupEntry 2 }

cucsSwSubGroupRn OBJECT-TYPE
    SYNTAX       SnmpAdminString
    MAX-ACCESS   read-only
    STATUS       current
    DESCRIPTION
        "Cisco UCS sw:SubGroup:rn managed object property"
    ::= { cucsSwSubGroupEntry 3 }

cucsSwSubGroupAggrPortId OBJECT-TYPE
    SYNTAX       CucsSwSubGroupAggrPortId
    MAX-ACCESS   read-only
    STATUS       current
    DESCRIPTION
        "Cisco UCS sw:SubGroup:aggrPortId managed object property"
    ::= { cucsSwSubGroupEntry 4 }

cucsSwSubGroupLicGP OBJECT-TYPE
    SYNTAX       Unsigned64
    MAX-ACCESS   read-only
    STATUS       current
    DESCRIPTION
        "Cisco UCS sw:SubGroup:licGP managed object property"
    ::= { cucsSwSubGroupEntry 5 }

cucsSwSubGroupLicState OBJECT-TYPE
    SYNTAX       CucsLicenseState
    MAX-ACCESS   read-only
    STATUS       current
    DESCRIPTION
        "Cisco UCS sw:SubGroup:licState managed object property"
    ::= { cucsSwSubGroupEntry 6 }

cucsSwSubGroupLocale OBJECT-TYPE
    SYNTAX       CucsNetworkLocale
    MAX-ACCESS   read-only
    STATUS       current
    DESCRIPTION
        "Cisco UCS sw:SubGroup:locale managed object property"
    ::= { cucsSwSubGroupEntry 7 }

cucsSwSubGroupName OBJECT-TYPE
    SYNTAX       SnmpAdminString
    MAX-ACCESS   read-only
    STATUS       current
    DESCRIPTION
        "Cisco UCS sw:SubGroup:name managed object property"
    ::= { cucsSwSubGroupEntry 8 }

cucsSwSubGroupSlotId OBJECT-TYPE
    SYNTAX       CucsSwSubGroupSlotId
    MAX-ACCESS   read-only
    STATUS       current
    DESCRIPTION
        "Cisco UCS sw:SubGroup:slotId managed object property"
    ::= { cucsSwSubGroupEntry 9 }

cucsSwSubGroupSwitchId OBJECT-TYPE
    SYNTAX       CucsNetworkSwitchId
    MAX-ACCESS   read-only
    STATUS       current
    DESCRIPTION
        "Cisco UCS sw:SubGroup:switchId managed object property"
    ::= { cucsSwSubGroupEntry 10 }

cucsSwSubGroupTransport OBJECT-TYPE
    SYNTAX       CucsNetworkTransport
    MAX-ACCESS   read-only
    STATUS       current
    DESCRIPTION
        "Cisco UCS sw:SubGroup:transport managed object property"
    ::= { cucsSwSubGroupEntry 11 }

cucsSwSubGroupType OBJECT-TYPE
    SYNTAX       CucsNetworkConnectionType
    MAX-ACCESS   read-only
    STATUS       current
    DESCRIPTION
        "Cisco UCS sw:SubGroup:type managed object property"
    ::= { cucsSwSubGroupEntry 12 }

cucsSwSystemStatsTable OBJECT-TYPE
    SYNTAX           SEQUENCE OF CucsSwSystemStatsEntry
    MAX-ACCESS       not-accessible
    STATUS           current
    DESCRIPTION
        "Cisco UCS sw:SystemStats managed object table"
    ::= { cucsSwObjects 28 }

cucsSwSystemStatsEntry OBJECT-TYPE
    SYNTAX           CucsSwSystemStatsEntry
    MAX-ACCESS       not-accessible
    STATUS           current
    DESCRIPTION
        "Entry for the cucsSwSystemStatsTable table."
    INDEX { cucsSwSystemStatsInstanceId }
    ::= { cucsSwSystemStatsTable 1 }

CucsSwSystemStatsEntry ::= SEQUENCE {
    cucsSwSystemStatsInstanceId                                      CucsManagedObjectId,
    cucsSwSystemStatsDn                                              CucsManagedObjectDn,
    cucsSwSystemStatsRn                                              SnmpAdminString,
    cucsSwSystemStatsIntervals                                       Gauge32,
    cucsSwSystemStatsLoad                                            INTEGER,
    cucsSwSystemStatsLoadAvg                                         INTEGER,
    cucsSwSystemStatsLoadMax                                         INTEGER,
    cucsSwSystemStatsLoadMin                                         INTEGER,
    cucsSwSystemStatsMemAvailable                                    Gauge32,
    cucsSwSystemStatsMemAvailableAvg                                 Gauge32,
    cucsSwSystemStatsMemAvailableMax                                 Gauge32,
    cucsSwSystemStatsMemAvailableMin                                 Gauge32,
    cucsSwSystemStatsMemCached                                       Gauge32,
    cucsSwSystemStatsMemCachedAvg                                    Gauge32,
    cucsSwSystemStatsMemCachedMax                                    Gauge32,
    cucsSwSystemStatsMemCachedMin                                    Gauge32,
    cucsSwSystemStatsSuspect                                         TruthValue,
    cucsSwSystemStatsThresholded                                     CucsSwSystemStatsThresholded,
    cucsSwSystemStatsTimeCollected                                   DateAndTime,
    cucsSwSystemStatsUpdate                                          Gauge32,
    cucsSwSystemStatsCorrectableParityError                          Gauge32,
    cucsSwSystemStatsCorrectableParityErrorAvg                       Gauge32,
    cucsSwSystemStatsCorrectableParityErrorMax                       Gauge32,
    cucsSwSystemStatsCorrectableParityErrorMin                       Gauge32,
    cucsSwSystemStatsKernelMemFree                                   Gauge32,
    cucsSwSystemStatsKernelMemFreeAvg                                Gauge32,
    cucsSwSystemStatsKernelMemFreeMax                                Gauge32,
    cucsSwSystemStatsKernelMemFreeMin                                Gauge32,
    cucsSwSystemStatsKernelMemTotal                                  Gauge32,
    cucsSwSystemStatsKernelMemTotalAvg                               Gauge32,
    cucsSwSystemStatsKernelMemTotalMax                               Gauge32,
    cucsSwSystemStatsKernelMemTotalMin                               Gauge32
}

cucsSwSystemStatsInstanceId OBJECT-TYPE
    SYNTAX       CucsManagedObjectId
    MAX-ACCESS   not-accessible
    STATUS       current
    DESCRIPTION
        "Instance identifier of the managed object."
    ::= { cucsSwSystemStatsEntry 1 }

cucsSwSystemStatsDn OBJECT-TYPE
    SYNTAX       CucsManagedObjectDn
    MAX-ACCESS   read-only
    STATUS       current
    DESCRIPTION
        "Cisco UCS sw:SystemStats:dn managed object property"
    ::= { cucsSwSystemStatsEntry 2 }

cucsSwSystemStatsRn OBJECT-TYPE
    SYNTAX       SnmpAdminString
    MAX-ACCESS   read-only
    STATUS       current
    DESCRIPTION
        "Cisco UCS sw:SystemStats:rn managed object property"
    ::= { cucsSwSystemStatsEntry 3 }

cucsSwSystemStatsIntervals OBJECT-TYPE
    SYNTAX       Gauge32
    MAX-ACCESS   read-only
    STATUS       current
    DESCRIPTION
        "Cisco UCS sw:SystemStats:intervals managed object property"
    ::= { cucsSwSystemStatsEntry 4 }

cucsSwSystemStatsLoad OBJECT-TYPE
    SYNTAX       INTEGER
    MAX-ACCESS   read-only
    STATUS       current
    DESCRIPTION
        "Cisco UCS sw:SystemStats:load managed object property"
    ::= { cucsSwSystemStatsEntry 5 }

cucsSwSystemStatsLoadAvg OBJECT-TYPE
    SYNTAX       INTEGER
    MAX-ACCESS   read-only
    STATUS       current
    DESCRIPTION
        "Cisco UCS sw:SystemStats:loadAvg managed object property"
    ::= { cucsSwSystemStatsEntry 6 }

cucsSwSystemStatsLoadMax OBJECT-TYPE
    SYNTAX       INTEGER
    MAX-ACCESS   read-only
    STATUS       current
    DESCRIPTION
        "Cisco UCS sw:SystemStats:loadMax managed object property"
    ::= { cucsSwSystemStatsEntry 7 }

cucsSwSystemStatsLoadMin OBJECT-TYPE
    SYNTAX       INTEGER
    MAX-ACCESS   read-only
    STATUS       current
    DESCRIPTION
        "Cisco UCS sw:SystemStats:loadMin managed object property"
    ::= { cucsSwSystemStatsEntry 8 }

cucsSwSystemStatsMemAvailable OBJECT-TYPE
    SYNTAX       Gauge32
    MAX-ACCESS   read-only
    STATUS       current
    DESCRIPTION
        "Cisco UCS sw:SystemStats:memAvailable managed object property"
    ::= { cucsSwSystemStatsEntry 9 }

cucsSwSystemStatsMemAvailableAvg OBJECT-TYPE
    SYNTAX       Gauge32
    MAX-ACCESS   read-only
    STATUS       current
    DESCRIPTION
        "Cisco UCS sw:SystemStats:memAvailableAvg managed object property"
    ::= { cucsSwSystemStatsEntry 10 }

cucsSwSystemStatsMemAvailableMax OBJECT-TYPE
    SYNTAX       Gauge32
    MAX-ACCESS   read-only
    STATUS       current
    DESCRIPTION
        "Cisco UCS sw:SystemStats:memAvailableMax managed object property"
    ::= { cucsSwSystemStatsEntry 11 }

cucsSwSystemStatsMemAvailableMin OBJECT-TYPE
    SYNTAX       Gauge32
    MAX-ACCESS   read-only
    STATUS       current
    DESCRIPTION
        "Cisco UCS sw:SystemStats:memAvailableMin managed object property"
    ::= { cucsSwSystemStatsEntry 12 }

cucsSwSystemStatsMemCached OBJECT-TYPE
    SYNTAX       Gauge32
    MAX-ACCESS   read-only
    STATUS       current
    DESCRIPTION
        "Cisco UCS sw:SystemStats:memCached managed object property"
    ::= { cucsSwSystemStatsEntry 13 }

cucsSwSystemStatsMemCachedAvg OBJECT-TYPE
    SYNTAX       Gauge32
    MAX-ACCESS   read-only
    STATUS       current
    DESCRIPTION
        "Cisco UCS sw:SystemStats:memCachedAvg managed object property"
    ::= { cucsSwSystemStatsEntry 14 }

cucsSwSystemStatsMemCachedMax OBJECT-TYPE
    SYNTAX       Gauge32
    MAX-ACCESS   read-only
    STATUS       current
    DESCRIPTION
        "Cisco UCS sw:SystemStats:memCachedMax managed object property"
    ::= { cucsSwSystemStatsEntry 15 }

cucsSwSystemStatsMemCachedMin OBJECT-TYPE
    SYNTAX       Gauge32
    MAX-ACCESS   read-only
    STATUS       current
    DESCRIPTION
        "Cisco UCS sw:SystemStats:memCachedMin managed object property"
    ::= { cucsSwSystemStatsEntry 16 }

cucsSwSystemStatsSuspect OBJECT-TYPE
    SYNTAX       TruthValue
    MAX-ACCESS   read-only
    STATUS       current
    DESCRIPTION
        "Cisco UCS sw:SystemStats:suspect managed object property"
    ::= { cucsSwSystemStatsEntry 17 }

cucsSwSystemStatsThresholded OBJECT-TYPE
    SYNTAX       CucsSwSystemStatsThresholded
    MAX-ACCESS   read-only
    STATUS       current
    DESCRIPTION
        "Cisco UCS sw:SystemStats:thresholded managed object property"
    ::= { cucsSwSystemStatsEntry 18 }

cucsSwSystemStatsTimeCollected OBJECT-TYPE
    SYNTAX       DateAndTime
    MAX-ACCESS   read-only
    STATUS       current
    DESCRIPTION
        "Cisco UCS sw:SystemStats:timeCollected managed object property"
    ::= { cucsSwSystemStatsEntry 19 }

cucsSwSystemStatsUpdate OBJECT-TYPE
    SYNTAX       Gauge32
    MAX-ACCESS   read-only
    STATUS       current
    DESCRIPTION
        "Cisco UCS sw:SystemStats:update managed object property"
    ::= { cucsSwSystemStatsEntry 20 }

cucsSwSystemStatsCorrectableParityError OBJECT-TYPE
    SYNTAX       Gauge32
    MAX-ACCESS   read-only
    STATUS       current
    DESCRIPTION
        "Cisco UCS sw:SystemStats:CorrectableParityError
        managed object property"
    ::= { cucsSwSystemStatsEntry 23 }

cucsSwSystemStatsCorrectableParityErrorAvg OBJECT-TYPE
    SYNTAX       Gauge32
    MAX-ACCESS   read-only
    STATUS       current
    DESCRIPTION
        "Cisco UCS sw:SystemStats:CorrectableParityErrorAvg
        managed object property"
    ::= { cucsSwSystemStatsEntry 24 }

cucsSwSystemStatsCorrectableParityErrorMax OBJECT-TYPE
    SYNTAX       Gauge32
    MAX-ACCESS   read-only
    STATUS       current
    DESCRIPTION
        "Cisco UCS sw:SystemStats:CorrectableParityErrorMax
        managed object property"
    ::= { cucsSwSystemStatsEntry 25 }

cucsSwSystemStatsCorrectableParityErrorMin OBJECT-TYPE
    SYNTAX       Gauge32
    MAX-ACCESS   read-only
    STATUS       current
    DESCRIPTION
        "Cisco UCS sw:SystemStats:CorrectableParityErrorMin
        managed object property"
    ::= { cucsSwSystemStatsEntry 26 }

cucsSwSystemStatsKernelMemFree OBJECT-TYPE
    SYNTAX       Gauge32
    MAX-ACCESS   read-only
    STATUS       current
    DESCRIPTION
        "Cisco UCS sw:SystemStats:kernelMemFree managed object property"
    ::= { cucsSwSystemStatsEntry 27 }

cucsSwSystemStatsKernelMemFreeAvg OBJECT-TYPE
    SYNTAX       Gauge32
    MAX-ACCESS   read-only
    STATUS       current
    DESCRIPTION
        "Cisco UCS sw:SystemStats:kernelMemFreeAvg managed
        object property"
    ::= { cucsSwSystemStatsEntry 28 }

cucsSwSystemStatsKernelMemFreeMax OBJECT-TYPE
    SYNTAX       Gauge32
    MAX-ACCESS   read-only
    STATUS       current
    DESCRIPTION
        "Cisco UCS sw:SystemStats:kernelMemFreeMax managed
        object property"
    ::= { cucsSwSystemStatsEntry 29 }

cucsSwSystemStatsKernelMemFreeMin OBJECT-TYPE
    SYNTAX       Gauge32
    MAX-ACCESS   read-only
    STATUS       current
    DESCRIPTION
        "Cisco UCS sw:SystemStats:kernelMemFreeMin managed
        object property"
    ::= { cucsSwSystemStatsEntry 30 }

cucsSwSystemStatsKernelMemTotal OBJECT-TYPE
    SYNTAX       Gauge32
    MAX-ACCESS   read-only
    STATUS       current
    DESCRIPTION
        "Cisco UCS sw:SystemStats:kernelMemTotal managed object property"
    ::= { cucsSwSystemStatsEntry 31 }

cucsSwSystemStatsKernelMemTotalAvg OBJECT-TYPE
    SYNTAX       Gauge32
    MAX-ACCESS   read-only
    STATUS       current
    DESCRIPTION
        "Cisco UCS sw:SystemStats:kernelMemTotalAvg managed
        object property"
    ::= { cucsSwSystemStatsEntry 32 }

cucsSwSystemStatsKernelMemTotalMax OBJECT-TYPE
    SYNTAX       Gauge32
    MAX-ACCESS   read-only
    STATUS       current
    DESCRIPTION
        "Cisco UCS sw:SystemStats:kernelMemTotalMax managed
        object property"
    ::= { cucsSwSystemStatsEntry 33 }

cucsSwSystemStatsKernelMemTotalMin OBJECT-TYPE
    SYNTAX       Gauge32
    MAX-ACCESS   read-only
    STATUS       current
    DESCRIPTION
        "Cisco UCS sw:SystemStats:kernelMemTotalMin managed
        object property"
    ::= { cucsSwSystemStatsEntry 34 }

cucsSwSystemStatsHistTable OBJECT-TYPE
    SYNTAX           SEQUENCE OF CucsSwSystemStatsHistEntry
    MAX-ACCESS       not-accessible
    STATUS           current
    DESCRIPTION
        "Cisco UCS sw:SystemStatsHist managed object table"
    ::= { cucsSwObjects 29 }

cucsSwSystemStatsHistEntry OBJECT-TYPE
    SYNTAX           CucsSwSystemStatsHistEntry
    MAX-ACCESS       not-accessible
    STATUS           current
    DESCRIPTION
        "Entry for the cucsSwSystemStatsHistTable table."
    INDEX { cucsSwSystemStatsHistInstanceId }
    ::= { cucsSwSystemStatsHistTable 1 }

CucsSwSystemStatsHistEntry ::= SEQUENCE {
    cucsSwSystemStatsHistInstanceId                                  CucsManagedObjectId,
    cucsSwSystemStatsHistDn                                          CucsManagedObjectDn,
    cucsSwSystemStatsHistRn                                          SnmpAdminString,
    cucsSwSystemStatsHistId                                          Unsigned64,
    cucsSwSystemStatsHistLoad                                        INTEGER,
    cucsSwSystemStatsHistLoadAvg                                     INTEGER,
    cucsSwSystemStatsHistLoadMax                                     INTEGER,
    cucsSwSystemStatsHistLoadMin                                     INTEGER,
    cucsSwSystemStatsHistMemAvailable                                Gauge32,
    cucsSwSystemStatsHistMemAvailableAvg                             Gauge32,
    cucsSwSystemStatsHistMemAvailableMax                             Gauge32,
    cucsSwSystemStatsHistMemAvailableMin                             Gauge32,
    cucsSwSystemStatsHistMemCached                                   Gauge32,
    cucsSwSystemStatsHistMemCachedAvg                                Gauge32,
    cucsSwSystemStatsHistMemCachedMax                                Gauge32,
    cucsSwSystemStatsHistMemCachedMin                                Gauge32,
    cucsSwSystemStatsHistMostRecent                                  TruthValue,
    cucsSwSystemStatsHistSuspect                                     TruthValue,
    cucsSwSystemStatsHistThresholded                                 CucsSwSystemStatsHistThresholded,
    cucsSwSystemStatsHistTimeCollected                               DateAndTime,
    cucsSwSystemStatsHistCorrectableParityError                      Gauge32,
    cucsSwSystemStatsHistCorrectableParityErrorAvg                   Gauge32,
    cucsSwSystemStatsHistCorrectableParityErrorMax                   Gauge32,
    cucsSwSystemStatsHistCorrectableParityErrorMin                   Gauge32,
    cucsSwSystemStatsHistKernelMemFree                               Gauge32,
    cucsSwSystemStatsHistKernelMemFreeAvg                            Gauge32,
    cucsSwSystemStatsHistKernelMemFreeMax                            Gauge32,
    cucsSwSystemStatsHistKernelMemFreeMin                            Gauge32,
    cucsSwSystemStatsHistKernelMemTotal                              Gauge32,
    cucsSwSystemStatsHistKernelMemTotalAvg                           Gauge32,
    cucsSwSystemStatsHistKernelMemTotalMax                           Gauge32,
    cucsSwSystemStatsHistKernelMemTotalMin                           Gauge32
}

cucsSwSystemStatsHistInstanceId OBJECT-TYPE
    SYNTAX       CucsManagedObjectId
    MAX-ACCESS   not-accessible
    STATUS       current
    DESCRIPTION
        "Instance identifier of the managed object."
    ::= { cucsSwSystemStatsHistEntry 1 }

cucsSwSystemStatsHistDn OBJECT-TYPE
    SYNTAX       CucsManagedObjectDn
    MAX-ACCESS   read-only
    STATUS       current
    DESCRIPTION
        "Cisco UCS sw:SystemStatsHist:dn managed object property"
    ::= { cucsSwSystemStatsHistEntry 2 }

cucsSwSystemStatsHistRn OBJECT-TYPE
    SYNTAX       SnmpAdminString
    MAX-ACCESS   read-only
    STATUS       current
    DESCRIPTION
        "Cisco UCS sw:SystemStatsHist:rn managed object property"
    ::= { cucsSwSystemStatsHistEntry 3 }

cucsSwSystemStatsHistId OBJECT-TYPE
    SYNTAX       Unsigned64
    MAX-ACCESS   read-only
    STATUS       current
    DESCRIPTION
        "Cisco UCS sw:SystemStatsHist:id managed object property"
    ::= { cucsSwSystemStatsHistEntry 4 }

cucsSwSystemStatsHistLoad OBJECT-TYPE
    SYNTAX       INTEGER
    MAX-ACCESS   read-only
    STATUS       current
    DESCRIPTION
        "Cisco UCS sw:SystemStatsHist:load managed object property"
    ::= { cucsSwSystemStatsHistEntry 5 }

cucsSwSystemStatsHistLoadAvg OBJECT-TYPE
    SYNTAX       INTEGER
    MAX-ACCESS   read-only
    STATUS       current
    DESCRIPTION
        "Cisco UCS sw:SystemStatsHist:loadAvg managed object property"
    ::= { cucsSwSystemStatsHistEntry 6 }

cucsSwSystemStatsHistLoadMax OBJECT-TYPE
    SYNTAX       INTEGER
    MAX-ACCESS   read-only
    STATUS       current
    DESCRIPTION
        "Cisco UCS sw:SystemStatsHist:loadMax managed object property"
    ::= { cucsSwSystemStatsHistEntry 7 }

cucsSwSystemStatsHistLoadMin OBJECT-TYPE
    SYNTAX       INTEGER
    MAX-ACCESS   read-only
    STATUS       current
    DESCRIPTION
        "Cisco UCS sw:SystemStatsHist:loadMin managed object property"
    ::= { cucsSwSystemStatsHistEntry 8 }

cucsSwSystemStatsHistMemAvailable OBJECT-TYPE
    SYNTAX       Gauge32
    MAX-ACCESS   read-only
    STATUS       current
    DESCRIPTION
        "Cisco UCS sw:SystemStatsHist:memAvailable managed
        object property"
    ::= { cucsSwSystemStatsHistEntry 9 }

cucsSwSystemStatsHistMemAvailableAvg OBJECT-TYPE
    SYNTAX       Gauge32
    MAX-ACCESS   read-only
    STATUS       current
    DESCRIPTION
        "Cisco UCS sw:SystemStatsHist:memAvailableAvg managed
        object property"
    ::= { cucsSwSystemStatsHistEntry 10 }

cucsSwSystemStatsHistMemAvailableMax OBJECT-TYPE
    SYNTAX       Gauge32
    MAX-ACCESS   read-only
    STATUS       current
    DESCRIPTION
        "Cisco UCS sw:SystemStatsHist:memAvailableMax managed
        object property"
    ::= { cucsSwSystemStatsHistEntry 11 }

cucsSwSystemStatsHistMemAvailableMin OBJECT-TYPE
    SYNTAX       Gauge32
    MAX-ACCESS   read-only
    STATUS       current
    DESCRIPTION
        "Cisco UCS sw:SystemStatsHist:memAvailableMin managed
        object property"
    ::= { cucsSwSystemStatsHistEntry 12 }

cucsSwSystemStatsHistMemCached OBJECT-TYPE
    SYNTAX       Gauge32
    MAX-ACCESS   read-only
    STATUS       current
    DESCRIPTION
        "Cisco UCS sw:SystemStatsHist:memCached managed object property"
    ::= { cucsSwSystemStatsHistEntry 13 }

cucsSwSystemStatsHistMemCachedAvg OBJECT-TYPE
    SYNTAX       Gauge32
    MAX-ACCESS   read-only
    STATUS       current
    DESCRIPTION
        "Cisco UCS sw:SystemStatsHist:memCachedAvg managed
        object property"
    ::= { cucsSwSystemStatsHistEntry 14 }

cucsSwSystemStatsHistMemCachedMax OBJECT-TYPE
    SYNTAX       Gauge32
    MAX-ACCESS   read-only
    STATUS       current
    DESCRIPTION
        "Cisco UCS sw:SystemStatsHist:memCachedMax managed
        object property"
    ::= { cucsSwSystemStatsHistEntry 15 }

cucsSwSystemStatsHistMemCachedMin OBJECT-TYPE
    SYNTAX       Gauge32
    MAX-ACCESS   read-only
    STATUS       current
    DESCRIPTION
        "Cisco UCS sw:SystemStatsHist:memCachedMin managed
        object property"
    ::= { cucsSwSystemStatsHistEntry 16 }

cucsSwSystemStatsHistMostRecent OBJECT-TYPE
    SYNTAX       TruthValue
    MAX-ACCESS   read-only
    STATUS       current
    DESCRIPTION
        "Cisco UCS sw:SystemStatsHist:mostRecent managed object property"
    ::= { cucsSwSystemStatsHistEntry 17 }

cucsSwSystemStatsHistSuspect OBJECT-TYPE
    SYNTAX       TruthValue
    MAX-ACCESS   read-only
    STATUS       current
    DESCRIPTION
        "Cisco UCS sw:SystemStatsHist:suspect managed object property"
    ::= { cucsSwSystemStatsHistEntry 18 }

cucsSwSystemStatsHistThresholded OBJECT-TYPE
    SYNTAX       CucsSwSystemStatsHistThresholded
    MAX-ACCESS   read-only
    STATUS       current
    DESCRIPTION
        "Cisco UCS sw:SystemStatsHist:thresholded managed object property"
    ::= { cucsSwSystemStatsHistEntry 19 }

cucsSwSystemStatsHistTimeCollected OBJECT-TYPE
    SYNTAX       DateAndTime
    MAX-ACCESS   read-only
    STATUS       current
    DESCRIPTION
        "Cisco UCS sw:SystemStatsHist:timeCollected managed
        object property"
    ::= { cucsSwSystemStatsHistEntry 20 }

cucsSwSystemStatsHistCorrectableParityError OBJECT-TYPE
    SYNTAX       Gauge32
    MAX-ACCESS   read-only
    STATUS       current
    DESCRIPTION
        "Cisco UCS sw:SystemStatsHist:CorrectableParityError
        managed object property"
    ::= { cucsSwSystemStatsHistEntry 21 }

cucsSwSystemStatsHistCorrectableParityErrorAvg OBJECT-TYPE
    SYNTAX       Gauge32
    MAX-ACCESS   read-only
    STATUS       current
    DESCRIPTION
        "Cisco UCS sw:SystemStatsHist:CorrectableParityErrorAvg
        managed object property"
    ::= { cucsSwSystemStatsHistEntry 22 }

cucsSwSystemStatsHistCorrectableParityErrorMax OBJECT-TYPE
    SYNTAX       Gauge32
    MAX-ACCESS   read-only
    STATUS       current
    DESCRIPTION
        "Cisco UCS sw:SystemStatsHist:CorrectableParityErrorMax
        managed object property"
    ::= { cucsSwSystemStatsHistEntry 23 }

cucsSwSystemStatsHistCorrectableParityErrorMin OBJECT-TYPE
    SYNTAX       Gauge32
    MAX-ACCESS   read-only
    STATUS       current
    DESCRIPTION
        "Cisco UCS sw:SystemStatsHist:CorrectableParityErrorMin
        managed object property"
    ::= { cucsSwSystemStatsHistEntry 24 }

cucsSwSystemStatsHistKernelMemFree OBJECT-TYPE
    SYNTAX       Gauge32
    MAX-ACCESS   read-only
    STATUS       current
    DESCRIPTION
        "Cisco UCS sw:SystemStatsHist:kernelMemFree managed
        object property"
    ::= { cucsSwSystemStatsHistEntry 25 }

cucsSwSystemStatsHistKernelMemFreeAvg OBJECT-TYPE
    SYNTAX       Gauge32
    MAX-ACCESS   read-only
    STATUS       current
    DESCRIPTION
        "Cisco UCS sw:SystemStatsHist:kernelMemFreeAvg
        managed object property"
    ::= { cucsSwSystemStatsHistEntry 26 }

cucsSwSystemStatsHistKernelMemFreeMax OBJECT-TYPE
    SYNTAX       Gauge32
    MAX-ACCESS   read-only
    STATUS       current
    DESCRIPTION
        "Cisco UCS sw:SystemStatsHist:kernelMemFreeMax
        managed object property"
    ::= { cucsSwSystemStatsHistEntry 27 }

cucsSwSystemStatsHistKernelMemFreeMin OBJECT-TYPE
    SYNTAX       Gauge32
    MAX-ACCESS   read-only
    STATUS       current
    DESCRIPTION
        "Cisco UCS sw:SystemStatsHist:kernelMemFreeMin
        managed object property"
    ::= { cucsSwSystemStatsHistEntry 28 }

cucsSwSystemStatsHistKernelMemTotal OBJECT-TYPE
    SYNTAX       Gauge32
    MAX-ACCESS   read-only
    STATUS       current
    DESCRIPTION
        "Cisco UCS sw:SystemStatsHist:kernelMemTotal managed
        object property"
    ::= { cucsSwSystemStatsHistEntry 29 }

cucsSwSystemStatsHistKernelMemTotalAvg OBJECT-TYPE
    SYNTAX       Gauge32
    MAX-ACCESS   read-only
    STATUS       current
    DESCRIPTION
        "Cisco UCS sw:SystemStatsHist:kernelMemTotalAvg
        managed object property"
    ::= { cucsSwSystemStatsHistEntry 30 }

cucsSwSystemStatsHistKernelMemTotalMax OBJECT-TYPE
    SYNTAX       Gauge32
    MAX-ACCESS   read-only
    STATUS       current
    DESCRIPTION
        "Cisco UCS sw:SystemStatsHist:kernelMemTotalMax
        managed object property"
    ::= { cucsSwSystemStatsHistEntry 31 }

cucsSwSystemStatsHistKernelMemTotalMin OBJECT-TYPE
    SYNTAX       Gauge32
    MAX-ACCESS   read-only
    STATUS       current
    DESCRIPTION
        "Cisco UCS sw:SystemStatsHist:kernelMemTotalMin
        managed object property"
    ::= { cucsSwSystemStatsHistEntry 32 }

cucsSwUlanTable OBJECT-TYPE
    SYNTAX           SEQUENCE OF CucsSwUlanEntry
    MAX-ACCESS       not-accessible
    STATUS           current
    DESCRIPTION
        "Cisco UCS sw:Ulan managed object table"
    ::= { cucsSwObjects 30 }

cucsSwUlanEntry OBJECT-TYPE
    SYNTAX           CucsSwUlanEntry
    MAX-ACCESS       not-accessible
    STATUS           current
    DESCRIPTION
        "Entry for the cucsSwUlanTable table."
    INDEX { cucsSwUlanInstanceId }
    ::= { cucsSwUlanTable 1 }

CucsSwUlanEntry ::= SEQUENCE {
    cucsSwUlanInstanceId                                             CucsManagedObjectId,
    cucsSwUlanDn                                                     CucsManagedObjectDn,
    cucsSwUlanRn                                                     SnmpAdminString,
    cucsSwUlanEpDn                                                   SnmpAdminString,
    cucsSwUlanId                                                     Gauge32,
    cucsSwUlanIfRole                                                 CucsFabricVnetEpIfRole,
    cucsSwUlanIfType                                                 CucsNetworkVnetEpIfType,
    cucsSwUlanLocale                                                 CucsFabricVnetEpLocale,
    cucsSwUlanName                                                   SnmpAdminString,
    cucsSwUlanPeerDn                                                 SnmpAdminString,
    cucsSwUlanPubNwDn                                                SnmpAdminString,
    cucsSwUlanPubNwId                                                Gauge32,
    cucsSwUlanPubNwName                                              SnmpAdminString,
    cucsSwUlanPurpose                                                CucsSwUlanPurpose,
    cucsSwUlanSharing                                                CucsFabricAVlanSharing,
    cucsSwUlanSwitchId                                               CucsNetworkSwitchId,
    cucsSwUlanTransport                                              CucsFabricAVlanTransport,
    cucsSwUlanType                                                   CucsFabricAVlanType,
    cucsSwUlanVlanType                                               CucsFabricEpVlanVlanType,
    cucsSwUlanOperState                                              CucsFabricVlanOperState,
    cucsSwUlanPolicyOwner                                            CucsFabricVnetEpPolicyOwner,
    cucsSwUlanAssocPrimaryVlanState                                  CucsFabricVlanAssocPrimaryVlanState,
    cucsSwUlanAssocPrimaryVlanSwitchId                               CucsFabricAVlanAssocPrimaryVlanSwitchId,
    cucsSwUlanOverlapStateForA                                       CucsFabricVlanOverlapState,
    cucsSwUlanOverlapStateForB                                       CucsFabricVlanOverlapState
}

cucsSwUlanInstanceId OBJECT-TYPE
    SYNTAX       CucsManagedObjectId
    MAX-ACCESS   not-accessible
    STATUS       current
    DESCRIPTION
        "Instance identifier of the managed object."
    ::= { cucsSwUlanEntry 1 }

cucsSwUlanDn OBJECT-TYPE
    SYNTAX       CucsManagedObjectDn
    MAX-ACCESS   read-only
    STATUS       current
    DESCRIPTION
        "Cisco UCS sw:Ulan:dn managed object property"
    ::= { cucsSwUlanEntry 2 }

cucsSwUlanRn OBJECT-TYPE
    SYNTAX       SnmpAdminString
    MAX-ACCESS   read-only
    STATUS       current
    DESCRIPTION
        "Cisco UCS sw:Ulan:rn managed object property"
    ::= { cucsSwUlanEntry 3 }

cucsSwUlanEpDn OBJECT-TYPE
    SYNTAX       SnmpAdminString
    MAX-ACCESS   read-only
    STATUS       current
    DESCRIPTION
        "Cisco UCS sw:Ulan:epDn managed object property"
    ::= { cucsSwUlanEntry 4 }

cucsSwUlanId OBJECT-TYPE
    SYNTAX       Gauge32
    MAX-ACCESS   read-only
    STATUS       current
    DESCRIPTION
        "Cisco UCS sw:Ulan:id managed object property"
    ::= { cucsSwUlanEntry 5 }

cucsSwUlanIfRole OBJECT-TYPE
    SYNTAX       CucsFabricVnetEpIfRole
    MAX-ACCESS   read-only
    STATUS       current
    DESCRIPTION
        "Cisco UCS sw:Ulan:ifRole managed object property"
    ::= { cucsSwUlanEntry 6 }

cucsSwUlanIfType OBJECT-TYPE
    SYNTAX       CucsNetworkVnetEpIfType
    MAX-ACCESS   read-only
    STATUS       current
    DESCRIPTION
        "Cisco UCS sw:Ulan:ifType managed object property"
    ::= { cucsSwUlanEntry 7 }

cucsSwUlanLocale OBJECT-TYPE
    SYNTAX       CucsFabricVnetEpLocale
    MAX-ACCESS   read-only
    STATUS       current
    DESCRIPTION
        "Cisco UCS sw:Ulan:locale managed object property"
    ::= { cucsSwUlanEntry 8 }

cucsSwUlanName OBJECT-TYPE
    SYNTAX       SnmpAdminString
    MAX-ACCESS   read-only
    STATUS       current
    DESCRIPTION
        "Cisco UCS sw:Ulan:name managed object property"
    ::= { cucsSwUlanEntry 9 }

cucsSwUlanPeerDn OBJECT-TYPE
    SYNTAX       SnmpAdminString
    MAX-ACCESS   read-only
    STATUS       current
    DESCRIPTION
        "Cisco UCS sw:Ulan:peerDn managed object property"
    ::= { cucsSwUlanEntry 10 }

cucsSwUlanPubNwDn OBJECT-TYPE
    SYNTAX       SnmpAdminString
    MAX-ACCESS   read-only
    STATUS       current
    DESCRIPTION
        "Cisco UCS sw:Ulan:pubNwDn managed object property"
    ::= { cucsSwUlanEntry 11 }

cucsSwUlanPubNwId OBJECT-TYPE
    SYNTAX       Gauge32
    MAX-ACCESS   read-only
    STATUS       current
    DESCRIPTION
        "Cisco UCS sw:Ulan:pubNwId managed object property"
    ::= { cucsSwUlanEntry 12 }

cucsSwUlanPubNwName OBJECT-TYPE
    SYNTAX       SnmpAdminString
    MAX-ACCESS   read-only
    STATUS       current
    DESCRIPTION
        "Cisco UCS sw:Ulan:pubNwName managed object property"
    ::= { cucsSwUlanEntry 13 }

cucsSwUlanPurpose OBJECT-TYPE
    SYNTAX       CucsSwUlanPurpose
    MAX-ACCESS   read-only
    STATUS       current
    DESCRIPTION
        "Cisco UCS sw:Ulan:purpose managed object property"
    ::= { cucsSwUlanEntry 14 }

cucsSwUlanSharing OBJECT-TYPE
    SYNTAX       CucsFabricAVlanSharing
    MAX-ACCESS   read-only
    STATUS       current
    DESCRIPTION
        "Cisco UCS sw:Ulan:sharing managed object property"
    ::= { cucsSwUlanEntry 15 }

cucsSwUlanSwitchId OBJECT-TYPE
    SYNTAX       CucsNetworkSwitchId
    MAX-ACCESS   read-only
    STATUS       current
    DESCRIPTION
        "Cisco UCS sw:Ulan:switchId managed object property"
    ::= { cucsSwUlanEntry 16 }

cucsSwUlanTransport OBJECT-TYPE
    SYNTAX       CucsFabricAVlanTransport
    MAX-ACCESS   read-only
    STATUS       current
    DESCRIPTION
        "Cisco UCS sw:Ulan:transport managed object property"
    ::= { cucsSwUlanEntry 17 }

cucsSwUlanType OBJECT-TYPE
    SYNTAX       CucsFabricAVlanType
    MAX-ACCESS   read-only
    STATUS       current
    DESCRIPTION
        "Cisco UCS sw:Ulan:type managed object property"
    ::= { cucsSwUlanEntry 18 }

cucsSwUlanVlanType OBJECT-TYPE
    SYNTAX       CucsFabricEpVlanVlanType
    MAX-ACCESS   read-only
    STATUS       current
    DESCRIPTION
        "Cisco UCS sw:Ulan:vlanType managed object property"
    ::= { cucsSwUlanEntry 19 }

cucsSwUlanOperState OBJECT-TYPE
    SYNTAX       CucsFabricVlanOperState
    MAX-ACCESS   read-only
    STATUS       current
    DESCRIPTION
        "Cisco UCS sw:Ulan:operState managed object property"
    ::= { cucsSwUlanEntry 20 }

cucsSwUlanPolicyOwner OBJECT-TYPE
    SYNTAX       CucsFabricVnetEpPolicyOwner
    MAX-ACCESS   read-only
    STATUS       current
    DESCRIPTION
        "Cisco UCS sw:Ulan:policyOwner managed object property"
    ::= { cucsSwUlanEntry 22 }

cucsSwUlanAssocPrimaryVlanState OBJECT-TYPE
    SYNTAX       CucsFabricVlanAssocPrimaryVlanState
    MAX-ACCESS   read-only
    STATUS       current
    DESCRIPTION
        "Cisco UCS sw:Ulan:assocPrimaryVlanState managed object property"
    ::= { cucsSwUlanEntry 23 }

cucsSwUlanAssocPrimaryVlanSwitchId OBJECT-TYPE
    SYNTAX       CucsFabricAVlanAssocPrimaryVlanSwitchId
    MAX-ACCESS   read-only
    STATUS       current
    DESCRIPTION
        "Cisco UCS sw:Ulan:assocPrimaryVlanSwitchId managed
        object property"
    ::= { cucsSwUlanEntry 24 }

cucsSwUlanOverlapStateForA OBJECT-TYPE
    SYNTAX       CucsFabricVlanOverlapState
    MAX-ACCESS   read-only
    STATUS       current
    DESCRIPTION
        "Cisco UCS sw:Ulan:overlapStateForA managed object property"
    ::= { cucsSwUlanEntry 25 }

cucsSwUlanOverlapStateForB OBJECT-TYPE
    SYNTAX       CucsFabricVlanOverlapState
    MAX-ACCESS   read-only
    STATUS       current
    DESCRIPTION
        "Cisco UCS sw:Ulan:overlapStateForB managed object property"
    ::= { cucsSwUlanEntry 26 }

cucsSwUtilityDomainTable OBJECT-TYPE
    SYNTAX           SEQUENCE OF CucsSwUtilityDomainEntry
    MAX-ACCESS       not-accessible
    STATUS           current
    DESCRIPTION
        "Cisco UCS sw:UtilityDomain managed object table"
    ::= { cucsSwObjects 31 }

cucsSwUtilityDomainEntry OBJECT-TYPE
    SYNTAX           CucsSwUtilityDomainEntry
    MAX-ACCESS       not-accessible
    STATUS           current
    DESCRIPTION
        "Entry for the cucsSwUtilityDomainTable table."
    INDEX { cucsSwUtilityDomainInstanceId }
    ::= { cucsSwUtilityDomainTable 1 }

CucsSwUtilityDomainEntry ::= SEQUENCE {
    cucsSwUtilityDomainInstanceId                                    CucsManagedObjectId,
    cucsSwUtilityDomainDn                                            CucsManagedObjectDn,
    cucsSwUtilityDomainRn                                            SnmpAdminString,
    cucsSwUtilityDomainFsmDescr                                      SnmpAdminString,
    cucsSwUtilityDomainFsmPrev                                       SnmpAdminString,
    cucsSwUtilityDomainFsmProgr                                      Gauge32,
    cucsSwUtilityDomainFsmRmtInvErrCode                              Gauge32,
    cucsSwUtilityDomainFsmRmtInvErrDescr                             SnmpAdminString,
    cucsSwUtilityDomainFsmRmtInvRslt                                 CucsConditionRemoteInvRslt,
    cucsSwUtilityDomainFsmStageDescr                                 SnmpAdminString,
    cucsSwUtilityDomainFsmStamp                                      DateAndTime,
    cucsSwUtilityDomainFsmStatus                                     SnmpAdminString,
    cucsSwUtilityDomainFsmTry                                        Gauge32,
    cucsSwUtilityDomainLocale                                        CucsSwUtilityDomainLocale,
    cucsSwUtilityDomainName                                          SnmpAdminString,
    cucsSwUtilityDomainSwitchId                                      CucsNetworkSwitchId,
    cucsSwUtilityDomainTransport                                     CucsNetworkTransport,
    cucsSwUtilityDomainType                                          CucsSwUtilityDomainType
}

cucsSwUtilityDomainInstanceId OBJECT-TYPE
    SYNTAX       CucsManagedObjectId
    MAX-ACCESS   not-accessible
    STATUS       current
    DESCRIPTION
        "Instance identifier of the managed object."
    ::= { cucsSwUtilityDomainEntry 1 }

cucsSwUtilityDomainDn OBJECT-TYPE
    SYNTAX       CucsManagedObjectDn
    MAX-ACCESS   read-only
    STATUS       current
    DESCRIPTION
        "Cisco UCS sw:UtilityDomain:dn managed object property"
    ::= { cucsSwUtilityDomainEntry 2 }

cucsSwUtilityDomainRn OBJECT-TYPE
    SYNTAX       SnmpAdminString
    MAX-ACCESS   read-only
    STATUS       current
    DESCRIPTION
        "Cisco UCS sw:UtilityDomain:rn managed object property"
    ::= { cucsSwUtilityDomainEntry 3 }

cucsSwUtilityDomainFsmDescr OBJECT-TYPE
    SYNTAX       SnmpAdminString
    MAX-ACCESS   read-only
    STATUS       current
    DESCRIPTION
        "Cisco UCS sw:UtilityDomain:fsmDescr managed object property"
    ::= { cucsSwUtilityDomainEntry 4 }

cucsSwUtilityDomainFsmPrev OBJECT-TYPE
    SYNTAX       SnmpAdminString
    MAX-ACCESS   read-only
    STATUS       current
    DESCRIPTION
        "Cisco UCS sw:UtilityDomain:fsmPrev managed object property"
    ::= { cucsSwUtilityDomainEntry 5 }

cucsSwUtilityDomainFsmProgr OBJECT-TYPE
    SYNTAX       Gauge32
    MAX-ACCESS   read-only
    STATUS       current
    DESCRIPTION
        "Cisco UCS sw:UtilityDomain:fsmProgr managed object property"
    ::= { cucsSwUtilityDomainEntry 6 }

cucsSwUtilityDomainFsmRmtInvErrCode OBJECT-TYPE
    SYNTAX       Gauge32
    MAX-ACCESS   read-only
    STATUS       current
    DESCRIPTION
        "Cisco UCS sw:UtilityDomain:fsmRmtInvErrCode managed
        object property"
    ::= { cucsSwUtilityDomainEntry 7 }

cucsSwUtilityDomainFsmRmtInvErrDescr OBJECT-TYPE
    SYNTAX       SnmpAdminString
    MAX-ACCESS   read-only
    STATUS       current
    DESCRIPTION
        "Cisco UCS sw:UtilityDomain:fsmRmtInvErrDescr managed
        object property"
    ::= { cucsSwUtilityDomainEntry 8 }

cucsSwUtilityDomainFsmRmtInvRslt OBJECT-TYPE
    SYNTAX       CucsConditionRemoteInvRslt
    MAX-ACCESS   read-only
    STATUS       current
    DESCRIPTION
        "Cisco UCS sw:UtilityDomain:fsmRmtInvRslt managed object property"
    ::= { cucsSwUtilityDomainEntry 9 }

cucsSwUtilityDomainFsmStageDescr OBJECT-TYPE
    SYNTAX       SnmpAdminString
    MAX-ACCESS   read-only
    STATUS       current
    DESCRIPTION
        "Cisco UCS sw:UtilityDomain:fsmStageDescr managed object property"
    ::= { cucsSwUtilityDomainEntry 10 }

cucsSwUtilityDomainFsmStamp OBJECT-TYPE
    SYNTAX       DateAndTime
    MAX-ACCESS   read-only
    STATUS       current
    DESCRIPTION
        "Cisco UCS sw:UtilityDomain:fsmStamp managed object property"
    ::= { cucsSwUtilityDomainEntry 11 }

cucsSwUtilityDomainFsmStatus OBJECT-TYPE
    SYNTAX       SnmpAdminString
    MAX-ACCESS   read-only
    STATUS       current
    DESCRIPTION
        "Cisco UCS sw:UtilityDomain:fsmStatus managed object property"
    ::= { cucsSwUtilityDomainEntry 12 }

cucsSwUtilityDomainFsmTry OBJECT-TYPE
    SYNTAX       Gauge32
    MAX-ACCESS   read-only
    STATUS       current
    DESCRIPTION
        "Cisco UCS sw:UtilityDomain:fsmTry managed object property"
    ::= { cucsSwUtilityDomainEntry 13 }

cucsSwUtilityDomainLocale OBJECT-TYPE
    SYNTAX       CucsSwUtilityDomainLocale
    MAX-ACCESS   read-only
    STATUS       current
    DESCRIPTION
        "Cisco UCS sw:UtilityDomain:locale managed object property"
    ::= { cucsSwUtilityDomainEntry 14 }

cucsSwUtilityDomainName OBJECT-TYPE
    SYNTAX       SnmpAdminString
    MAX-ACCESS   read-only
    STATUS       current
    DESCRIPTION
        "Cisco UCS sw:UtilityDomain:name managed object property"
    ::= { cucsSwUtilityDomainEntry 15 }

cucsSwUtilityDomainSwitchId OBJECT-TYPE
    SYNTAX       CucsNetworkSwitchId
    MAX-ACCESS   read-only
    STATUS       current
    DESCRIPTION
        "Cisco UCS sw:UtilityDomain:switchId managed object property"
    ::= { cucsSwUtilityDomainEntry 16 }

cucsSwUtilityDomainTransport OBJECT-TYPE
    SYNTAX       CucsNetworkTransport
    MAX-ACCESS   read-only
    STATUS       current
    DESCRIPTION
        "Cisco UCS sw:UtilityDomain:transport managed object property"
    ::= { cucsSwUtilityDomainEntry 17 }

cucsSwUtilityDomainType OBJECT-TYPE
    SYNTAX       CucsSwUtilityDomainType
    MAX-ACCESS   read-only
    STATUS       current
    DESCRIPTION
        "Cisco UCS sw:UtilityDomain:type managed object property"
    ::= { cucsSwUtilityDomainEntry 18 }

cucsSwUtilityDomainFsmTable OBJECT-TYPE
    SYNTAX           SEQUENCE OF CucsSwUtilityDomainFsmEntry
    MAX-ACCESS       not-accessible
    STATUS           current
    DESCRIPTION
        "Cisco UCS sw:UtilityDomainFsm managed object table"
    ::= { cucsSwObjects 63 }

cucsSwUtilityDomainFsmEntry OBJECT-TYPE
    SYNTAX           CucsSwUtilityDomainFsmEntry
    MAX-ACCESS       not-accessible
    STATUS           current
    DESCRIPTION
        "Entry for the cucsSwUtilityDomainFsmTable table."
    INDEX { cucsSwUtilityDomainFsmInstanceId }
    ::= { cucsSwUtilityDomainFsmTable 1 }

CucsSwUtilityDomainFsmEntry ::= SEQUENCE {
    cucsSwUtilityDomainFsmInstanceId                                 CucsManagedObjectId,
    cucsSwUtilityDomainFsmDn                                         CucsManagedObjectDn,
    cucsSwUtilityDomainFsmRn                                         SnmpAdminString,
    cucsSwUtilityDomainFsmCompletionTime                             DateAndTime,
    cucsSwUtilityDomainFsmCurrentFsm                                 CucsSwUtilityDomainFsmCurrentFsm,
    cucsSwUtilityDomainFsmDescrData                                  SnmpAdminString,
    cucsSwUtilityDomainFsmFsmStatus                                  CucsFsmFsmStageStatus,
    cucsSwUtilityDomainFsmProgress                                   Gauge32,
    cucsSwUtilityDomainFsmRmtErrCode                                 Gauge32,
    cucsSwUtilityDomainFsmRmtErrDescr                                SnmpAdminString,
    cucsSwUtilityDomainFsmRmtRslt                                    CucsConditionRemoteInvRslt
}

cucsSwUtilityDomainFsmInstanceId OBJECT-TYPE
    SYNTAX       CucsManagedObjectId
    MAX-ACCESS   not-accessible
    STATUS       current
    DESCRIPTION
        "Instance identifier of the managed object."
    ::= { cucsSwUtilityDomainFsmEntry 1 }

cucsSwUtilityDomainFsmDn OBJECT-TYPE
    SYNTAX       CucsManagedObjectDn
    MAX-ACCESS   read-only
    STATUS       current
    DESCRIPTION
        "Cisco UCS sw:UtilityDomainFsm:dn managed object property"
    ::= { cucsSwUtilityDomainFsmEntry 2 }

cucsSwUtilityDomainFsmRn OBJECT-TYPE
    SYNTAX       SnmpAdminString
    MAX-ACCESS   read-only
    STATUS       current
    DESCRIPTION
        "Cisco UCS sw:UtilityDomainFsm:rn managed object property"
    ::= { cucsSwUtilityDomainFsmEntry 3 }

cucsSwUtilityDomainFsmCompletionTime OBJECT-TYPE
    SYNTAX       DateAndTime
    MAX-ACCESS   read-only
    STATUS       current
    DESCRIPTION
        "Cisco UCS sw:UtilityDomainFsm:completionTime managed
        object property"
    ::= { cucsSwUtilityDomainFsmEntry 4 }

cucsSwUtilityDomainFsmCurrentFsm OBJECT-TYPE
    SYNTAX       CucsSwUtilityDomainFsmCurrentFsm
    MAX-ACCESS   read-only
    STATUS       current
    DESCRIPTION
        "Cisco UCS sw:UtilityDomainFsm:currentFsm managed object property"
    ::= { cucsSwUtilityDomainFsmEntry 5 }

cucsSwUtilityDomainFsmDescrData OBJECT-TYPE
    SYNTAX       SnmpAdminString
    MAX-ACCESS   read-only
    STATUS       current
    DESCRIPTION
        "Cisco UCS sw:UtilityDomainFsm:descr managed object property"
    ::= { cucsSwUtilityDomainFsmEntry 6 }

cucsSwUtilityDomainFsmFsmStatus OBJECT-TYPE
    SYNTAX       CucsFsmFsmStageStatus
    MAX-ACCESS   read-only
    STATUS       current
    DESCRIPTION
        "Cisco UCS sw:UtilityDomainFsm:fsmStatus managed object property"
    ::= { cucsSwUtilityDomainFsmEntry 7 }

cucsSwUtilityDomainFsmProgress OBJECT-TYPE
    SYNTAX       Gauge32
    MAX-ACCESS   read-only
    STATUS       current
    DESCRIPTION
        "Cisco UCS sw:UtilityDomainFsm:progress managed object property"
    ::= { cucsSwUtilityDomainFsmEntry 8 }

cucsSwUtilityDomainFsmRmtErrCode OBJECT-TYPE
    SYNTAX       Gauge32
    MAX-ACCESS   read-only
    STATUS       current
    DESCRIPTION
        "Cisco UCS sw:UtilityDomainFsm:rmtErrCode managed object property"
    ::= { cucsSwUtilityDomainFsmEntry 9 }

cucsSwUtilityDomainFsmRmtErrDescr OBJECT-TYPE
    SYNTAX       SnmpAdminString
    MAX-ACCESS   read-only
    STATUS       current
    DESCRIPTION
        "Cisco UCS sw:UtilityDomainFsm:rmtErrDescr managed
        object property"
    ::= { cucsSwUtilityDomainFsmEntry 10 }

cucsSwUtilityDomainFsmRmtRslt OBJECT-TYPE
    SYNTAX       CucsConditionRemoteInvRslt
    MAX-ACCESS   read-only
    STATUS       current
    DESCRIPTION
        "Cisco UCS sw:UtilityDomainFsm:rmtRslt managed object property"
    ::= { cucsSwUtilityDomainFsmEntry 11 }

cucsSwUtilityDomainFsmStageTable OBJECT-TYPE
    SYNTAX           SEQUENCE OF CucsSwUtilityDomainFsmStageEntry
    MAX-ACCESS       not-accessible
    STATUS           current
    DESCRIPTION
        "Cisco UCS sw:UtilityDomainFsmStage managed object table"
    ::= { cucsSwObjects 64 }

cucsSwUtilityDomainFsmStageEntry OBJECT-TYPE
    SYNTAX           CucsSwUtilityDomainFsmStageEntry
    MAX-ACCESS       not-accessible
    STATUS           current
    DESCRIPTION
        "Entry for the cucsSwUtilityDomainFsmStageTable table."
    INDEX { cucsSwUtilityDomainFsmStageInstanceId }
    ::= { cucsSwUtilityDomainFsmStageTable 1 }

CucsSwUtilityDomainFsmStageEntry ::= SEQUENCE {
    cucsSwUtilityDomainFsmStageInstanceId                            CucsManagedObjectId,
    cucsSwUtilityDomainFsmStageDn                                    CucsManagedObjectDn,
    cucsSwUtilityDomainFsmStageRn                                    SnmpAdminString,
    cucsSwUtilityDomainFsmStageDescrData                             SnmpAdminString,
    cucsSwUtilityDomainFsmStageLastUpdateTime                        DateAndTime,
    cucsSwUtilityDomainFsmStageName                                  CucsSwUtilityDomainFsmStageName,
    cucsSwUtilityDomainFsmStageOrder                                 Gauge32,
    cucsSwUtilityDomainFsmStageRetry                                 Gauge32,
    cucsSwUtilityDomainFsmStageStageStatus                           CucsFsmFsmStageStatus
}

cucsSwUtilityDomainFsmStageInstanceId OBJECT-TYPE
    SYNTAX       CucsManagedObjectId
    MAX-ACCESS   not-accessible
    STATUS       current
    DESCRIPTION
        "Instance identifier of the managed object."
    ::= { cucsSwUtilityDomainFsmStageEntry 1 }

cucsSwUtilityDomainFsmStageDn OBJECT-TYPE
    SYNTAX       CucsManagedObjectDn
    MAX-ACCESS   read-only
    STATUS       current
    DESCRIPTION
        "Cisco UCS sw:UtilityDomainFsmStage:dn managed object property"
    ::= { cucsSwUtilityDomainFsmStageEntry 2 }

cucsSwUtilityDomainFsmStageRn OBJECT-TYPE
    SYNTAX       SnmpAdminString
    MAX-ACCESS   read-only
    STATUS       current
    DESCRIPTION
        "Cisco UCS sw:UtilityDomainFsmStage:rn managed object property"
    ::= { cucsSwUtilityDomainFsmStageEntry 3 }

cucsSwUtilityDomainFsmStageDescrData OBJECT-TYPE
    SYNTAX       SnmpAdminString
    MAX-ACCESS   read-only
    STATUS       current
    DESCRIPTION
        "Cisco UCS sw:UtilityDomainFsmStage:descr managed object property"
    ::= { cucsSwUtilityDomainFsmStageEntry 4 }

cucsSwUtilityDomainFsmStageLastUpdateTime OBJECT-TYPE
    SYNTAX       DateAndTime
    MAX-ACCESS   read-only
    STATUS       current
    DESCRIPTION
        "Cisco UCS sw:UtilityDomainFsmStage:lastUpdateTime
        managed object property"
    ::= { cucsSwUtilityDomainFsmStageEntry 5 }

cucsSwUtilityDomainFsmStageName OBJECT-TYPE
    SYNTAX       CucsSwUtilityDomainFsmStageName
    MAX-ACCESS   read-only
    STATUS       current
    DESCRIPTION
        "Cisco UCS sw:UtilityDomainFsmStage:name managed object property"
    ::= { cucsSwUtilityDomainFsmStageEntry 6 }

cucsSwUtilityDomainFsmStageOrder OBJECT-TYPE
    SYNTAX       Gauge32
    MAX-ACCESS   read-only
    STATUS       current
    DESCRIPTION
        "Cisco UCS sw:UtilityDomainFsmStage:order managed object property"
    ::= { cucsSwUtilityDomainFsmStageEntry 7 }

cucsSwUtilityDomainFsmStageRetry OBJECT-TYPE
    SYNTAX       Gauge32
    MAX-ACCESS   read-only
    STATUS       current
    DESCRIPTION
        "Cisco UCS sw:UtilityDomainFsmStage:retry managed object property"
    ::= { cucsSwUtilityDomainFsmStageEntry 8 }

cucsSwUtilityDomainFsmStageStageStatus OBJECT-TYPE
    SYNTAX       CucsFsmFsmStageStatus
    MAX-ACCESS   read-only
    STATUS       current
    DESCRIPTION
        "Cisco UCS sw:UtilityDomainFsmStage:stageStatus
        managed object property"
    ::= { cucsSwUtilityDomainFsmStageEntry 9 }

cucsSwUtilityDomainFsmTaskTable OBJECT-TYPE
    SYNTAX           SEQUENCE OF CucsSwUtilityDomainFsmTaskEntry
    MAX-ACCESS       not-accessible
    STATUS           current
    DESCRIPTION
        "Cisco UCS sw:UtilityDomainFsmTask managed object table"
    ::= { cucsSwObjects 32 }

cucsSwUtilityDomainFsmTaskEntry OBJECT-TYPE
    SYNTAX           CucsSwUtilityDomainFsmTaskEntry
    MAX-ACCESS       not-accessible
    STATUS           current
    DESCRIPTION
        "Entry for the cucsSwUtilityDomainFsmTaskTable table."
    INDEX { cucsSwUtilityDomainFsmTaskInstanceId }
    ::= { cucsSwUtilityDomainFsmTaskTable 1 }

CucsSwUtilityDomainFsmTaskEntry ::= SEQUENCE {
    cucsSwUtilityDomainFsmTaskInstanceId                             CucsManagedObjectId,
    cucsSwUtilityDomainFsmTaskDn                                     CucsManagedObjectDn,
    cucsSwUtilityDomainFsmTaskRn                                     SnmpAdminString,
    cucsSwUtilityDomainFsmTaskCompletion                             CucsFsmCompletion,
    cucsSwUtilityDomainFsmTaskFlags                                  CucsFsmFlags,
    cucsSwUtilityDomainFsmTaskItem                                   CucsSwUtilityDomainFsmTaskItem,
    cucsSwUtilityDomainFsmTaskSeqId                                  Gauge32
}

cucsSwUtilityDomainFsmTaskInstanceId OBJECT-TYPE
    SYNTAX       CucsManagedObjectId
    MAX-ACCESS   not-accessible
    STATUS       current
    DESCRIPTION
        "Instance identifier of the managed object."
    ::= { cucsSwUtilityDomainFsmTaskEntry 1 }

cucsSwUtilityDomainFsmTaskDn OBJECT-TYPE
    SYNTAX       CucsManagedObjectDn
    MAX-ACCESS   read-only
    STATUS       current
    DESCRIPTION
        "Cisco UCS sw:UtilityDomainFsmTask:dn managed object property"
    ::= { cucsSwUtilityDomainFsmTaskEntry 2 }

cucsSwUtilityDomainFsmTaskRn OBJECT-TYPE
    SYNTAX       SnmpAdminString
    MAX-ACCESS   read-only
    STATUS       current
    DESCRIPTION
        "Cisco UCS sw:UtilityDomainFsmTask:rn managed object property"
    ::= { cucsSwUtilityDomainFsmTaskEntry 3 }

cucsSwUtilityDomainFsmTaskCompletion OBJECT-TYPE
    SYNTAX       CucsFsmCompletion
    MAX-ACCESS   read-only
    STATUS       current
    DESCRIPTION
        "Cisco UCS sw:UtilityDomainFsmTask:completion managed
        object property"
    ::= { cucsSwUtilityDomainFsmTaskEntry 4 }

cucsSwUtilityDomainFsmTaskFlags OBJECT-TYPE
    SYNTAX       CucsFsmFlags
    MAX-ACCESS   read-only
    STATUS       current
    DESCRIPTION
        "Cisco UCS sw:UtilityDomainFsmTask:flags managed object property"
    ::= { cucsSwUtilityDomainFsmTaskEntry 5 }

cucsSwUtilityDomainFsmTaskItem OBJECT-TYPE
    SYNTAX       CucsSwUtilityDomainFsmTaskItem
    MAX-ACCESS   read-only
    STATUS       current
    DESCRIPTION
        "Cisco UCS sw:UtilityDomainFsmTask:item managed object property"
    ::= { cucsSwUtilityDomainFsmTaskEntry 6 }

cucsSwUtilityDomainFsmTaskSeqId OBJECT-TYPE
    SYNTAX       Gauge32
    MAX-ACCESS   read-only
    STATUS       current
    DESCRIPTION
        "Cisco UCS sw:UtilityDomainFsmTask:seqId managed object property"
    ::= { cucsSwUtilityDomainFsmTaskEntry 7 }

cucsSwVIFRefTable OBJECT-TYPE
    SYNTAX           SEQUENCE OF CucsSwVIFRefEntry
    MAX-ACCESS       not-accessible
    STATUS           current
    DESCRIPTION
        "Cisco UCS sw:VIFRef managed object table"
    ::= { cucsSwObjects 88 }

cucsSwVIFRefEntry OBJECT-TYPE
    SYNTAX           CucsSwVIFRefEntry
    MAX-ACCESS       not-accessible
    STATUS           current
    DESCRIPTION
        "Entry for the cucsSwVIFRefTable table."
    INDEX { cucsSwVIFRefInstanceId }
    ::= { cucsSwVIFRefTable 1 }

CucsSwVIFRefEntry ::= SEQUENCE {
    cucsSwVIFRefInstanceId                                           CucsManagedObjectId,
    cucsSwVIFRefDn                                                   CucsManagedObjectDn,
    cucsSwVIFRefRn                                                   SnmpAdminString,
    cucsSwVIFRefId                                                   Gauge32,
    cucsSwVIFRefPeerDn                                               SnmpAdminString
}

cucsSwVIFRefInstanceId OBJECT-TYPE
    SYNTAX       CucsManagedObjectId
    MAX-ACCESS   not-accessible
    STATUS       current
    DESCRIPTION
        "Instance identifier of the managed object."
    ::= { cucsSwVIFRefEntry 1 }

cucsSwVIFRefDn OBJECT-TYPE
    SYNTAX       CucsManagedObjectDn
    MAX-ACCESS   read-only
    STATUS       current
    DESCRIPTION
        "Cisco UCS sw:VIFRef:dn managed object property"
    ::= { cucsSwVIFRefEntry 2 }

cucsSwVIFRefRn OBJECT-TYPE
    SYNTAX       SnmpAdminString
    MAX-ACCESS   read-only
    STATUS       current
    DESCRIPTION
        "Cisco UCS sw:VIFRef:rn managed object property"
    ::= { cucsSwVIFRefEntry 3 }

cucsSwVIFRefId OBJECT-TYPE
    SYNTAX       Gauge32
    MAX-ACCESS   read-only
    STATUS       current
    DESCRIPTION
        "Cisco UCS sw:VIFRef:id managed object property"
    ::= { cucsSwVIFRefEntry 4 }

cucsSwVIFRefPeerDn OBJECT-TYPE
    SYNTAX       SnmpAdminString
    MAX-ACCESS   read-only
    STATUS       current
    DESCRIPTION
        "Cisco UCS sw:VIFRef:peerDn managed object property"
    ::= { cucsSwVIFRefEntry 5 }

cucsSwVirtL3IntfTable OBJECT-TYPE
    SYNTAX           SEQUENCE OF CucsSwVirtL3IntfEntry
    MAX-ACCESS       not-accessible
    STATUS           current
    DESCRIPTION
        "Cisco UCS sw:VirtL3Intf managed object table"
    ::= { cucsSwObjects 81 }

cucsSwVirtL3IntfEntry OBJECT-TYPE
    SYNTAX           CucsSwVirtL3IntfEntry
    MAX-ACCESS       not-accessible
    STATUS           current
    DESCRIPTION
        "Entry for the cucsSwVirtL3IntfTable table."
    INDEX { cucsSwVirtL3IntfInstanceId }
    ::= { cucsSwVirtL3IntfTable 1 }

CucsSwVirtL3IntfEntry ::= SEQUENCE {
    cucsSwVirtL3IntfInstanceId                                       CucsManagedObjectId,
    cucsSwVirtL3IntfDn                                               CucsManagedObjectDn,
    cucsSwVirtL3IntfRn                                               SnmpAdminString,
    cucsSwVirtL3IntfIpAddress                                        InetAddressIPv4,
    cucsSwVirtL3IntfName                                             SnmpAdminString,
    cucsSwVirtL3IntfNetmask                                          InetAddressIPv4,
    cucsSwVirtL3IntfVlanId                                           Gauge32
}

cucsSwVirtL3IntfInstanceId OBJECT-TYPE
    SYNTAX       CucsManagedObjectId
    MAX-ACCESS   not-accessible
    STATUS       current
    DESCRIPTION
        "Instance identifier of the managed object."
    ::= { cucsSwVirtL3IntfEntry 1 }

cucsSwVirtL3IntfDn OBJECT-TYPE
    SYNTAX       CucsManagedObjectDn
    MAX-ACCESS   read-only
    STATUS       current
    DESCRIPTION
        "Cisco UCS sw:VirtL3Intf:dn managed object property"
    ::= { cucsSwVirtL3IntfEntry 2 }

cucsSwVirtL3IntfRn OBJECT-TYPE
    SYNTAX       SnmpAdminString
    MAX-ACCESS   read-only
    STATUS       current
    DESCRIPTION
        "Cisco UCS sw:VirtL3Intf:rn managed object property"
    ::= { cucsSwVirtL3IntfEntry 3 }

cucsSwVirtL3IntfIpAddress OBJECT-TYPE
    SYNTAX       InetAddressIPv4
    MAX-ACCESS   read-only
    STATUS       current
    DESCRIPTION
        "Cisco UCS sw:VirtL3Intf:ipAddress managed object property"
    ::= { cucsSwVirtL3IntfEntry 4 }

cucsSwVirtL3IntfName OBJECT-TYPE
    SYNTAX       SnmpAdminString
    MAX-ACCESS   read-only
    STATUS       current
    DESCRIPTION
        "Cisco UCS sw:VirtL3Intf:name managed object property"
    ::= { cucsSwVirtL3IntfEntry 5 }

cucsSwVirtL3IntfNetmask OBJECT-TYPE
    SYNTAX       InetAddressIPv4
    MAX-ACCESS   read-only
    STATUS       current
    DESCRIPTION
        "Cisco UCS sw:VirtL3Intf:netmask managed object property"
    ::= { cucsSwVirtL3IntfEntry 6 }

cucsSwVirtL3IntfVlanId OBJECT-TYPE
    SYNTAX       Gauge32
    MAX-ACCESS   read-only
    STATUS       current
    DESCRIPTION
        "Cisco UCS sw:VirtL3Intf:vlanId managed object property"
    ::= { cucsSwVirtL3IntfEntry 7 }

cucsSwVlanTable OBJECT-TYPE
    SYNTAX           SEQUENCE OF CucsSwVlanEntry
    MAX-ACCESS       not-accessible
    STATUS           current
    DESCRIPTION
        "Cisco UCS sw:Vlan managed object table"
    ::= { cucsSwObjects 33 }

cucsSwVlanEntry OBJECT-TYPE
    SYNTAX           CucsSwVlanEntry
    MAX-ACCESS       not-accessible
    STATUS           current
    DESCRIPTION
        "Entry for the cucsSwVlanTable table."
    INDEX { cucsSwVlanInstanceId }
    ::= { cucsSwVlanTable 1 }

CucsSwVlanEntry ::= SEQUENCE {
    cucsSwVlanInstanceId                                             CucsManagedObjectId,
    cucsSwVlanDn                                                     CucsManagedObjectDn,
    cucsSwVlanRn                                                     SnmpAdminString,
    cucsSwVlanEpDn                                                   SnmpAdminString,
    cucsSwVlanId                                                     Gauge32,
    cucsSwVlanIfRole                                                 CucsFabricVnetEpIfRole,
    cucsSwVlanIfType                                                 CucsNetworkVnetEpIfType,
    cucsSwVlanLc                                                     CucsSwVlanLc,
    cucsSwVlanLocale                                                 CucsFabricVnetEpLocale,
    cucsSwVlanMonTrafDir                                             CucsFabricTrafficDirection,
    cucsSwVlanName                                                   SnmpAdminString,
    cucsSwVlanPeerDn                                                 SnmpAdminString,
    cucsSwVlanPubNwDn                                                SnmpAdminString,
    cucsSwVlanPubNwId                                                Gauge32,
    cucsSwVlanPubNwName                                              SnmpAdminString,
    cucsSwVlanSharing                                                CucsFabricAVlanSharing,
    cucsSwVlanSwitchId                                               CucsNetworkSwitchId,
    cucsSwVlanTransport                                              CucsFabricAVlanTransport,
    cucsSwVlanType                                                   CucsFabricAVlanType,
    cucsSwVlanVlanType                                               CucsFabricEpVlanVlanType,
    cucsSwVlanOperState                                              CucsFabricVlanOperState,
    cucsSwVlanCompressionType                                        CucsSwVlanCompType,
    cucsSwVlanQuerierIpAddrs                                         InetAddressIPv4,
    cucsSwVlanSnoopingEnabled                                        TruthValue,
    cucsSwVlanPolicyOwner                                            CucsFabricVnetEpPolicyOwner,
    cucsSwVlanAssocPrimaryVlanState                                  CucsFabricVlanAssocPrimaryVlanState,
    cucsSwVlanAssocPrimaryVlanSwitchId                               CucsFabricAVlanAssocPrimaryVlanSwitchId,
    cucsSwVlanOverlapStateForA                                       CucsFabricVlanOverlapState,
    cucsSwVlanOverlapStateForB                                       CucsFabricVlanOverlapState,
    cucsSwVlanSecVlanPerPrimaryVlanCount                             Gauge32,
    cucsSwVlanSecVlanPerPrimaryVlanCountStatus                       CucsNetworkCountStatus
}

cucsSwVlanInstanceId OBJECT-TYPE
    SYNTAX       CucsManagedObjectId
    MAX-ACCESS   not-accessible
    STATUS       current
    DESCRIPTION
        "Instance identifier of the managed object."
    ::= { cucsSwVlanEntry 1 }

cucsSwVlanDn OBJECT-TYPE
    SYNTAX       CucsManagedObjectDn
    MAX-ACCESS   read-only
    STATUS       current
    DESCRIPTION
        "Cisco UCS sw:Vlan:dn managed object property"
    ::= { cucsSwVlanEntry 2 }

cucsSwVlanRn OBJECT-TYPE
    SYNTAX       SnmpAdminString
    MAX-ACCESS   read-only
    STATUS       current
    DESCRIPTION
        "Cisco UCS sw:Vlan:rn managed object property"
    ::= { cucsSwVlanEntry 3 }

cucsSwVlanEpDn OBJECT-TYPE
    SYNTAX       SnmpAdminString
    MAX-ACCESS   read-only
    STATUS       current
    DESCRIPTION
        "Cisco UCS sw:Vlan:epDn managed object property"
    ::= { cucsSwVlanEntry 4 }

cucsSwVlanId OBJECT-TYPE
    SYNTAX       Gauge32
    MAX-ACCESS   read-only
    STATUS       current
    DESCRIPTION
        "Cisco UCS sw:Vlan:id managed object property"
    ::= { cucsSwVlanEntry 5 }

cucsSwVlanIfRole OBJECT-TYPE
    SYNTAX       CucsFabricVnetEpIfRole
    MAX-ACCESS   read-only
    STATUS       current
    DESCRIPTION
        "Cisco UCS sw:Vlan:ifRole managed object property"
    ::= { cucsSwVlanEntry 6 }

cucsSwVlanIfType OBJECT-TYPE
    SYNTAX       CucsNetworkVnetEpIfType
    MAX-ACCESS   read-only
    STATUS       current
    DESCRIPTION
        "Cisco UCS sw:Vlan:ifType managed object property"
    ::= { cucsSwVlanEntry 7 }

cucsSwVlanLc OBJECT-TYPE
    SYNTAX       CucsSwVlanLc
    MAX-ACCESS   read-only
    STATUS       current
    DESCRIPTION
        "Cisco UCS sw:Vlan:lc managed object property"
    ::= { cucsSwVlanEntry 8 }

cucsSwVlanLocale OBJECT-TYPE
    SYNTAX       CucsFabricVnetEpLocale
    MAX-ACCESS   read-only
    STATUS       current
    DESCRIPTION
        "Cisco UCS sw:Vlan:locale managed object property"
    ::= { cucsSwVlanEntry 9 }

cucsSwVlanMonTrafDir OBJECT-TYPE
    SYNTAX       CucsFabricTrafficDirection
    MAX-ACCESS   read-only
    STATUS       current
    DESCRIPTION
        "Cisco UCS sw:Vlan:monTrafDir managed object property"
    ::= { cucsSwVlanEntry 10 }

cucsSwVlanName OBJECT-TYPE
    SYNTAX       SnmpAdminString
    MAX-ACCESS   read-only
    STATUS       current
    DESCRIPTION
        "Cisco UCS sw:Vlan:name managed object property"
    ::= { cucsSwVlanEntry 11 }

cucsSwVlanPeerDn OBJECT-TYPE
    SYNTAX       SnmpAdminString
    MAX-ACCESS   read-only
    STATUS       current
    DESCRIPTION
        "Cisco UCS sw:Vlan:peerDn managed object property"
    ::= { cucsSwVlanEntry 12 }

cucsSwVlanPubNwDn OBJECT-TYPE
    SYNTAX       SnmpAdminString
    MAX-ACCESS   read-only
    STATUS       current
    DESCRIPTION
        "Cisco UCS sw:Vlan:pubNwDn managed object property"
    ::= { cucsSwVlanEntry 13 }

cucsSwVlanPubNwId OBJECT-TYPE
    SYNTAX       Gauge32
    MAX-ACCESS   read-only
    STATUS       current
    DESCRIPTION
        "Cisco UCS sw:Vlan:pubNwId managed object property"
    ::= { cucsSwVlanEntry 14 }

cucsSwVlanPubNwName OBJECT-TYPE
    SYNTAX       SnmpAdminString
    MAX-ACCESS   read-only
    STATUS       current
    DESCRIPTION
        "Cisco UCS sw:Vlan:pubNwName managed object property"
    ::= { cucsSwVlanEntry 15 }

cucsSwVlanSharing OBJECT-TYPE
    SYNTAX       CucsFabricAVlanSharing
    MAX-ACCESS   read-only
    STATUS       current
    DESCRIPTION
        "Cisco UCS sw:Vlan:sharing managed object property"
    ::= { cucsSwVlanEntry 16 }

cucsSwVlanSwitchId OBJECT-TYPE
    SYNTAX       CucsNetworkSwitchId
    MAX-ACCESS   read-only
    STATUS       current
    DESCRIPTION
        "Cisco UCS sw:Vlan:switchId managed object property"
    ::= { cucsSwVlanEntry 17 }

cucsSwVlanTransport OBJECT-TYPE
    SYNTAX       CucsFabricAVlanTransport
    MAX-ACCESS   read-only
    STATUS       current
    DESCRIPTION
        "Cisco UCS sw:Vlan:transport managed object property"
    ::= { cucsSwVlanEntry 18 }

cucsSwVlanType OBJECT-TYPE
    SYNTAX       CucsFabricAVlanType
    MAX-ACCESS   read-only
    STATUS       current
    DESCRIPTION
        "Cisco UCS sw:Vlan:type managed object property"
    ::= { cucsSwVlanEntry 19 }

cucsSwVlanVlanType OBJECT-TYPE
    SYNTAX       CucsFabricEpVlanVlanType
    MAX-ACCESS   read-only
    STATUS       current
    DESCRIPTION
        "Cisco UCS sw:Vlan:vlanType managed object property"
    ::= { cucsSwVlanEntry 20 }

cucsSwVlanOperState OBJECT-TYPE
    SYNTAX       CucsFabricVlanOperState
    MAX-ACCESS   read-only
    STATUS       current
    DESCRIPTION
        "Cisco UCS sw:Vlan:operState managed object property"
    ::= { cucsSwVlanEntry 21 }

cucsSwVlanCompressionType OBJECT-TYPE
    SYNTAX       CucsSwVlanCompType
    MAX-ACCESS   read-only
    STATUS       current
    DESCRIPTION
        "Cisco UCS sw:Vlan:compressionType managed object property"
    ::= { cucsSwVlanEntry 22 }

cucsSwVlanQuerierIpAddrs OBJECT-TYPE
    SYNTAX       InetAddressIPv4
    MAX-ACCESS   read-only
    STATUS       current
    DESCRIPTION
        "Cisco UCS sw:Vlan:querierIpAddrs managed object property"
    ::= { cucsSwVlanEntry 23 }

cucsSwVlanSnoopingEnabled OBJECT-TYPE
    SYNTAX       TruthValue
    MAX-ACCESS   read-only
    STATUS       current
    DESCRIPTION
        "Cisco UCS sw:Vlan:snoopingEnabled managed object property"
    ::= { cucsSwVlanEntry 24 }

cucsSwVlanPolicyOwner OBJECT-TYPE
    SYNTAX       CucsFabricVnetEpPolicyOwner
    MAX-ACCESS   read-only
    STATUS       current
    DESCRIPTION
        "Cisco UCS sw:Vlan:policyOwner managed object property"
    ::= { cucsSwVlanEntry 26 }

cucsSwVlanAssocPrimaryVlanState OBJECT-TYPE
    SYNTAX       CucsFabricVlanAssocPrimaryVlanState
    MAX-ACCESS   read-only
    STATUS       current
    DESCRIPTION
        "Cisco UCS sw:Vlan:assocPrimaryVlanState managed object property"
    ::= { cucsSwVlanEntry 27 }

cucsSwVlanAssocPrimaryVlanSwitchId OBJECT-TYPE
    SYNTAX       CucsFabricAVlanAssocPrimaryVlanSwitchId
    MAX-ACCESS   read-only
    STATUS       current
    DESCRIPTION
        "Cisco UCS sw:Vlan:assocPrimaryVlanSwitchId managed
        object property"
    ::= { cucsSwVlanEntry 28 }

cucsSwVlanOverlapStateForA OBJECT-TYPE
    SYNTAX       CucsFabricVlanOverlapState
    MAX-ACCESS   read-only
    STATUS       current
    DESCRIPTION
        "Cisco UCS sw:Vlan:overlapStateForA managed object property"
    ::= { cucsSwVlanEntry 29 }

cucsSwVlanOverlapStateForB OBJECT-TYPE
    SYNTAX       CucsFabricVlanOverlapState
    MAX-ACCESS   read-only
    STATUS       current
    DESCRIPTION
        "Cisco UCS sw:Vlan:overlapStateForB managed object property"
    ::= { cucsSwVlanEntry 30 }

cucsSwVlanSecVlanPerPrimaryVlanCount OBJECT-TYPE
    SYNTAX       Gauge32
    MAX-ACCESS   read-only
    STATUS       current
    DESCRIPTION
        "Cisco UCS sw:Vlan:secVlanPerPrimaryVlanCount managed
        object property"
    ::= { cucsSwVlanEntry 31 }

cucsSwVlanSecVlanPerPrimaryVlanCountStatus OBJECT-TYPE
    SYNTAX       CucsNetworkCountStatus
    MAX-ACCESS   read-only
    STATUS       current
    DESCRIPTION
        "Cisco UCS sw:Vlan:secVlanPerPrimaryVlanCountStatus
        managed object property"
    ::= { cucsSwVlanEntry 32 }

cucsSwVlanGroupTable OBJECT-TYPE
    SYNTAX           SEQUENCE OF CucsSwVlanGroupEntry
    MAX-ACCESS       not-accessible
    STATUS           current
    DESCRIPTION
        "Cisco UCS sw:VlanGroup managed object table"
    ::= { cucsSwObjects 65 }

cucsSwVlanGroupEntry OBJECT-TYPE
    SYNTAX           CucsSwVlanGroupEntry
    MAX-ACCESS       not-accessible
    STATUS           current
    DESCRIPTION
        "Entry for the cucsSwVlanGroupTable table."
    INDEX { cucsSwVlanGroupInstanceId }
    ::= { cucsSwVlanGroupTable 1 }

CucsSwVlanGroupEntry ::= SEQUENCE {
    cucsSwVlanGroupInstanceId                                        CucsManagedObjectId,
    cucsSwVlanGroupDn                                                CucsManagedObjectDn,
    cucsSwVlanGroupRn                                                SnmpAdminString,
    cucsSwVlanGroupId                                                Gauge32,
    cucsSwVlanGroupPeerDn                                            SnmpAdminString,
    cucsSwVlanGroupSwitchId                                          CucsNetworkSwitchId,
    cucsSwVlanGroupType                                              CucsSwVlanGroupType,
    cucsSwVlanGroupPvScore                                           Gauge32
}

cucsSwVlanGroupInstanceId OBJECT-TYPE
    SYNTAX       CucsManagedObjectId
    MAX-ACCESS   not-accessible
    STATUS       current
    DESCRIPTION
        "Instance identifier of the managed object."
    ::= { cucsSwVlanGroupEntry 1 }

cucsSwVlanGroupDn OBJECT-TYPE
    SYNTAX       CucsManagedObjectDn
    MAX-ACCESS   read-only
    STATUS       current
    DESCRIPTION
        "Cisco UCS sw:VlanGroup:dn managed object property"
    ::= { cucsSwVlanGroupEntry 2 }

cucsSwVlanGroupRn OBJECT-TYPE
    SYNTAX       SnmpAdminString
    MAX-ACCESS   read-only
    STATUS       current
    DESCRIPTION
        "Cisco UCS sw:VlanGroup:rn managed object property"
    ::= { cucsSwVlanGroupEntry 3 }

cucsSwVlanGroupId OBJECT-TYPE
    SYNTAX       Gauge32
    MAX-ACCESS   read-only
    STATUS       current
    DESCRIPTION
        "Cisco UCS sw:VlanGroup:id managed object property"
    ::= { cucsSwVlanGroupEntry 4 }

cucsSwVlanGroupPeerDn OBJECT-TYPE
    SYNTAX       SnmpAdminString
    MAX-ACCESS   read-only
    STATUS       current
    DESCRIPTION
        "Cisco UCS sw:VlanGroup:peerDn managed object property"
    ::= { cucsSwVlanGroupEntry 5 }

cucsSwVlanGroupSwitchId OBJECT-TYPE
    SYNTAX       CucsNetworkSwitchId
    MAX-ACCESS   read-only
    STATUS       current
    DESCRIPTION
        "Cisco UCS sw:VlanGroup:switchId managed object property"
    ::= { cucsSwVlanGroupEntry 6 }

cucsSwVlanGroupType OBJECT-TYPE
    SYNTAX       CucsSwVlanGroupType
    MAX-ACCESS   read-only
    STATUS       current
    DESCRIPTION
        "Cisco UCS sw:VlanGroup:type managed object property"
    ::= { cucsSwVlanGroupEntry 7 }

cucsSwVlanGroupPvScore OBJECT-TYPE
    SYNTAX       Gauge32
    MAX-ACCESS   read-only
    STATUS       current
    DESCRIPTION
        "Cisco UCS sw:VlanGroup:pvScore managed object property"
    ::= { cucsSwVlanGroupEntry 8 }

cucsSwVlanPortNsTable OBJECT-TYPE
    SYNTAX           SEQUENCE OF CucsSwVlanPortNsEntry
    MAX-ACCESS       not-accessible
    STATUS           current
    DESCRIPTION
        "Cisco UCS sw:VlanPortNs managed object table"
    ::= { cucsSwObjects 34 }

cucsSwVlanPortNsEntry OBJECT-TYPE
    SYNTAX           CucsSwVlanPortNsEntry
    MAX-ACCESS       not-accessible
    STATUS           current
    DESCRIPTION
        "Entry for the cucsSwVlanPortNsTable table."
    INDEX { cucsSwVlanPortNsInstanceId }
    ::= { cucsSwVlanPortNsTable 1 }

CucsSwVlanPortNsEntry ::= SEQUENCE {
    cucsSwVlanPortNsInstanceId                                       CucsManagedObjectId,
    cucsSwVlanPortNsDn                                               CucsManagedObjectDn,
    cucsSwVlanPortNsRn                                               SnmpAdminString,
    cucsSwVlanPortNsAccessVlanPortCount                              Gauge32,
    cucsSwVlanPortNsAllocStatus                                      CucsSwVlanPortNsAllocStatus,
    cucsSwVlanPortNsBorderVlanPortCount                              Gauge32,
    cucsSwVlanPortNsLimit                                            Gauge32,
    cucsSwVlanPortNsSwitchId                                         CucsNetworkSwitchId,
    cucsSwVlanPortNsConfigStatus                                     CucsSwConfigStatus,
    cucsSwVlanPortNsVlanCompOffLimit                                 Gauge32,
    cucsSwVlanPortNsVlanCompOnLimit                                  Gauge32,
    cucsSwVlanPortNsTotalVlanPortCount                               Gauge32,
    cucsSwVlanPortNsCompressedOptimizationSets                       Gauge32,
    cucsSwVlanPortNsCompressedVlanPortCount                          Gauge32,
    cucsSwVlanPortNsTotalOptimizationSets                            Gauge32,
    cucsSwVlanPortNsUncompressedVlanPortCount                        Gauge32
}

cucsSwVlanPortNsInstanceId OBJECT-TYPE
    SYNTAX       CucsManagedObjectId
    MAX-ACCESS   not-accessible
    STATUS       current
    DESCRIPTION
        "Instance identifier of the managed object."
    ::= { cucsSwVlanPortNsEntry 1 }

cucsSwVlanPortNsDn OBJECT-TYPE
    SYNTAX       CucsManagedObjectDn
    MAX-ACCESS   read-only
    STATUS       current
    DESCRIPTION
        "Cisco UCS sw:VlanPortNs:dn managed object property"
    ::= { cucsSwVlanPortNsEntry 2 }

cucsSwVlanPortNsRn OBJECT-TYPE
    SYNTAX       SnmpAdminString
    MAX-ACCESS   read-only
    STATUS       current
    DESCRIPTION
        "Cisco UCS sw:VlanPortNs:rn managed object property"
    ::= { cucsSwVlanPortNsEntry 3 }

cucsSwVlanPortNsAccessVlanPortCount OBJECT-TYPE
    SYNTAX       Gauge32
    MAX-ACCESS   read-only
    STATUS       current
    DESCRIPTION
        "Cisco UCS sw:VlanPortNs:accessVlanPortCount managed
        object property"
    ::= { cucsSwVlanPortNsEntry 4 }

cucsSwVlanPortNsAllocStatus OBJECT-TYPE
    SYNTAX       CucsSwVlanPortNsAllocStatus
    MAX-ACCESS   read-only
    STATUS       current
    DESCRIPTION
        "Cisco UCS sw:VlanPortNs:allocStatus managed object property"
    ::= { cucsSwVlanPortNsEntry 5 }

cucsSwVlanPortNsBorderVlanPortCount OBJECT-TYPE
    SYNTAX       Gauge32
    MAX-ACCESS   read-only
    STATUS       current
    DESCRIPTION
        "Cisco UCS sw:VlanPortNs:borderVlanPortCount managed
        object property"
    ::= { cucsSwVlanPortNsEntry 6 }

cucsSwVlanPortNsLimit OBJECT-TYPE
    SYNTAX       Gauge32
    MAX-ACCESS   read-only
    STATUS       current
    DESCRIPTION
        "Cisco UCS sw:VlanPortNs:limit managed object property"
    ::= { cucsSwVlanPortNsEntry 7 }

cucsSwVlanPortNsSwitchId OBJECT-TYPE
    SYNTAX       CucsNetworkSwitchId
    MAX-ACCESS   read-only
    STATUS       current
    DESCRIPTION
        "Cisco UCS sw:VlanPortNs:switchId managed object property"
    ::= { cucsSwVlanPortNsEntry 8 }

cucsSwVlanPortNsConfigStatus OBJECT-TYPE
    SYNTAX       CucsSwConfigStatus
    MAX-ACCESS   read-only
    STATUS       current
    DESCRIPTION
        "Cisco UCS sw:VlanPortNs:configStatus managed object property"
    ::= { cucsSwVlanPortNsEntry 9 }

cucsSwVlanPortNsVlanCompOffLimit OBJECT-TYPE
    SYNTAX       Gauge32
    MAX-ACCESS   read-only
    STATUS       current
    DESCRIPTION
        "Cisco UCS sw:VlanPortNs:vlanCompOffLimit managed object property"
    ::= { cucsSwVlanPortNsEntry 10 }

cucsSwVlanPortNsVlanCompOnLimit OBJECT-TYPE
    SYNTAX       Gauge32
    MAX-ACCESS   read-only
    STATUS       current
    DESCRIPTION
        "Cisco UCS sw:VlanPortNs:vlanCompOnLimit managed object property"
    ::= { cucsSwVlanPortNsEntry 11 }

cucsSwVlanPortNsTotalVlanPortCount OBJECT-TYPE
    SYNTAX       Gauge32
    MAX-ACCESS   read-only
    STATUS       current
    DESCRIPTION
        "Cisco UCS sw:VlanPortNs:totalVlanPortCount managed
        object property"
    ::= { cucsSwVlanPortNsEntry 12 }

cucsSwVlanPortNsCompressedOptimizationSets OBJECT-TYPE
    SYNTAX       Gauge32
    MAX-ACCESS   read-only
    STATUS       current
    DESCRIPTION
        "Cisco UCS sw:VlanPortNs:compressedOptimizationSets
        managed object property"
    ::= { cucsSwVlanPortNsEntry 13 }

cucsSwVlanPortNsCompressedVlanPortCount OBJECT-TYPE
    SYNTAX       Gauge32
    MAX-ACCESS   read-only
    STATUS       current
    DESCRIPTION
        "Cisco UCS sw:VlanPortNs:compressedVlanPortCount
        managed object property"
    ::= { cucsSwVlanPortNsEntry 14 }

cucsSwVlanPortNsTotalOptimizationSets OBJECT-TYPE
    SYNTAX       Gauge32
    MAX-ACCESS   read-only
    STATUS       current
    DESCRIPTION
        "Cisco UCS sw:VlanPortNs:totalOptimizationSets
        managed object property"
    ::= { cucsSwVlanPortNsEntry 15 }

cucsSwVlanPortNsUncompressedVlanPortCount OBJECT-TYPE
    SYNTAX       Gauge32
    MAX-ACCESS   read-only
    STATUS       current
    DESCRIPTION
        "Cisco UCS sw:VlanPortNs:uncompressedVlanPortCount
        managed object property"
    ::= { cucsSwVlanPortNsEntry 16 }

cucsSwVlanPortNsOverrideTable OBJECT-TYPE
    SYNTAX           SEQUENCE OF CucsSwVlanPortNsOverrideEntry
    MAX-ACCESS       not-accessible
    STATUS           current
    DESCRIPTION
        "Cisco UCS sw:VlanPortNsOverride managed object table"
    ::= { cucsSwObjects 37 }

cucsSwVlanPortNsOverrideEntry OBJECT-TYPE
    SYNTAX           CucsSwVlanPortNsOverrideEntry
    MAX-ACCESS       not-accessible
    STATUS           current
    DESCRIPTION
        "Entry for the cucsSwVlanPortNsOverrideTable table."
    INDEX { cucsSwVlanPortNsOverrideInstanceId }
    ::= { cucsSwVlanPortNsOverrideTable 1 }

CucsSwVlanPortNsOverrideEntry ::= SEQUENCE {
    cucsSwVlanPortNsOverrideInstanceId                               CucsManagedObjectId,
    cucsSwVlanPortNsOverrideDn                                       CucsManagedObjectDn,
    cucsSwVlanPortNsOverrideRn                                       SnmpAdminString,
    cucsSwVlanPortNsOverrideLimit                                    Gauge32
}

cucsSwVlanPortNsOverrideInstanceId OBJECT-TYPE
    SYNTAX       CucsManagedObjectId
    MAX-ACCESS   not-accessible
    STATUS       current
    DESCRIPTION
        "Instance identifier of the managed object."
    ::= { cucsSwVlanPortNsOverrideEntry 1 }

cucsSwVlanPortNsOverrideDn OBJECT-TYPE
    SYNTAX       CucsManagedObjectDn
    MAX-ACCESS   read-only
    STATUS       current
    DESCRIPTION
        "Cisco UCS sw:VlanPortNsOverride:dn managed object property"
    ::= { cucsSwVlanPortNsOverrideEntry 2 }

cucsSwVlanPortNsOverrideRn OBJECT-TYPE
    SYNTAX       SnmpAdminString
    MAX-ACCESS   read-only
    STATUS       current
    DESCRIPTION
        "Cisco UCS sw:VlanPortNsOverride:rn managed object property"
    ::= { cucsSwVlanPortNsOverrideEntry 3 }

cucsSwVlanPortNsOverrideLimit OBJECT-TYPE
    SYNTAX       Gauge32
    MAX-ACCESS   read-only
    STATUS       current
    DESCRIPTION
        "Cisco UCS sw:VlanPortNsOverride:limit managed object property"
    ::= { cucsSwVlanPortNsOverrideEntry 4 }

cucsSwVlanRefTable OBJECT-TYPE
    SYNTAX           SEQUENCE OF CucsSwVlanRefEntry
    MAX-ACCESS       not-accessible
    STATUS           current
    DESCRIPTION
        "Cisco UCS sw:VlanRef managed object table"
    ::= { cucsSwObjects 66 }

cucsSwVlanRefEntry OBJECT-TYPE
    SYNTAX           CucsSwVlanRefEntry
    MAX-ACCESS       not-accessible
    STATUS           current
    DESCRIPTION
        "Entry for the cucsSwVlanRefTable table."
    INDEX { cucsSwVlanRefInstanceId }
    ::= { cucsSwVlanRefTable 1 }

CucsSwVlanRefEntry ::= SEQUENCE {
    cucsSwVlanRefInstanceId                                          CucsManagedObjectId,
    cucsSwVlanRefDn                                                  CucsManagedObjectDn,
    cucsSwVlanRefRn                                                  SnmpAdminString,
    cucsSwVlanRefCompressionType                                     CucsSwVlanCompType,
    cucsSwVlanRefConfigStatus                                        CucsSwVlanConfigStatusType,
    cucsSwVlanRefId                                                  Gauge32,
    cucsSwVlanRefPeerDn                                              SnmpAdminString
}

cucsSwVlanRefInstanceId OBJECT-TYPE
    SYNTAX       CucsManagedObjectId
    MAX-ACCESS   not-accessible
    STATUS       current
    DESCRIPTION
        "Instance identifier of the managed object."
    ::= { cucsSwVlanRefEntry 1 }

cucsSwVlanRefDn OBJECT-TYPE
    SYNTAX       CucsManagedObjectDn
    MAX-ACCESS   read-only
    STATUS       current
    DESCRIPTION
        "Cisco UCS sw:VlanRef:dn managed object property"
    ::= { cucsSwVlanRefEntry 2 }

cucsSwVlanRefRn OBJECT-TYPE
    SYNTAX       SnmpAdminString
    MAX-ACCESS   read-only
    STATUS       current
    DESCRIPTION
        "Cisco UCS sw:VlanRef:rn managed object property"
    ::= { cucsSwVlanRefEntry 3 }

cucsSwVlanRefCompressionType OBJECT-TYPE
    SYNTAX       CucsSwVlanCompType
    MAX-ACCESS   read-only
    STATUS       current
    DESCRIPTION
        "Cisco UCS sw:VlanRef:compressionType managed object property"
    ::= { cucsSwVlanRefEntry 4 }

cucsSwVlanRefConfigStatus OBJECT-TYPE
    SYNTAX       CucsSwVlanConfigStatusType
    MAX-ACCESS   read-only
    STATUS       current
    DESCRIPTION
        "Cisco UCS sw:VlanRef:configStatus managed object property"
    ::= { cucsSwVlanRefEntry 5 }

cucsSwVlanRefId OBJECT-TYPE
    SYNTAX       Gauge32
    MAX-ACCESS   read-only
    STATUS       current
    DESCRIPTION
        "Cisco UCS sw:VlanRef:id managed object property"
    ::= { cucsSwVlanRefEntry 6 }

cucsSwVlanRefPeerDn OBJECT-TYPE
    SYNTAX       SnmpAdminString
    MAX-ACCESS   read-only
    STATUS       current
    DESCRIPTION
        "Cisco UCS sw:VlanRef:peerDn managed object property"
    ::= { cucsSwVlanRefEntry 7 }

cucsSwVsanTable OBJECT-TYPE
    SYNTAX           SEQUENCE OF CucsSwVsanEntry
    MAX-ACCESS       not-accessible
    STATUS           current
    DESCRIPTION
        "Cisco UCS sw:Vsan managed object table"
    ::= { cucsSwObjects 35 }

cucsSwVsanEntry OBJECT-TYPE
    SYNTAX           CucsSwVsanEntry
    MAX-ACCESS       not-accessible
    STATUS           current
    DESCRIPTION
        "Entry for the cucsSwVsanTable table."
    INDEX { cucsSwVsanInstanceId }
    ::= { cucsSwVsanTable 1 }

CucsSwVsanEntry ::= SEQUENCE {
    cucsSwVsanInstanceId                                             CucsManagedObjectId,
    cucsSwVsanDn                                                     CucsManagedObjectDn,
    cucsSwVsanRn                                                     SnmpAdminString,
    cucsSwVsanEpDn                                                   SnmpAdminString,
    cucsSwVsanFcoeVlan                                               Gauge32,
    cucsSwVsanId                                                     Gauge32,
    cucsSwVsanIfRole                                                 CucsFabricVnetEpIfRole,
    cucsSwVsanIfType                                                 CucsNetworkVnetEpIfType,
    cucsSwVsanLc                                                     CucsFsmLifecycle,
    cucsSwVsanLocale                                                 CucsFabricVnetEpLocale,
    cucsSwVsanMonTrafDir                                             CucsFabricTrafficDirection,
    cucsSwVsanName                                                   SnmpAdminString,
    cucsSwVsanPeerDn                                                 SnmpAdminString,
    cucsSwVsanSwitchId                                               CucsNetworkSwitchId,
    cucsSwVsanTransport                                              CucsFabricAVsanTransport,
    cucsSwVsanType                                                   CucsFabricAVsanType,
    cucsSwVsanDefaultZoning                                          CucsFabricDefaultZoningState,
    cucsSwVsanOperState                                              CucsFabricVsanOperState,
    cucsSwVsanFcZoneSharingMode                                      CucsFabricFcZoneSharingMode,
    cucsSwVsanFltAggr                                                Unsigned64,
    cucsSwVsanZoningState                                            CucsFabricZoningState,
    cucsSwVsanPolicyOwner                                            CucsFabricVnetEpPolicyOwner
}

cucsSwVsanInstanceId OBJECT-TYPE
    SYNTAX       CucsManagedObjectId
    MAX-ACCESS   not-accessible
    STATUS       current
    DESCRIPTION
        "Instance identifier of the managed object."
    ::= { cucsSwVsanEntry 1 }

cucsSwVsanDn OBJECT-TYPE
    SYNTAX       CucsManagedObjectDn
    MAX-ACCESS   read-only
    STATUS       current
    DESCRIPTION
        "Cisco UCS sw:Vsan:dn managed object property"
    ::= { cucsSwVsanEntry 2 }

cucsSwVsanRn OBJECT-TYPE
    SYNTAX       SnmpAdminString
    MAX-ACCESS   read-only
    STATUS       current
    DESCRIPTION
        "Cisco UCS sw:Vsan:rn managed object property"
    ::= { cucsSwVsanEntry 3 }

cucsSwVsanEpDn OBJECT-TYPE
    SYNTAX       SnmpAdminString
    MAX-ACCESS   read-only
    STATUS       current
    DESCRIPTION
        "Cisco UCS sw:Vsan:epDn managed object property"
    ::= { cucsSwVsanEntry 4 }

cucsSwVsanFcoeVlan OBJECT-TYPE
    SYNTAX       Gauge32
    MAX-ACCESS   read-only
    STATUS       current
    DESCRIPTION
        "Cisco UCS sw:Vsan:fcoeVlan managed object property"
    ::= { cucsSwVsanEntry 5 }

cucsSwVsanId OBJECT-TYPE
    SYNTAX       Gauge32
    MAX-ACCESS   read-only
    STATUS       current
    DESCRIPTION
        "Cisco UCS sw:Vsan:id managed object property"
    ::= { cucsSwVsanEntry 6 }

cucsSwVsanIfRole OBJECT-TYPE
    SYNTAX       CucsFabricVnetEpIfRole
    MAX-ACCESS   read-only
    STATUS       current
    DESCRIPTION
        "Cisco UCS sw:Vsan:ifRole managed object property"
    ::= { cucsSwVsanEntry 7 }

cucsSwVsanIfType OBJECT-TYPE
    SYNTAX       CucsNetworkVnetEpIfType
    MAX-ACCESS   read-only
    STATUS       current
    DESCRIPTION
        "Cisco UCS sw:Vsan:ifType managed object property"
    ::= { cucsSwVsanEntry 8 }

cucsSwVsanLc OBJECT-TYPE
    SYNTAX       CucsFsmLifecycle
    MAX-ACCESS   read-only
    STATUS       current
    DESCRIPTION
        "Cisco UCS sw:Vsan:lc managed object property"
    ::= { cucsSwVsanEntry 9 }

cucsSwVsanLocale OBJECT-TYPE
    SYNTAX       CucsFabricVnetEpLocale
    MAX-ACCESS   read-only
    STATUS       current
    DESCRIPTION
        "Cisco UCS sw:Vsan:locale managed object property"
    ::= { cucsSwVsanEntry 10 }

cucsSwVsanMonTrafDir OBJECT-TYPE
    SYNTAX       CucsFabricTrafficDirection
    MAX-ACCESS   read-only
    STATUS       current
    DESCRIPTION
        "Cisco UCS sw:Vsan:monTrafDir managed object property"
    ::= { cucsSwVsanEntry 11 }

cucsSwVsanName OBJECT-TYPE
    SYNTAX       SnmpAdminString
    MAX-ACCESS   read-only
    STATUS       current
    DESCRIPTION
        "Cisco UCS sw:Vsan:name managed object property"
    ::= { cucsSwVsanEntry 12 }

cucsSwVsanPeerDn OBJECT-TYPE
    SYNTAX       SnmpAdminString
    MAX-ACCESS   read-only
    STATUS       current
    DESCRIPTION
        "Cisco UCS sw:Vsan:peerDn managed object property"
    ::= { cucsSwVsanEntry 13 }

cucsSwVsanSwitchId OBJECT-TYPE
    SYNTAX       CucsNetworkSwitchId
    MAX-ACCESS   read-only
    STATUS       current
    DESCRIPTION
        "Cisco UCS sw:Vsan:switchId managed object property"
    ::= { cucsSwVsanEntry 14 }

cucsSwVsanTransport OBJECT-TYPE
    SYNTAX       CucsFabricAVsanTransport
    MAX-ACCESS   read-only
    STATUS       current
    DESCRIPTION
        "Cisco UCS sw:Vsan:transport managed object property"
    ::= { cucsSwVsanEntry 15 }

cucsSwVsanType OBJECT-TYPE
    SYNTAX       CucsFabricAVsanType
    MAX-ACCESS   read-only
    STATUS       current
    DESCRIPTION
        "Cisco UCS sw:Vsan:type managed object property"
    ::= { cucsSwVsanEntry 16 }

cucsSwVsanDefaultZoning OBJECT-TYPE
    SYNTAX       CucsFabricDefaultZoningState
    MAX-ACCESS   read-only
    STATUS       current
    DESCRIPTION
        "Cisco UCS sw:Vsan:defaultZoning managed object property"
    ::= { cucsSwVsanEntry 17 }

cucsSwVsanOperState OBJECT-TYPE
    SYNTAX       CucsFabricVsanOperState
    MAX-ACCESS   read-only
    STATUS       current
    DESCRIPTION
        "Cisco UCS sw:Vsan:operState managed object property"
    ::= { cucsSwVsanEntry 18 }

cucsSwVsanFcZoneSharingMode OBJECT-TYPE
    SYNTAX       CucsFabricFcZoneSharingMode
    MAX-ACCESS   read-only
    STATUS       current
    DESCRIPTION
        "Cisco UCS sw:Vsan:fcZoneSharingMode managed object property"
    ::= { cucsSwVsanEntry 19 }

cucsSwVsanFltAggr OBJECT-TYPE
    SYNTAX       Unsigned64
    MAX-ACCESS   read-only
    STATUS       current
    DESCRIPTION
        "Cisco UCS sw:Vsan:fltAggr managed object property"
    ::= { cucsSwVsanEntry 20 }

cucsSwVsanZoningState OBJECT-TYPE
    SYNTAX       CucsFabricZoningState
    MAX-ACCESS   read-only
    STATUS       current
    DESCRIPTION
        "Cisco UCS sw:Vsan:zoningState managed object property"
    ::= { cucsSwVsanEntry 21 }

cucsSwVsanPolicyOwner OBJECT-TYPE
    SYNTAX       CucsFabricVnetEpPolicyOwner
    MAX-ACCESS   read-only
    STATUS       current
    DESCRIPTION
        "Cisco UCS sw:Vsan:policyOwner managed object property"
    ::= { cucsSwVsanEntry 23 }

cucsSwZoneInitiatorMemberTable OBJECT-TYPE
    SYNTAX           SEQUENCE OF CucsSwZoneInitiatorMemberEntry
    MAX-ACCESS       not-accessible
    STATUS           current
    DESCRIPTION
        "Cisco UCS sw:ZoneInitiatorMember managed object table"
    ::= { cucsSwObjects 67 }

cucsSwZoneInitiatorMemberEntry OBJECT-TYPE
    SYNTAX           CucsSwZoneInitiatorMemberEntry
    MAX-ACCESS       not-accessible
    STATUS           current
    DESCRIPTION
        "Entry for the cucsSwZoneInitiatorMemberTable table."
    INDEX { cucsSwZoneInitiatorMemberInstanceId }
    ::= { cucsSwZoneInitiatorMemberTable 1 }

CucsSwZoneInitiatorMemberEntry ::= SEQUENCE {
    cucsSwZoneInitiatorMemberInstanceId                              CucsManagedObjectId,
    cucsSwZoneInitiatorMemberDn                                      CucsManagedObjectDn,
    cucsSwZoneInitiatorMemberRn                                      SnmpAdminString,
    cucsSwZoneInitiatorMemberEpDn                                    SnmpAdminString,
    cucsSwZoneInitiatorMemberLc                                      CucsSwFcZoneMemberLc,
    cucsSwZoneInitiatorMemberName                                    SnmpAdminString,
    cucsSwZoneInitiatorMemberPeerDn                                  SnmpAdminString,
    cucsSwZoneInitiatorMemberWwpn                                    Unsigned64
}

cucsSwZoneInitiatorMemberInstanceId OBJECT-TYPE
    SYNTAX       CucsManagedObjectId
    MAX-ACCESS   not-accessible
    STATUS       current
    DESCRIPTION
        "Instance identifier of the managed object."
    ::= { cucsSwZoneInitiatorMemberEntry 1 }

cucsSwZoneInitiatorMemberDn OBJECT-TYPE
    SYNTAX       CucsManagedObjectDn
    MAX-ACCESS   read-only
    STATUS       current
    DESCRIPTION
        "Cisco UCS sw:ZoneInitiatorMember:dn managed object property"
    ::= { cucsSwZoneInitiatorMemberEntry 2 }

cucsSwZoneInitiatorMemberRn OBJECT-TYPE
    SYNTAX       SnmpAdminString
    MAX-ACCESS   read-only
    STATUS       current
    DESCRIPTION
        "Cisco UCS sw:ZoneInitiatorMember:rn managed object property"
    ::= { cucsSwZoneInitiatorMemberEntry 3 }

cucsSwZoneInitiatorMemberEpDn OBJECT-TYPE
    SYNTAX       SnmpAdminString
    MAX-ACCESS   read-only
    STATUS       current
    DESCRIPTION
        "Cisco UCS sw:ZoneInitiatorMember:epDn managed object property"
    ::= { cucsSwZoneInitiatorMemberEntry 4 }

cucsSwZoneInitiatorMemberLc OBJECT-TYPE
    SYNTAX       CucsSwFcZoneMemberLc
    MAX-ACCESS   read-only
    STATUS       current
    DESCRIPTION
        "Cisco UCS sw:ZoneInitiatorMember:lc managed object property"
    ::= { cucsSwZoneInitiatorMemberEntry 5 }

cucsSwZoneInitiatorMemberName OBJECT-TYPE
    SYNTAX       SnmpAdminString
    MAX-ACCESS   read-only
    STATUS       current
    DESCRIPTION
        "Cisco UCS sw:ZoneInitiatorMember:name managed object property"
    ::= { cucsSwZoneInitiatorMemberEntry 6 }

cucsSwZoneInitiatorMemberPeerDn OBJECT-TYPE
    SYNTAX       SnmpAdminString
    MAX-ACCESS   read-only
    STATUS       current
    DESCRIPTION
        "Cisco UCS sw:ZoneInitiatorMember:peerDn managed object property"
    ::= { cucsSwZoneInitiatorMemberEntry 7 }

cucsSwZoneInitiatorMemberWwpn OBJECT-TYPE
    SYNTAX       Unsigned64
    MAX-ACCESS   read-only
    STATUS       current
    DESCRIPTION
        "Cisco UCS sw:ZoneInitiatorMember:wwpn managed object property"
    ::= { cucsSwZoneInitiatorMemberEntry 8 }

cucsSwZoneTargetMemberTable OBJECT-TYPE
    SYNTAX           SEQUENCE OF CucsSwZoneTargetMemberEntry
    MAX-ACCESS       not-accessible
    STATUS           current
    DESCRIPTION
        "Cisco UCS sw:ZoneTargetMember managed object table"
    ::= { cucsSwObjects 68 }

cucsSwZoneTargetMemberEntry OBJECT-TYPE
    SYNTAX           CucsSwZoneTargetMemberEntry
    MAX-ACCESS       not-accessible
    STATUS           current
    DESCRIPTION
        "Entry for the cucsSwZoneTargetMemberTable table."
    INDEX { cucsSwZoneTargetMemberInstanceId }
    ::= { cucsSwZoneTargetMemberTable 1 }

CucsSwZoneTargetMemberEntry ::= SEQUENCE {
    cucsSwZoneTargetMemberInstanceId                                 CucsManagedObjectId,
    cucsSwZoneTargetMemberDn                                         CucsManagedObjectDn,
    cucsSwZoneTargetMemberRn                                         SnmpAdminString,
    cucsSwZoneTargetMemberEpDn                                       SnmpAdminString,
    cucsSwZoneTargetMemberLc                                         CucsSwFcZoneMemberLc,
    cucsSwZoneTargetMemberName                                       SnmpAdminString,
    cucsSwZoneTargetMemberPeerDn                                     SnmpAdminString,
    cucsSwZoneTargetMemberWwpn                                       Unsigned64
}

cucsSwZoneTargetMemberInstanceId OBJECT-TYPE
    SYNTAX       CucsManagedObjectId
    MAX-ACCESS   not-accessible
    STATUS       current
    DESCRIPTION
        "Instance identifier of the managed object."
    ::= { cucsSwZoneTargetMemberEntry 1 }

cucsSwZoneTargetMemberDn OBJECT-TYPE
    SYNTAX       CucsManagedObjectDn
    MAX-ACCESS   read-only
    STATUS       current
    DESCRIPTION
        "Cisco UCS sw:ZoneTargetMember:dn managed object property"
    ::= { cucsSwZoneTargetMemberEntry 2 }

cucsSwZoneTargetMemberRn OBJECT-TYPE
    SYNTAX       SnmpAdminString
    MAX-ACCESS   read-only
    STATUS       current
    DESCRIPTION
        "Cisco UCS sw:ZoneTargetMember:rn managed object property"
    ::= { cucsSwZoneTargetMemberEntry 3 }

cucsSwZoneTargetMemberEpDn OBJECT-TYPE
    SYNTAX       SnmpAdminString
    MAX-ACCESS   read-only
    STATUS       current
    DESCRIPTION
        "Cisco UCS sw:ZoneTargetMember:epDn managed object property"
    ::= { cucsSwZoneTargetMemberEntry 4 }

cucsSwZoneTargetMemberLc OBJECT-TYPE
    SYNTAX       CucsSwFcZoneMemberLc
    MAX-ACCESS   read-only
    STATUS       current
    DESCRIPTION
        "Cisco UCS sw:ZoneTargetMember:lc managed object property"
    ::= { cucsSwZoneTargetMemberEntry 5 }

cucsSwZoneTargetMemberName OBJECT-TYPE
    SYNTAX       SnmpAdminString
    MAX-ACCESS   read-only
    STATUS       current
    DESCRIPTION
        "Cisco UCS sw:ZoneTargetMember:name managed object property"
    ::= { cucsSwZoneTargetMemberEntry 6 }

cucsSwZoneTargetMemberPeerDn OBJECT-TYPE
    SYNTAX       SnmpAdminString
    MAX-ACCESS   read-only
    STATUS       current
    DESCRIPTION
        "Cisco UCS sw:ZoneTargetMember:peerDn managed object property"
    ::= { cucsSwZoneTargetMemberEntry 7 }

cucsSwZoneTargetMemberWwpn OBJECT-TYPE
    SYNTAX       Unsigned64
    MAX-ACCESS   read-only
    STATUS       current
    DESCRIPTION
        "Cisco UCS sw:ZoneTargetMember:wwpn managed object property"
    ::= { cucsSwZoneTargetMemberEntry 8 }

END
