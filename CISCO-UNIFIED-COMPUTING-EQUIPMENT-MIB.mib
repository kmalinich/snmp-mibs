-- *********************************************************************
-- CISCO-UNIFIED-COMPUTING-EQUIPMENT-MIB.my
--
-- MIB representation of the Cisco Unified Computing System
-- EQUIPMENT management information model package
--
-- Created July 2018 by Charles Bullis
--
-- Copyright (c) 2005-2018 Cisco Systems, Inc. All rights reserved.
--
-- *********************************************************************

CISCO-UNIFIED-COMPUTING-EQUIPMENT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAdaptorReachability,
    CucsComputeCheckPoint,
    CucsComputeInventoryStatus,
    CucsComputeLinkAggregationCap,
    CucsComputeMemoryUnitConstraintType,
    CucsConditionRemoteInvRslt,
    CucsConditionSeverity,
    CucsEquipmentActiveStatus,
    CucsEquipmentAdminActionType,
    CucsEquipmentAdminPowerState,
    CucsEquipmentAirflowDirection,
    CucsEquipmentApply,
    CucsEquipmentAsicType,
    CucsEquipmentAssignment,
    CucsEquipmentAssociation,
    CucsEquipmentAvailability,
    CucsEquipmentBeaconLedFsmCurrentFsm,
    CucsEquipmentBeaconLedFsmStageName,
    CucsEquipmentBeaconLedFsmTaskItem,
    CucsEquipmentBeaconLedState,
    CucsEquipmentBiosTokenType,
    CucsEquipmentBiosUpdateMethod,
    CucsEquipmentBoardAggregationRole,
    CucsEquipmentBootDeviceType,
    CucsEquipmentCType,
    CucsEquipmentChassisAdminState,
    CucsEquipmentChassisAssocState,
    CucsEquipmentChassisConfigIssues,
    CucsEquipmentChassisConfigProgressIndicator,
    CucsEquipmentChassisConfigState,
    CucsEquipmentChassisFsmCurrentFsm,
    CucsEquipmentChassisFsmStageName,
    CucsEquipmentChassisFsmTaskFlags,
    CucsEquipmentChassisFsmTaskItem,
    CucsEquipmentChassisId,
    CucsEquipmentChassisIssues,
    CucsEquipmentChassisPowerOperState,
    CucsEquipmentChassisProfileBindingOperState,
    CucsEquipmentChassisProfileConfigState,
    CucsEquipmentChassisProfileFsmCurrentFsm,
    CucsEquipmentChassisProfileFsmStageName,
    CucsEquipmentChassisProfileFsmTaskFlags,
    CucsEquipmentChassisProfileFsmTaskItem,
    CucsEquipmentChassisProfileOperState,
    CucsEquipmentChassisQualMaxId,
    CucsEquipmentChassisQualMinId,
    CucsEquipmentChassisStatsHistThresholded,
    CucsEquipmentChassisStatsThresholded,
    CucsEquipmentCommStatus,
    CucsEquipmentConfigState,
    CucsEquipmentConfigWarnings,
    CucsEquipmentConnectionStatus,
    CucsEquipmentContType,
    CucsEquipmentControllerDefType,
    CucsEquipmentControllerSubType,
    CucsEquipmentDeviceType,
    CucsEquipmentDiscovery,
    CucsEquipmentDiscoveryCapOperPowerRequirement,
    CucsEquipmentDiscoveryState,
    CucsEquipmentDriveSecCapIsSupported,
    CucsEquipmentEnabledStatus,
    CucsEquipmentEvacState,
    CucsEquipmentFanId,
    CucsEquipmentFanModule,
    CucsEquipmentFanModuleId,
    CucsEquipmentFanModuleStatsHistThresholded,
    CucsEquipmentFanModuleStatsThresholded,
    CucsEquipmentFanModuleTray,
    CucsEquipmentFanStatsHistThresholded,
    CucsEquipmentFanStatsThresholded,
    CucsEquipmentFanTray,
    CucsEquipmentFexCapProviderRole,
    CucsEquipmentFexEnvStatsHistThresholded,
    CucsEquipmentFexEnvStatsThresholded,
    CucsEquipmentFexFsmCurrentFsm,
    CucsEquipmentFexFsmStageName,
    CucsEquipmentFexFsmTaskItem,
    CucsEquipmentFexId,
    CucsEquipmentFexPowerSummaryHistThresholded,
    CucsEquipmentFexPowerSummaryThresholded,
    CucsEquipmentFexPsuInputStatsHistThresholded,
    CucsEquipmentFexPsuInputStatsThresholded,
    CucsEquipmentFexSystemStatsHistThresholded,
    CucsEquipmentFexSystemStatsThresholded,
    CucsEquipmentHealthLedState,
    CucsEquipmentHostMgmtControllerCapCommMethod,
    CucsEquipmentHwType,
    CucsEquipmentHxCapIsSedSupported,
    CucsEquipmentHxCapIsUsbNicSupported,
    CucsEquipmentIOCardBaseFsmCurrentFsm,
    CucsEquipmentIOCardBaseFsmStageName,
    CucsEquipmentIOCardBaseFsmTaskFlags,
    CucsEquipmentIOCardBaseFsmTaskItem,
    CucsEquipmentIOCardFsmCurrentFsm,
    CucsEquipmentIOCardFsmStageName,
    CucsEquipmentIOCardFsmTaskItem,
    CucsEquipmentIOCardId,
    CucsEquipmentIOCardIssues,
    CucsEquipmentIOCardStatsHistThresholded,
    CucsEquipmentIOCardStatsThresholded,
    CucsEquipmentInternalFanType,
    CucsEquipmentIsSupported,
    CucsEquipmentLedColor,
    CucsEquipmentLedLocatorState,
    CucsEquipmentLedOperState,
    CucsEquipmentLocalDiskControllerDefOobControllerClassIdentifier,
    CucsEquipmentLocatorLedFsmCurrentFsm,
    CucsEquipmentLocatorLedFsmStageName,
    CucsEquipmentLocatorLedFsmTaskItem,
    CucsEquipmentMemoryUnitDiscoveryModifierAction,
    CucsEquipmentMethod,
    CucsEquipmentMmuPercent,
    CucsEquipmentNetworkElementFanStatsHistThresholded,
    CucsEquipmentNetworkElementFanStatsThresholded,
    CucsEquipmentOperability,
    CucsEquipmentOwner,
    CucsEquipmentOwnership,
    CucsEquipmentPOSTRecoverability,
    CucsEquipmentPasswordState,
    CucsEquipmentPictureType,
    CucsEquipmentPortAttribute,
    CucsEquipmentPortBitmask,
    CucsEquipmentPowerCapDefProfileMethod,
    CucsEquipmentPowerState,
    CucsEquipmentPresence,
    CucsEquipmentPsuFsmCurrentFsm,
    CucsEquipmentPsuFsmStageName,
    CucsEquipmentPsuFsmTaskFlags,
    CucsEquipmentPsuFsmTaskItem,
    CucsEquipmentPsuId,
    CucsEquipmentPsuInputSrc,
    CucsEquipmentPsuInputStatsHistThresholded,
    CucsEquipmentPsuInputStatsThresholded,
    CucsEquipmentPsuOutputStatsHistThresholded,
    CucsEquipmentPsuOutputStatsThresholded,
    CucsEquipmentPsuStateQualifier,
    CucsEquipmentPsuStatsHistThresholded,
    CucsEquipmentPsuStatsThresholded,
    CucsEquipmentPsuType,
    CucsEquipmentPsuVoltageType,
    CucsEquipmentRackUnitFanStatsHistThresholded,
    CucsEquipmentRackUnitFanStatsThresholded,
    CucsEquipmentRackUnitPsuStatsHistThresholded,
    CucsEquipmentRackUnitPsuStatsThresholded,
    CucsEquipmentRemovalConditions,
    CucsEquipmentResetOn,
    CucsEquipmentResolveFromRemoteServer,
    CucsEquipmentSecureBios,
    CucsEquipmentSensorThresholdStatus,
    CucsEquipmentServerSiocConnState,
    CucsEquipmentServiceState,
    CucsEquipmentSharedIOModuleId,
    CucsEquipmentSiocRole,
    CucsEquipmentSiocTempStatsHistThresholded,
    CucsEquipmentSiocTempStatsThresholded,
    CucsEquipmentSlotArrayLocation,
    CucsEquipmentSlotArrayOrientation,
    CucsEquipmentSlotArraySelector,
    CucsEquipmentSlotSpanOrientation,
    CucsEquipmentStorageContainmentMethod,
    CucsEquipmentStorageMethod,
    CucsEquipmentSwitchIOCardFsmCurrentFsm,
    CucsEquipmentSwitchIOCardFsmStageName,
    CucsEquipmentSwitchIOCardFsmTaskItem,
    CucsEquipmentSwitchIOCardId,
    CucsEquipmentSystemIOControllerFsmCurrentFsm,
    CucsEquipmentSystemIOControllerFsmStageName,
    CucsEquipmentSystemIOControllerFsmTaskItem,
    CucsEquipmentSystemIOControllerId,
    CucsEquipmentTpmConfigSupport,
    CucsEquipmentTpmType,
    CucsEquipmentType,
    CucsEquipmentUnifiedPortAlgorithm,
    CucsEquipmentUuidFeatureCapUuidSupportMode,
    CucsEquipmentXcvrId,
    CucsEquipmentXcvrType,
    CucsFsmCompletion,
    CucsFsmFlags,
    CucsFsmFsmStageStatus,
    CucsLicenseState,
    CucsMgmtUpgradeStatus,
    CucsNetworkSide,
    CucsNetworkSwitchId,
    CucsPolicyPolicyOwner,
    CucsPoolPoolAssignmentOrder,
    CucsPortEthSpeed,
    CucsPortGroupType,
    CucsPortSpeed,
    CucsPortSpeedBitmask,
    CucsPowerFanSpeed,
    CucsStorageConfigIssues,
    CucsStorageConnectionProtocol,
    CucsStorageControllerForm,
    CucsStorageControllerMode,
    CucsStorageLocalDiskMode,
    CucsStorageTechnology
        FROM CISCO-UNIFIED-COMPUTING-TC-MIB;

cucsEquipmentObjects MODULE-IDENTITY
    LAST-UPDATED    "201807260000Z"
    ORGANIZATION    "Cisco Systems Inc."
    CONTACT-INFO
        "Cisco Systems
        Customer Service

        Postal: 170 W Tasman Drive
        San Jose, CA  95134
        USA

        Tel: +1 800 553 -NETS

        E-mail: cs-san@cisco.com, cs-lan-switch-snmp@cisco.com"
    DESCRIPTION
        "MIB representation of the Cisco Unified Computing System
        EQUIPMENT management information model package"
    ::= { ciscoUnifiedComputingMIBObjects 15 }

cucsEquipmentAdaptorConnDefTable OBJECT-TYPE
    SYNTAX           SEQUENCE OF CucsEquipmentAdaptorConnDefEntry
    MAX-ACCESS       not-accessible
    STATUS           current
    DESCRIPTION
        "Cisco UCS equipment:AdaptorConnDef managed object table"
    ::= { cucsEquipmentObjects 95 }

cucsEquipmentAdaptorConnDefEntry OBJECT-TYPE
    SYNTAX           CucsEquipmentAdaptorConnDefEntry
    MAX-ACCESS       not-accessible
    STATUS           current
    DESCRIPTION
        "Entry for the cucsEquipmentAdaptorConnDefTable table."
    INDEX { cucsEquipmentAdaptorConnDefInstanceId }
    ::= { cucsEquipmentAdaptorConnDefTable 1 }

CucsEquipmentAdaptorConnDefEntry ::= SEQUENCE {
    cucsEquipmentAdaptorConnDefInstanceId                            CucsManagedObjectId,
    cucsEquipmentAdaptorConnDefDn                                    CucsManagedObjectDn,
    cucsEquipmentAdaptorConnDefRn                                    SnmpAdminString,
    cucsEquipmentAdaptorConnDefAdaptorEp                             Gauge32,
    cucsEquipmentAdaptorConnDefDescr                                 SnmpAdminString,
    cucsEquipmentAdaptorConnDefIntId                                 SnmpAdminString,
    cucsEquipmentAdaptorConnDefIomEp                                 Gauge32,
    cucsEquipmentAdaptorConnDefName                                  SnmpAdminString,
    cucsEquipmentAdaptorConnDefPolicyLevel                           Gauge32,
    cucsEquipmentAdaptorConnDefPolicyOwner                           CucsPolicyPolicyOwner
}

cucsEquipmentAdaptorConnDefInstanceId OBJECT-TYPE
    SYNTAX       CucsManagedObjectId
    MAX-ACCESS   not-accessible
    STATUS       current
    DESCRIPTION
        "Instance identifier of the managed object."
    ::= { cucsEquipmentAdaptorConnDefEntry 1 }

cucsEquipmentAdaptorConnDefDn OBJECT-TYPE
    SYNTAX       CucsManagedObjectDn
    MAX-ACCESS   read-only
    STATUS       current
    DESCRIPTION
        "Cisco UCS equipment:AdaptorConnDef:dn managed object property"
    ::= { cucsEquipmentAdaptorConnDefEntry 2 }

cucsEquipmentAdaptorConnDefRn OBJECT-TYPE
    SYNTAX       SnmpAdminString
    MAX-ACCESS   read-only
    STATUS       current
    DESCRIPTION
        "Cisco UCS equipment:AdaptorConnDef:rn managed object property"
    ::= { cucsEquipmentAdaptorConnDefEntry 3 }

cucsEquipmentAdaptorConnDefAdaptorEp OBJECT-TYPE
    SYNTAX       Gauge32
    MAX-ACCESS   read-only
    STATUS       current
    DESCRIPTION
        "Cisco UCS equipment:AdaptorConnDef:adaptorEp managed
        object property"
    ::= { cucsEquipmentAdaptorConnDefEntry 4 }

cucsEquipmentAdaptorConnDefDescr OBJECT-TYPE
    SYNTAX       SnmpAdminString
    MAX-ACCESS   read-only
    STATUS       current
    DESCRIPTION
        "Cisco UCS equipment:AdaptorConnDef:descr managed object property"
    ::= { cucsEquipmentAdaptorConnDefEntry 5 }

cucsEquipmentAdaptorConnDefIntId OBJECT-TYPE
    SYNTAX       SnmpAdminString
    MAX-ACCESS   read-only
    STATUS       current
    DESCRIPTION
        "Cisco UCS equipment:AdaptorConnDef:intId managed object property"
    ::= { cucsEquipmentAdaptorConnDefEntry 6 }

cucsEquipmentAdaptorConnDefIomEp OBJECT-TYPE
    SYNTAX       Gauge32
    MAX-ACCESS   read-only
    STATUS       current
    DESCRIPTION
        "Cisco UCS equipment:AdaptorConnDef:iomEp managed object property"
    ::= { cucsEquipmentAdaptorConnDefEntry 7 }

cucsEquipmentAdaptorConnDefName OBJECT-TYPE
    SYNTAX       SnmpAdminString
    MAX-ACCESS   read-only
    STATUS       current
    DESCRIPTION
        "Cisco UCS equipment:AdaptorConnDef:name managed object property"
    ::= { cucsEquipmentAdaptorConnDefEntry 8 }

cucsEquipmentAdaptorConnDefPolicyLevel OBJECT-TYPE
    SYNTAX       Gauge32
    MAX-ACCESS   read-only
    STATUS       current
    DESCRIPTION
        "Cisco UCS equipment:AdaptorConnDef:policyLevel
        managed object property"
    ::= { cucsEquipmentAdaptorConnDefEntry 9 }

cucsEquipmentAdaptorConnDefPolicyOwner OBJECT-TYPE
    SYNTAX       CucsPolicyPolicyOwner
    MAX-ACCESS   read-only
    STATUS       current
    DESCRIPTION
        "Cisco UCS equipment:AdaptorConnDef:policyOwner
        managed object property"
    ::= { cucsEquipmentAdaptorConnDefEntry 10 }

cucsEquipmentAdaptorDefTable OBJECT-TYPE
    SYNTAX           SEQUENCE OF CucsEquipmentAdaptorDefEntry
    MAX-ACCESS       not-accessible
    STATUS           current
    DESCRIPTION
        "Cisco UCS equipment:AdaptorDef managed object table"
    ::= { cucsEquipmentObjects 1 }

cucsEquipmentAdaptorDefEntry OBJECT-TYPE
    SYNTAX           CucsEquipmentAdaptorDefEntry
    MAX-ACCESS       not-accessible
    STATUS           current
    DESCRIPTION
        "Entry for the cucsEquipmentAdaptorDefTable table."
    INDEX { cucsEquipmentAdaptorDefInstanceId }
    ::= { cucsEquipmentAdaptorDefTable 1 }

CucsEquipmentAdaptorDefEntry ::= SEQUENCE {
    cucsEquipmentAdaptorDefInstanceId                                CucsManagedObjectId,
    cucsEquipmentAdaptorDefDn                                        CucsManagedObjectDn,
    cucsEquipmentAdaptorDefRn                                        SnmpAdminString,
    cucsEquipmentAdaptorDefDescr                                     SnmpAdminString,
    cucsEquipmentAdaptorDefEthernetPortSpeed                         Unsigned64,
    cucsEquipmentAdaptorDefFibreChannelPortSpeed                     Unsigned64,
    cucsEquipmentAdaptorDefIntId                                     SnmpAdminString,
    cucsEquipmentAdaptorDefName                                      SnmpAdminString,
    cucsEquipmentAdaptorDefPolicyLevel                               Gauge32,
    cucsEquipmentAdaptorDefPolicyOwner                               CucsPolicyPolicyOwner,
    cucsEquipmentAdaptorDefForceUpdateVersion                        TruthValue
}

cucsEquipmentAdaptorDefInstanceId OBJECT-TYPE
    SYNTAX       CucsManagedObjectId
    MAX-ACCESS   not-accessible
    STATUS       current
    DESCRIPTION
        "Instance identifier of the managed object."
    ::= { cucsEquipmentAdaptorDefEntry 1 }

cucsEquipmentAdaptorDefDn OBJECT-TYPE
    SYNTAX       CucsManagedObjectDn
    MAX-ACCESS   read-only
    STATUS       current
    DESCRIPTION
        "Cisco UCS equipment:AdaptorDef:dn managed object property"
    ::= { cucsEquipmentAdaptorDefEntry 2 }

cucsEquipmentAdaptorDefRn OBJECT-TYPE
    SYNTAX       SnmpAdminString
    MAX-ACCESS   read-only
    STATUS       current
    DESCRIPTION
        "Cisco UCS equipment:AdaptorDef:rn managed object property"
    ::= { cucsEquipmentAdaptorDefEntry 3 }

cucsEquipmentAdaptorDefDescr OBJECT-TYPE
    SYNTAX       SnmpAdminString
    MAX-ACCESS   read-only
    STATUS       current
    DESCRIPTION
        "Cisco UCS equipment:AdaptorDef:descr managed object property"
    ::= { cucsEquipmentAdaptorDefEntry 4 }

cucsEquipmentAdaptorDefEthernetPortSpeed OBJECT-TYPE
    SYNTAX       Unsigned64
    MAX-ACCESS   read-only
    STATUS       current
    DESCRIPTION
        "Cisco UCS equipment:AdaptorDef:ethernetPortSpeed
        managed object property"
    ::= { cucsEquipmentAdaptorDefEntry 5 }

cucsEquipmentAdaptorDefFibreChannelPortSpeed OBJECT-TYPE
    SYNTAX       Unsigned64
    MAX-ACCESS   read-only
    STATUS       current
    DESCRIPTION
        "Cisco UCS equipment:AdaptorDef:fibreChannelPortSpeed
        managed object property"
    ::= { cucsEquipmentAdaptorDefEntry 6 }

cucsEquipmentAdaptorDefIntId OBJECT-TYPE
    SYNTAX       SnmpAdminString
    MAX-ACCESS   read-only
    STATUS       current
    DESCRIPTION
        "Cisco UCS equipment:AdaptorDef:intId managed object property"
    ::= { cucsEquipmentAdaptorDefEntry 7 }

cucsEquipmentAdaptorDefName OBJECT-TYPE
    SYNTAX       SnmpAdminString
    MAX-ACCESS   read-only
    STATUS       current
    DESCRIPTION
        "Cisco UCS equipment:AdaptorDef:name managed object property"
    ::= { cucsEquipmentAdaptorDefEntry 8 }

cucsEquipmentAdaptorDefPolicyLevel OBJECT-TYPE
    SYNTAX       Gauge32
    MAX-ACCESS   read-only
    STATUS       current
    DESCRIPTION
        "Cisco UCS equipment:AdaptorDef:policyLevel managed
        object property"
    ::= { cucsEquipmentAdaptorDefEntry 9 }

cucsEquipmentAdaptorDefPolicyOwner OBJECT-TYPE
    SYNTAX       CucsPolicyPolicyOwner
    MAX-ACCESS   read-only
    STATUS       current
    DESCRIPTION
        "Cisco UCS equipment:AdaptorDef:policyOwner managed
        object property"
    ::= { cucsEquipmentAdaptorDefEntry 10 }

cucsEquipmentAdaptorDefForceUpdateVersion OBJECT-TYPE
    SYNTAX       TruthValue
    MAX-ACCESS   read-only
    STATUS       current
    DESCRIPTION
        "Cisco UCS equipment:AdaptorDef:forceUpdateVersion
        managed object property"
    ::= { cucsEquipmentAdaptorDefEntry 11 }

cucsEquipmentAdvancedBootOrderTable OBJECT-TYPE
    SYNTAX           SEQUENCE OF CucsEquipmentAdvancedBootOrderEntry
    MAX-ACCESS       not-accessible
    STATUS           current
    DESCRIPTION
        "Cisco UCS equipment:AdvancedBootOrder managed object table"
    ::= { cucsEquipmentObjects 120 }

cucsEquipmentAdvancedBootOrderEntry OBJECT-TYPE
    SYNTAX           CucsEquipmentAdvancedBootOrderEntry
    MAX-ACCESS       not-accessible
    STATUS           current
    DESCRIPTION
        "Entry for the cucsEquipmentAdvancedBootOrderTable table."
    INDEX { cucsEquipmentAdvancedBootOrderInstanceId }
    ::= { cucsEquipmentAdvancedBootOrderTable 1 }

CucsEquipmentAdvancedBootOrderEntry ::= SEQUENCE {
    cucsEquipmentAdvancedBootOrderInstanceId                         CucsManagedObjectId,
    cucsEquipmentAdvancedBootOrderDn                                 CucsManagedObjectDn,
    cucsEquipmentAdvancedBootOrderRn                                 SnmpAdminString,
    cucsEquipmentAdvancedBootOrderIsSupported                        TruthValue,
    cucsEquipmentAdvancedBootOrderMinBiosVersion                     SnmpAdminString,
    cucsEquipmentAdvancedBootOrderMinCimcVersion                     SnmpAdminString,
    cucsEquipmentAdvancedBootOrderDescr                              SnmpAdminString,
    cucsEquipmentAdvancedBootOrderIntId                              SnmpAdminString,
    cucsEquipmentAdvancedBootOrderName                               SnmpAdminString,
    cucsEquipmentAdvancedBootOrderPolicyLevel                        Gauge32,
    cucsEquipmentAdvancedBootOrderPolicyOwner                        CucsPolicyPolicyOwner
}

cucsEquipmentAdvancedBootOrderInstanceId OBJECT-TYPE
    SYNTAX       CucsManagedObjectId
    MAX-ACCESS   not-accessible
    STATUS       current
    DESCRIPTION
        "Instance identifier of the managed object."
    ::= { cucsEquipmentAdvancedBootOrderEntry 1 }

cucsEquipmentAdvancedBootOrderDn OBJECT-TYPE
    SYNTAX       CucsManagedObjectDn
    MAX-ACCESS   read-only
    STATUS       current
    DESCRIPTION
        "Cisco UCS equipment:AdvancedBootOrder:dn managed object property"
    ::= { cucsEquipmentAdvancedBootOrderEntry 2 }

cucsEquipmentAdvancedBootOrderRn OBJECT-TYPE
    SYNTAX       SnmpAdminString
    MAX-ACCESS   read-only
    STATUS       current
    DESCRIPTION
        "Cisco UCS equipment:AdvancedBootOrder:rn managed object property"
    ::= { cucsEquipmentAdvancedBootOrderEntry 3 }

cucsEquipmentAdvancedBootOrderIsSupported OBJECT-TYPE
    SYNTAX       TruthValue
    MAX-ACCESS   read-only
    STATUS       current
    DESCRIPTION
        "Cisco UCS equipment:AdvancedBootOrder:isSupported
        managed object property"
    ::= { cucsEquipmentAdvancedBootOrderEntry 4 }

cucsEquipmentAdvancedBootOrderMinBiosVersion OBJECT-TYPE
    SYNTAX       SnmpAdminString
    MAX-ACCESS   read-only
    STATUS       current
    DESCRIPTION
        "Cisco UCS equipment:AdvancedBootOrder:minBiosVersion
        managed object property"
    ::= { cucsEquipmentAdvancedBootOrderEntry 5 }

cucsEquipmentAdvancedBootOrderMinCimcVersion OBJECT-TYPE
    SYNTAX       SnmpAdminString
    MAX-ACCESS   read-only
    STATUS       current
    DESCRIPTION
        "Cisco UCS equipment:AdvancedBootOrder:minCimcVersion
        managed object property"
    ::= { cucsEquipmentAdvancedBootOrderEntry 6 }

cucsEquipmentAdvancedBootOrderDescr OBJECT-TYPE
    SYNTAX       SnmpAdminString
    MAX-ACCESS   read-only
    STATUS       current
    DESCRIPTION
        "Cisco UCS equipment:AdvancedBootOrder:descr managed
        object property"
    ::= { cucsEquipmentAdvancedBootOrderEntry 7 }

cucsEquipmentAdvancedBootOrderIntId OBJECT-TYPE
    SYNTAX       SnmpAdminString
    MAX-ACCESS   read-only
    STATUS       current
    DESCRIPTION
        "Cisco UCS equipment:AdvancedBootOrder:intId managed
        object property"
    ::= { cucsEquipmentAdvancedBootOrderEntry 8 }

cucsEquipmentAdvancedBootOrderName OBJECT-TYPE
    SYNTAX       SnmpAdminString
    MAX-ACCESS   read-only
    STATUS       current
    DESCRIPTION
        "Cisco UCS equipment:AdvancedBootOrder:name managed
        object property"
    ::= { cucsEquipmentAdvancedBootOrderEntry 9 }

cucsEquipmentAdvancedBootOrderPolicyLevel OBJECT-TYPE
    SYNTAX       Gauge32
    MAX-ACCESS   read-only
    STATUS       current
    DESCRIPTION
        "Cisco UCS equipment:AdvancedBootOrder:policyLevel
        managed object property"
    ::= { cucsEquipmentAdvancedBootOrderEntry 10 }

cucsEquipmentAdvancedBootOrderPolicyOwner OBJECT-TYPE
    SYNTAX       CucsPolicyPolicyOwner
    MAX-ACCESS   read-only
    STATUS       current
    DESCRIPTION
        "Cisco UCS equipment:AdvancedBootOrder:policyOwner
        managed object property"
    ::= { cucsEquipmentAdvancedBootOrderEntry 11 }

cucsEquipmentAutoconfigPolicyTable OBJECT-TYPE
    SYNTAX           SEQUENCE OF CucsEquipmentAutoconfigPolicyEntry
    MAX-ACCESS       not-accessible
    STATUS           current
    DESCRIPTION
        "Cisco UCS equipment:AutoconfigPolicy managed object table"
    ::= { cucsEquipmentObjects 203 }

cucsEquipmentAutoconfigPolicyEntry OBJECT-TYPE
    SYNTAX           CucsEquipmentAutoconfigPolicyEntry
    MAX-ACCESS       not-accessible
    STATUS           current
    DESCRIPTION
        "Entry for the cucsEquipmentAutoconfigPolicyTable table."
    INDEX { cucsEquipmentAutoconfigPolicyInstanceId }
    ::= { cucsEquipmentAutoconfigPolicyTable 1 }

CucsEquipmentAutoconfigPolicyEntry ::= SEQUENCE {
    cucsEquipmentAutoconfigPolicyInstanceId                          CucsManagedObjectId,
    cucsEquipmentAutoconfigPolicyDn                                  CucsManagedObjectDn,
    cucsEquipmentAutoconfigPolicyRn                                  SnmpAdminString,
    cucsEquipmentAutoconfigPolicyDescr                               SnmpAdminString,
    cucsEquipmentAutoconfigPolicyDstDn                               SnmpAdminString,
    cucsEquipmentAutoconfigPolicyIntId                               SnmpAdminString,
    cucsEquipmentAutoconfigPolicyName                                SnmpAdminString,
    cucsEquipmentAutoconfigPolicyOperQualifier                       SnmpAdminString,
    cucsEquipmentAutoconfigPolicyPolicyLevel                         Gauge32,
    cucsEquipmentAutoconfigPolicyPolicyOwner                         CucsPolicyPolicyOwner,
    cucsEquipmentAutoconfigPolicyQualifier                           SnmpAdminString,
    cucsEquipmentAutoconfigPolicySrcTemplName                        SnmpAdminString
}

cucsEquipmentAutoconfigPolicyInstanceId OBJECT-TYPE
    SYNTAX       CucsManagedObjectId
    MAX-ACCESS   not-accessible
    STATUS       current
    DESCRIPTION
        "Instance identifier of the managed object."
    ::= { cucsEquipmentAutoconfigPolicyEntry 1 }

cucsEquipmentAutoconfigPolicyDn OBJECT-TYPE
    SYNTAX       CucsManagedObjectDn
    MAX-ACCESS   read-only
    STATUS       current
    DESCRIPTION
        "Cisco UCS equipment:AutoconfigPolicy:dn managed object property"
    ::= { cucsEquipmentAutoconfigPolicyEntry 2 }

cucsEquipmentAutoconfigPolicyRn OBJECT-TYPE
    SYNTAX       SnmpAdminString
    MAX-ACCESS   read-only
    STATUS       current
    DESCRIPTION
        "Cisco UCS equipment:AutoconfigPolicy:rn managed object property"
    ::= { cucsEquipmentAutoconfigPolicyEntry 3 }

cucsEquipmentAutoconfigPolicyDescr OBJECT-TYPE
    SYNTAX       SnmpAdminString
    MAX-ACCESS   read-only
    STATUS       current
    DESCRIPTION
        "Cisco UCS equipment:AutoconfigPolicy:descr managed
        object property"
    ::= { cucsEquipmentAutoconfigPolicyEntry 4 }

cucsEquipmentAutoconfigPolicyDstDn OBJECT-TYPE
    SYNTAX       SnmpAdminString
    MAX-ACCESS   read-only
    STATUS       current
    DESCRIPTION
        "Cisco UCS equipment:AutoconfigPolicy:dstDn managed
        object property"
    ::= { cucsEquipmentAutoconfigPolicyEntry 5 }

cucsEquipmentAutoconfigPolicyIntId OBJECT-TYPE
    SYNTAX       SnmpAdminString
    MAX-ACCESS   read-only
    STATUS       current
    DESCRIPTION
        "Cisco UCS equipment:AutoconfigPolicy:intId managed
        object property"
    ::= { cucsEquipmentAutoconfigPolicyEntry 6 }

cucsEquipmentAutoconfigPolicyName OBJECT-TYPE
    SYNTAX       SnmpAdminString
    MAX-ACCESS   read-only
    STATUS       current
    DESCRIPTION
        "Cisco UCS equipment:AutoconfigPolicy:name managed
        object property"
    ::= { cucsEquipmentAutoconfigPolicyEntry 7 }

cucsEquipmentAutoconfigPolicyOperQualifier OBJECT-TYPE
    SYNTAX       SnmpAdminString
    MAX-ACCESS   read-only
    STATUS       current
    DESCRIPTION
        "Cisco UCS equipment:AutoconfigPolicy:operQualifier
        managed object property"
    ::= { cucsEquipmentAutoconfigPolicyEntry 8 }

cucsEquipmentAutoconfigPolicyPolicyLevel OBJECT-TYPE
    SYNTAX       Gauge32
    MAX-ACCESS   read-only
    STATUS       current
    DESCRIPTION
        "Cisco UCS equipment:AutoconfigPolicy:policyLevel
        managed object property"
    ::= { cucsEquipmentAutoconfigPolicyEntry 9 }

cucsEquipmentAutoconfigPolicyPolicyOwner OBJECT-TYPE
    SYNTAX       CucsPolicyPolicyOwner
    MAX-ACCESS   read-only
    STATUS       current
    DESCRIPTION
        "Cisco UCS equipment:AutoconfigPolicy:policyOwner
        managed object property"
    ::= { cucsEquipmentAutoconfigPolicyEntry 10 }

cucsEquipmentAutoconfigPolicyQualifier OBJECT-TYPE
    SYNTAX       SnmpAdminString
    MAX-ACCESS   read-only
    STATUS       current
    DESCRIPTION
        "Cisco UCS equipment:AutoconfigPolicy:qualifier
        managed object property"
    ::= { cucsEquipmentAutoconfigPolicyEntry 11 }

cucsEquipmentAutoconfigPolicySrcTemplName OBJECT-TYPE
    SYNTAX       SnmpAdminString
    MAX-ACCESS   read-only
    STATUS       current
    DESCRIPTION
        "Cisco UCS equipment:AutoconfigPolicy:srcTemplName
        managed object property"
    ::= { cucsEquipmentAutoconfigPolicyEntry 12 }

cucsEquipmentBaseBoardCapProviderTable OBJECT-TYPE
    SYNTAX           SEQUENCE OF CucsEquipmentBaseBoardCapProviderEntry
    MAX-ACCESS       not-accessible
    STATUS           current
    DESCRIPTION
        "Cisco UCS equipment:BaseBoardCapProvider managed object table"
    ::= { cucsEquipmentObjects 2 }

cucsEquipmentBaseBoardCapProviderEntry OBJECT-TYPE
    SYNTAX           CucsEquipmentBaseBoardCapProviderEntry
    MAX-ACCESS       not-accessible
    STATUS           current
    DESCRIPTION
        "Entry for the cucsEquipmentBaseBoardCapProviderTable table."
    INDEX { cucsEquipmentBaseBoardCapProviderInstanceId }
    ::= { cucsEquipmentBaseBoardCapProviderTable 1 }

CucsEquipmentBaseBoardCapProviderEntry ::= SEQUENCE {
    cucsEquipmentBaseBoardCapProviderInstanceId                      CucsManagedObjectId,
    cucsEquipmentBaseBoardCapProviderDn                              CucsManagedObjectDn,
    cucsEquipmentBaseBoardCapProviderRn                              SnmpAdminString,
    cucsEquipmentBaseBoardCapProviderDeprecated                      TruthValue,
    cucsEquipmentBaseBoardCapProviderGencount                        Gauge32,
    cucsEquipmentBaseBoardCapProviderMgmtPlaneVer                    SnmpAdminString,
    cucsEquipmentBaseBoardCapProviderModel                           SnmpAdminString,
    cucsEquipmentBaseBoardCapProviderRevision                        SnmpAdminString,
    cucsEquipmentBaseBoardCapProviderVendor                          SnmpAdminString,
    cucsEquipmentBaseBoardCapProviderPromCardType                    Gauge32,
    cucsEquipmentBaseBoardCapProviderDeleted                         TruthValue,
    cucsEquipmentBaseBoardCapProviderElementLoadFailures             Gauge32,
    cucsEquipmentBaseBoardCapProviderElementsLoaded                  Gauge32,
    cucsEquipmentBaseBoardCapProviderLoadErrors                      Gauge32,
    cucsEquipmentBaseBoardCapProviderLoadWarnings                    Gauge32
}

cucsEquipmentBaseBoardCapProviderInstanceId OBJECT-TYPE
    SYNTAX       CucsManagedObjectId
    MAX-ACCESS   not-accessible
    STATUS       current
    DESCRIPTION
        "Instance identifier of the managed object."
    ::= { cucsEquipmentBaseBoardCapProviderEntry 1 }

cucsEquipmentBaseBoardCapProviderDn OBJECT-TYPE
    SYNTAX       CucsManagedObjectDn
    MAX-ACCESS   read-only
    STATUS       current
    DESCRIPTION
        "Cisco UCS equipment:BaseBoardCapProvider:dn managed
        object property"
    ::= { cucsEquipmentBaseBoardCapProviderEntry 2 }

cucsEquipmentBaseBoardCapProviderRn OBJECT-TYPE
    SYNTAX       SnmpAdminString
    MAX-ACCESS   read-only
    STATUS       current
    DESCRIPTION
        "Cisco UCS equipment:BaseBoardCapProvider:rn managed
        object property"
    ::= { cucsEquipmentBaseBoardCapProviderEntry 3 }

cucsEquipmentBaseBoardCapProviderDeprecated OBJECT-TYPE
    SYNTAX       TruthValue
    MAX-ACCESS   read-only
    STATUS       current
    DESCRIPTION
        "Cisco UCS equipment:BaseBoardCapProvider:deprecated
        managed object property"
    ::= { cucsEquipmentBaseBoardCapProviderEntry 4 }

cucsEquipmentBaseBoardCapProviderGencount OBJECT-TYPE
    SYNTAX       Gauge32
    MAX-ACCESS   read-only
    STATUS       current
    DESCRIPTION
        "Cisco UCS equipment:BaseBoardCapProvider:gencount
        managed object property"
    ::= { cucsEquipmentBaseBoardCapProviderEntry 5 }

cucsEquipmentBaseBoardCapProviderMgmtPlaneVer OBJECT-TYPE
    SYNTAX       SnmpAdminString
    MAX-ACCESS   read-only
    STATUS       current
    DESCRIPTION
        "Cisco UCS equipment:BaseBoardCapProvider:mgmtPlaneVer
        managed object property"
    ::= { cucsEquipmentBaseBoardCapProviderEntry 6 }

cucsEquipmentBaseBoardCapProviderModel OBJECT-TYPE
    SYNTAX       SnmpAdminString
    MAX-ACCESS   read-only
    STATUS       current
    DESCRIPTION
        "Cisco UCS equipment:BaseBoardCapProvider:model
        managed object property"
    ::= { cucsEquipmentBaseBoardCapProviderEntry 7 }

cucsEquipmentBaseBoardCapProviderRevision OBJECT-TYPE
    SYNTAX       SnmpAdminString
    MAX-ACCESS   read-only
    STATUS       current
    DESCRIPTION
        "Cisco UCS equipment:BaseBoardCapProvider:revision
        managed object property"
    ::= { cucsEquipmentBaseBoardCapProviderEntry 8 }

cucsEquipmentBaseBoardCapProviderVendor OBJECT-TYPE
    SYNTAX       SnmpAdminString
    MAX-ACCESS   read-only
    STATUS       current
    DESCRIPTION
        "Cisco UCS equipment:BaseBoardCapProvider:vendor
        managed object property"
    ::= { cucsEquipmentBaseBoardCapProviderEntry 9 }

cucsEquipmentBaseBoardCapProviderPromCardType OBJECT-TYPE
    SYNTAX       Gauge32
    MAX-ACCESS   read-only
    STATUS       current
    DESCRIPTION
        "Cisco UCS equipment:BaseBoardCapProvider:promCardType
        managed object property"
    ::= { cucsEquipmentBaseBoardCapProviderEntry 10 }

cucsEquipmentBaseBoardCapProviderDeleted OBJECT-TYPE
    SYNTAX       TruthValue
    MAX-ACCESS   read-only
    STATUS       current
    DESCRIPTION
        "Cisco UCS equipment:BaseBoardCapProvider:deleted
        managed object property"
    ::= { cucsEquipmentBaseBoardCapProviderEntry 11 }

cucsEquipmentBaseBoardCapProviderElementLoadFailures OBJECT-TYPE
    SYNTAX       Gauge32
    MAX-ACCESS   read-only
    STATUS       current
    DESCRIPTION
        "Cisco UCS equipment:BaseBoardCapProvider:elementLoadFailures
        managed object property"
    ::= { cucsEquipmentBaseBoardCapProviderEntry 12 }

cucsEquipmentBaseBoardCapProviderElementsLoaded OBJECT-TYPE
    SYNTAX       Gauge32
    MAX-ACCESS   read-only
    STATUS       current
    DESCRIPTION
        "Cisco UCS equipment:BaseBoardCapProvider:elementsLoaded
        managed object property"
    ::= { cucsEquipmentBaseBoardCapProviderEntry 13 }

cucsEquipmentBaseBoardCapProviderLoadErrors OBJECT-TYPE
    SYNTAX       Gauge32
    MAX-ACCESS   read-only
    STATUS       current
    DESCRIPTION
        "Cisco UCS equipment:BaseBoardCapProvider:loadErrors
        managed object property"
    ::= { cucsEquipmentBaseBoardCapProviderEntry 14 }

cucsEquipmentBaseBoardCapProviderLoadWarnings OBJECT-TYPE
    SYNTAX       Gauge32
    MAX-ACCESS   read-only
    STATUS       current
    DESCRIPTION
        "Cisco UCS equipment:BaseBoardCapProvider:loadWarnings
        managed object property"
    ::= { cucsEquipmentBaseBoardCapProviderEntry 15 }

cucsEquipmentBeaconCapProviderTable OBJECT-TYPE
    SYNTAX           SEQUENCE OF CucsEquipmentBeaconCapProviderEntry
    MAX-ACCESS       not-accessible
    STATUS           current
    DESCRIPTION
        "Cisco UCS equipment:BeaconCapProvider managed object table"
    ::= { cucsEquipmentObjects 81 }

cucsEquipmentBeaconCapProviderEntry OBJECT-TYPE
    SYNTAX           CucsEquipmentBeaconCapProviderEntry
    MAX-ACCESS       not-accessible
    STATUS           current
    DESCRIPTION
        "Entry for the cucsEquipmentBeaconCapProviderTable table."
    INDEX { cucsEquipmentBeaconCapProviderInstanceId }
    ::= { cucsEquipmentBeaconCapProviderTable 1 }

CucsEquipmentBeaconCapProviderEntry ::= SEQUENCE {
    cucsEquipmentBeaconCapProviderInstanceId                         CucsManagedObjectId,
    cucsEquipmentBeaconCapProviderDn                                 CucsManagedObjectDn,
    cucsEquipmentBeaconCapProviderRn                                 SnmpAdminString,
    cucsEquipmentBeaconCapProviderDescr                              SnmpAdminString,
    cucsEquipmentBeaconCapProviderIntId                              SnmpAdminString,
    cucsEquipmentBeaconCapProviderName                               SnmpAdminString,
    cucsEquipmentBeaconCapProviderPortModeBeacon                     TruthValue,
    cucsEquipmentBeaconCapProviderPolicyLevel                        Gauge32,
    cucsEquipmentBeaconCapProviderPolicyOwner                        CucsPolicyPolicyOwner
}

cucsEquipmentBeaconCapProviderInstanceId OBJECT-TYPE
    SYNTAX       CucsManagedObjectId
    MAX-ACCESS   not-accessible
    STATUS       current
    DESCRIPTION
        "Instance identifier of the managed object."
    ::= { cucsEquipmentBeaconCapProviderEntry 1 }

cucsEquipmentBeaconCapProviderDn OBJECT-TYPE
    SYNTAX       CucsManagedObjectDn
    MAX-ACCESS   read-only
    STATUS       current
    DESCRIPTION
        "Cisco UCS equipment:BeaconCapProvider:dn managed object property"
    ::= { cucsEquipmentBeaconCapProviderEntry 2 }

cucsEquipmentBeaconCapProviderRn OBJECT-TYPE
    SYNTAX       SnmpAdminString
    MAX-ACCESS   read-only
    STATUS       current
    DESCRIPTION
        "Cisco UCS equipment:BeaconCapProvider:rn managed object property"
    ::= { cucsEquipmentBeaconCapProviderEntry 3 }

cucsEquipmentBeaconCapProviderDescr OBJECT-TYPE
    SYNTAX       SnmpAdminString
    MAX-ACCESS   read-only
    STATUS       current
    DESCRIPTION
        "Cisco UCS equipment:BeaconCapProvider:descr managed
        object property"
    ::= { cucsEquipmentBeaconCapProviderEntry 4 }

cucsEquipmentBeaconCapProviderIntId OBJECT-TYPE
    SYNTAX       SnmpAdminString
    MAX-ACCESS   read-only
    STATUS       current
    DESCRIPTION
        "Cisco UCS equipment:BeaconCapProvider:intId managed
        object property"
    ::= { cucsEquipmentBeaconCapProviderEntry 5 }

cucsEquipmentBeaconCapProviderName OBJECT-TYPE
    SYNTAX       SnmpAdminString
    MAX-ACCESS   read-only
    STATUS       current
    DESCRIPTION
        "Cisco UCS equipment:BeaconCapProvider:name managed
        object property"
    ::= { cucsEquipmentBeaconCapProviderEntry 6 }

cucsEquipmentBeaconCapProviderPortModeBeacon OBJECT-TYPE
    SYNTAX       TruthValue
    MAX-ACCESS   read-only
    STATUS       current
    DESCRIPTION
        "Cisco UCS equipment:BeaconCapProvider:portModeBeacon
        managed object property"
    ::= { cucsEquipmentBeaconCapProviderEntry 7 }

cucsEquipmentBeaconCapProviderPolicyLevel OBJECT-TYPE
    SYNTAX       Gauge32
    MAX-ACCESS   read-only
    STATUS       current
    DESCRIPTION
        "Cisco UCS equipment:BeaconCapProvider:policyLevel
        managed object property"
    ::= { cucsEquipmentBeaconCapProviderEntry 8 }

cucsEquipmentBeaconCapProviderPolicyOwner OBJECT-TYPE
    SYNTAX       CucsPolicyPolicyOwner
    MAX-ACCESS   read-only
    STATUS       current
    DESCRIPTION
        "Cisco UCS equipment:BeaconCapProvider:policyOwner
        managed object property"
    ::= { cucsEquipmentBeaconCapProviderEntry 9 }

cucsEquipmentBeaconLedTable OBJECT-TYPE
    SYNTAX           SEQUENCE OF CucsEquipmentBeaconLedEntry
    MAX-ACCESS       not-accessible
    STATUS           current
    DESCRIPTION
        "Cisco UCS equipment:BeaconLed managed object table"
    ::= { cucsEquipmentObjects 82 }

cucsEquipmentBeaconLedEntry OBJECT-TYPE
    SYNTAX           CucsEquipmentBeaconLedEntry
    MAX-ACCESS       not-accessible
    STATUS           current
    DESCRIPTION
        "Entry for the cucsEquipmentBeaconLedTable table."
    INDEX { cucsEquipmentBeaconLedInstanceId }
    ::= { cucsEquipmentBeaconLedTable 1 }

CucsEquipmentBeaconLedEntry ::= SEQUENCE {
    cucsEquipmentBeaconLedInstanceId                                 CucsManagedObjectId,
    cucsEquipmentBeaconLedDn                                         CucsManagedObjectDn,
    cucsEquipmentBeaconLedRn                                         SnmpAdminString,
    cucsEquipmentBeaconLedAdminState                                 CucsEquipmentBeaconLedState,
    cucsEquipmentBeaconLedColor                                      CucsEquipmentLedColor,
    cucsEquipmentBeaconLedFsmDescr                                   SnmpAdminString,
    cucsEquipmentBeaconLedFsmPrev                                    SnmpAdminString,
    cucsEquipmentBeaconLedFsmProgr                                   Gauge32,
    cucsEquipmentBeaconLedFsmRmtInvErrCode                           Gauge32,
    cucsEquipmentBeaconLedFsmRmtInvErrDescr                          SnmpAdminString,
    cucsEquipmentBeaconLedFsmRmtInvRslt                              CucsConditionRemoteInvRslt,
    cucsEquipmentBeaconLedFsmStageDescr                              SnmpAdminString,
    cucsEquipmentBeaconLedFsmStamp                                   DateAndTime,
    cucsEquipmentBeaconLedFsmStatus                                  SnmpAdminString,
    cucsEquipmentBeaconLedFsmTry                                     Gauge32,
    cucsEquipmentBeaconLedId                                         Gauge32,
    cucsEquipmentBeaconLedName                                       SnmpAdminString,
    cucsEquipmentBeaconLedOperState                                  CucsEquipmentLedOperState
}

cucsEquipmentBeaconLedInstanceId OBJECT-TYPE
    SYNTAX       CucsManagedObjectId
    MAX-ACCESS   not-accessible
    STATUS       current
    DESCRIPTION
        "Instance identifier of the managed object."
    ::= { cucsEquipmentBeaconLedEntry 1 }

cucsEquipmentBeaconLedDn OBJECT-TYPE
    SYNTAX       CucsManagedObjectDn
    MAX-ACCESS   read-only
    STATUS       current
    DESCRIPTION
        "Cisco UCS equipment:BeaconLed:dn managed object property"
    ::= { cucsEquipmentBeaconLedEntry 2 }

cucsEquipmentBeaconLedRn OBJECT-TYPE
    SYNTAX       SnmpAdminString
    MAX-ACCESS   read-only
    STATUS       current
    DESCRIPTION
        "Cisco UCS equipment:BeaconLed:rn managed object property"
    ::= { cucsEquipmentBeaconLedEntry 3 }

cucsEquipmentBeaconLedAdminState OBJECT-TYPE
    SYNTAX       CucsEquipmentBeaconLedState
    MAX-ACCESS   read-only
    STATUS       current
    DESCRIPTION
        "Cisco UCS equipment:BeaconLed:adminState managed object property"
    ::= { cucsEquipmentBeaconLedEntry 4 }

cucsEquipmentBeaconLedColor OBJECT-TYPE
    SYNTAX       CucsEquipmentLedColor
    MAX-ACCESS   read-only
    STATUS       current
    DESCRIPTION
        "Cisco UCS equipment:BeaconLed:color managed object property"
    ::= { cucsEquipmentBeaconLedEntry 5 }

cucsEquipmentBeaconLedFsmDescr OBJECT-TYPE
    SYNTAX       SnmpAdminString
    MAX-ACCESS   read-only
    STATUS       current
    DESCRIPTION
        "Cisco UCS equipment:BeaconLed:fsmDescr managed object property"
    ::= { cucsEquipmentBeaconLedEntry 6 }

cucsEquipmentBeaconLedFsmPrev OBJECT-TYPE
    SYNTAX       SnmpAdminString
    MAX-ACCESS   read-only
    STATUS       current
    DESCRIPTION
        "Cisco UCS equipment:BeaconLed:fsmPrev managed object property"
    ::= { cucsEquipmentBeaconLedEntry 7 }

cucsEquipmentBeaconLedFsmProgr OBJECT-TYPE
    SYNTAX       Gauge32
    MAX-ACCESS   read-only
    STATUS       current
    DESCRIPTION
        "Cisco UCS equipment:BeaconLed:fsmProgr managed object property"
    ::= { cucsEquipmentBeaconLedEntry 8 }

cucsEquipmentBeaconLedFsmRmtInvErrCode OBJECT-TYPE
    SYNTAX       Gauge32
    MAX-ACCESS   read-only
    STATUS       current
    DESCRIPTION
        "Cisco UCS equipment:BeaconLed:fsmRmtInvErrCode
        managed object property"
    ::= { cucsEquipmentBeaconLedEntry 9 }

cucsEquipmentBeaconLedFsmRmtInvErrDescr OBJECT-TYPE
    SYNTAX       SnmpAdminString
    MAX-ACCESS   read-only
    STATUS       current
    DESCRIPTION
        "Cisco UCS equipment:BeaconLed:fsmRmtInvErrDescr
        managed object property"
    ::= { cucsEquipmentBeaconLedEntry 10 }

cucsEquipmentBeaconLedFsmRmtInvRslt OBJECT-TYPE
    SYNTAX       CucsConditionRemoteInvRslt
    MAX-ACCESS   read-only
    STATUS       current
    DESCRIPTION
        "Cisco UCS equipment:BeaconLed:fsmRmtInvRslt managed
        object property"
    ::= { cucsEquipmentBeaconLedEntry 11 }

cucsEquipmentBeaconLedFsmStageDescr OBJECT-TYPE
    SYNTAX       SnmpAdminString
    MAX-ACCESS   read-only
    STATUS       current
    DESCRIPTION
        "Cisco UCS equipment:BeaconLed:fsmStageDescr managed
        object property"
    ::= { cucsEquipmentBeaconLedEntry 12 }

cucsEquipmentBeaconLedFsmStamp OBJECT-TYPE
    SYNTAX       DateAndTime
    MAX-ACCESS   read-only
    STATUS       current
    DESCRIPTION
        "Cisco UCS equipment:BeaconLed:fsmStamp managed object property"
    ::= { cucsEquipmentBeaconLedEntry 13 }

cucsEquipmentBeaconLedFsmStatus OBJECT-TYPE
    SYNTAX       SnmpAdminString
    MAX-ACCESS   read-only
    STATUS       current
    DESCRIPTION
        "Cisco UCS equipment:BeaconLed:fsmStatus managed object property"
    ::= { cucsEquipmentBeaconLedEntry 14 }

cucsEquipmentBeaconLedFsmTry OBJECT-TYPE
    SYNTAX       Gauge32
    MAX-ACCESS   read-only
    STATUS       current
    DESCRIPTION
        "Cisco UCS equipment:BeaconLed:fsmTry managed object property"
    ::= { cucsEquipmentBeaconLedEntry 15 }

cucsEquipmentBeaconLedId OBJECT-TYPE
    SYNTAX       Gauge32
    MAX-ACCESS   read-only
    STATUS       current
    DESCRIPTION
        "Cisco UCS equipment:BeaconLed:id managed object property"
    ::= { cucsEquipmentBeaconLedEntry 16 }

cucsEquipmentBeaconLedName OBJECT-TYPE
    SYNTAX       SnmpAdminString
    MAX-ACCESS   read-only
    STATUS       current
    DESCRIPTION
        "Cisco UCS equipment:BeaconLed:name managed object property"
    ::= { cucsEquipmentBeaconLedEntry 17 }

cucsEquipmentBeaconLedOperState OBJECT-TYPE
    SYNTAX       CucsEquipmentLedOperState
    MAX-ACCESS   read-only
    STATUS       current
    DESCRIPTION
        "Cisco UCS equipment:BeaconLed:operState managed object property"
    ::= { cucsEquipmentBeaconLedEntry 18 }

cucsEquipmentBeaconLedFsmTable OBJECT-TYPE
    SYNTAX           SEQUENCE OF CucsEquipmentBeaconLedFsmEntry
    MAX-ACCESS       not-accessible
    STATUS           current
    DESCRIPTION
        "Cisco UCS equipment:BeaconLedFsm managed object table"
    ::= { cucsEquipmentObjects 103 }

cucsEquipmentBeaconLedFsmEntry OBJECT-TYPE
    SYNTAX           CucsEquipmentBeaconLedFsmEntry
    MAX-ACCESS       not-accessible
    STATUS           current
    DESCRIPTION
        "Entry for the cucsEquipmentBeaconLedFsmTable table."
    INDEX { cucsEquipmentBeaconLedFsmInstanceId }
    ::= { cucsEquipmentBeaconLedFsmTable 1 }

CucsEquipmentBeaconLedFsmEntry ::= SEQUENCE {
    cucsEquipmentBeaconLedFsmInstanceId                              CucsManagedObjectId,
    cucsEquipmentBeaconLedFsmDn                                      CucsManagedObjectDn,
    cucsEquipmentBeaconLedFsmRn                                      SnmpAdminString,
    cucsEquipmentBeaconLedFsmCompletionTime                          DateAndTime,
    cucsEquipmentBeaconLedFsmCurrentFsm                              CucsEquipmentBeaconLedFsmCurrentFsm,
    cucsEquipmentBeaconLedFsmDescrData                               SnmpAdminString,
    cucsEquipmentBeaconLedFsmFsmStatus                               CucsFsmFsmStageStatus,
    cucsEquipmentBeaconLedFsmProgress                                Gauge32,
    cucsEquipmentBeaconLedFsmRmtErrCode                              Gauge32,
    cucsEquipmentBeaconLedFsmRmtErrDescr                             SnmpAdminString,
    cucsEquipmentBeaconLedFsmRmtRslt                                 CucsConditionRemoteInvRslt
}

cucsEquipmentBeaconLedFsmInstanceId OBJECT-TYPE
    SYNTAX       CucsManagedObjectId
    MAX-ACCESS   not-accessible
    STATUS       current
    DESCRIPTION
        "Instance identifier of the managed object."
    ::= { cucsEquipmentBeaconLedFsmEntry 1 }

cucsEquipmentBeaconLedFsmDn OBJECT-TYPE
    SYNTAX       CucsManagedObjectDn
    MAX-ACCESS   read-only
    STATUS       current
    DESCRIPTION
        "Cisco UCS equipment:BeaconLedFsm:dn managed object property"
    ::= { cucsEquipmentBeaconLedFsmEntry 2 }

cucsEquipmentBeaconLedFsmRn OBJECT-TYPE
    SYNTAX       SnmpAdminString
    MAX-ACCESS   read-only
    STATUS       current
    DESCRIPTION
        "Cisco UCS equipment:BeaconLedFsm:rn managed object property"
    ::= { cucsEquipmentBeaconLedFsmEntry 3 }

cucsEquipmentBeaconLedFsmCompletionTime OBJECT-TYPE
    SYNTAX       DateAndTime
    MAX-ACCESS   read-only
    STATUS       current
    DESCRIPTION
        "Cisco UCS equipment:BeaconLedFsm:completionTime
        managed object property"
    ::= { cucsEquipmentBeaconLedFsmEntry 4 }

cucsEquipmentBeaconLedFsmCurrentFsm OBJECT-TYPE
    SYNTAX       CucsEquipmentBeaconLedFsmCurrentFsm
    MAX-ACCESS   read-only
    STATUS       current
    DESCRIPTION
        "Cisco UCS equipment:BeaconLedFsm:currentFsm managed
        object property"
    ::= { cucsEquipmentBeaconLedFsmEntry 5 }

cucsEquipmentBeaconLedFsmDescrData OBJECT-TYPE
    SYNTAX       SnmpAdminString
    MAX-ACCESS   read-only
    STATUS       current
    DESCRIPTION
        "Cisco UCS equipment:BeaconLedFsm:descr managed object property"
    ::= { cucsEquipmentBeaconLedFsmEntry 6 }

cucsEquipmentBeaconLedFsmFsmStatus OBJECT-TYPE
    SYNTAX       CucsFsmFsmStageStatus
    MAX-ACCESS   read-only
    STATUS       current
    DESCRIPTION
        "Cisco UCS equipment:BeaconLedFsm:fsmStatus managed
        object property"
    ::= { cucsEquipmentBeaconLedFsmEntry 7 }

cucsEquipmentBeaconLedFsmProgress OBJECT-TYPE
    SYNTAX       Gauge32
    MAX-ACCESS   read-only
    STATUS       current
    DESCRIPTION
        "Cisco UCS equipment:BeaconLedFsm:progress managed
        object property"
    ::= { cucsEquipmentBeaconLedFsmEntry 8 }

cucsEquipmentBeaconLedFsmRmtErrCode OBJECT-TYPE
    SYNTAX       Gauge32
    MAX-ACCESS   read-only
    STATUS       current
    DESCRIPTION
        "Cisco UCS equipment:BeaconLedFsm:rmtErrCode managed
        object property"
    ::= { cucsEquipmentBeaconLedFsmEntry 9 }

cucsEquipmentBeaconLedFsmRmtErrDescr OBJECT-TYPE
    SYNTAX       SnmpAdminString
    MAX-ACCESS   read-only
    STATUS       current
    DESCRIPTION
        "Cisco UCS equipment:BeaconLedFsm:rmtErrDescr managed
        object property"
    ::= { cucsEquipmentBeaconLedFsmEntry 10 }

cucsEquipmentBeaconLedFsmRmtRslt OBJECT-TYPE
    SYNTAX       CucsConditionRemoteInvRslt
    MAX-ACCESS   read-only
    STATUS       current
    DESCRIPTION
        "Cisco UCS equipment:BeaconLedFsm:rmtRslt managed object property"
    ::= { cucsEquipmentBeaconLedFsmEntry 11 }

cucsEquipmentBeaconLedFsmStageTable OBJECT-TYPE
    SYNTAX           SEQUENCE OF CucsEquipmentBeaconLedFsmStageEntry
    MAX-ACCESS       not-accessible
    STATUS           current
    DESCRIPTION
        "Cisco UCS equipment:BeaconLedFsmStage managed object table"
    ::= { cucsEquipmentObjects 104 }

cucsEquipmentBeaconLedFsmStageEntry OBJECT-TYPE
    SYNTAX           CucsEquipmentBeaconLedFsmStageEntry
    MAX-ACCESS       not-accessible
    STATUS           current
    DESCRIPTION
        "Entry for the cucsEquipmentBeaconLedFsmStageTable table."
    INDEX { cucsEquipmentBeaconLedFsmStageInstanceId }
    ::= { cucsEquipmentBeaconLedFsmStageTable 1 }

CucsEquipmentBeaconLedFsmStageEntry ::= SEQUENCE {
    cucsEquipmentBeaconLedFsmStageInstanceId                         CucsManagedObjectId,
    cucsEquipmentBeaconLedFsmStageDn                                 CucsManagedObjectDn,
    cucsEquipmentBeaconLedFsmStageRn                                 SnmpAdminString,
    cucsEquipmentBeaconLedFsmStageDescrData                          SnmpAdminString,
    cucsEquipmentBeaconLedFsmStageLastUpdateTime                     DateAndTime,
    cucsEquipmentBeaconLedFsmStageName                               CucsEquipmentBeaconLedFsmStageName,
    cucsEquipmentBeaconLedFsmStageOrder                              Gauge32,
    cucsEquipmentBeaconLedFsmStageRetry                              Gauge32,
    cucsEquipmentBeaconLedFsmStageStageStatus                        CucsFsmFsmStageStatus
}

cucsEquipmentBeaconLedFsmStageInstanceId OBJECT-TYPE
    SYNTAX       CucsManagedObjectId
    MAX-ACCESS   not-accessible
    STATUS       current
    DESCRIPTION
        "Instance identifier of the managed object."
    ::= { cucsEquipmentBeaconLedFsmStageEntry 1 }

cucsEquipmentBeaconLedFsmStageDn OBJECT-TYPE
    SYNTAX       CucsManagedObjectDn
    MAX-ACCESS   read-only
    STATUS       current
    DESCRIPTION
        "Cisco UCS equipment:BeaconLedFsmStage:dn managed object property"
    ::= { cucsEquipmentBeaconLedFsmStageEntry 2 }

cucsEquipmentBeaconLedFsmStageRn OBJECT-TYPE
    SYNTAX       SnmpAdminString
    MAX-ACCESS   read-only
    STATUS       current
    DESCRIPTION
        "Cisco UCS equipment:BeaconLedFsmStage:rn managed object property"
    ::= { cucsEquipmentBeaconLedFsmStageEntry 3 }

cucsEquipmentBeaconLedFsmStageDescrData OBJECT-TYPE
    SYNTAX       SnmpAdminString
    MAX-ACCESS   read-only
    STATUS       current
    DESCRIPTION
        "Cisco UCS equipment:BeaconLedFsmStage:descr managed
        object property"
    ::= { cucsEquipmentBeaconLedFsmStageEntry 4 }

cucsEquipmentBeaconLedFsmStageLastUpdateTime OBJECT-TYPE
    SYNTAX       DateAndTime
    MAX-ACCESS   read-only
    STATUS       current
    DESCRIPTION
        "Cisco UCS equipment:BeaconLedFsmStage:lastUpdateTime
        managed object property"
    ::= { cucsEquipmentBeaconLedFsmStageEntry 5 }

cucsEquipmentBeaconLedFsmStageName OBJECT-TYPE
    SYNTAX       CucsEquipmentBeaconLedFsmStageName
    MAX-ACCESS   read-only
    STATUS       current
    DESCRIPTION
        "Cisco UCS equipment:BeaconLedFsmStage:name managed
        object property"
    ::= { cucsEquipmentBeaconLedFsmStageEntry 6 }

cucsEquipmentBeaconLedFsmStageOrder OBJECT-TYPE
    SYNTAX       Gauge32
    MAX-ACCESS   read-only
    STATUS       current
    DESCRIPTION
        "Cisco UCS equipment:BeaconLedFsmStage:order managed
        object property"
    ::= { cucsEquipmentBeaconLedFsmStageEntry 7 }

cucsEquipmentBeaconLedFsmStageRetry OBJECT-TYPE
    SYNTAX       Gauge32
    MAX-ACCESS   read-only
    STATUS       current
    DESCRIPTION
        "Cisco UCS equipment:BeaconLedFsmStage:retry managed
        object property"
    ::= { cucsEquipmentBeaconLedFsmStageEntry 8 }

cucsEquipmentBeaconLedFsmStageStageStatus OBJECT-TYPE
    SYNTAX       CucsFsmFsmStageStatus
    MAX-ACCESS   read-only
    STATUS       current
    DESCRIPTION
        "Cisco UCS equipment:BeaconLedFsmStage:stageStatus
        managed object property"
    ::= { cucsEquipmentBeaconLedFsmStageEntry 9 }

cucsEquipmentBeaconLedFsmTaskTable OBJECT-TYPE
    SYNTAX           SEQUENCE OF CucsEquipmentBeaconLedFsmTaskEntry
    MAX-ACCESS       not-accessible
    STATUS           current
    DESCRIPTION
        "Cisco UCS equipment:BeaconLedFsmTask managed object table"
    ::= { cucsEquipmentObjects 83 }

cucsEquipmentBeaconLedFsmTaskEntry OBJECT-TYPE
    SYNTAX           CucsEquipmentBeaconLedFsmTaskEntry
    MAX-ACCESS       not-accessible
    STATUS           current
    DESCRIPTION
        "Entry for the cucsEquipmentBeaconLedFsmTaskTable table."
    INDEX { cucsEquipmentBeaconLedFsmTaskInstanceId }
    ::= { cucsEquipmentBeaconLedFsmTaskTable 1 }

CucsEquipmentBeaconLedFsmTaskEntry ::= SEQUENCE {
    cucsEquipmentBeaconLedFsmTaskInstanceId                          CucsManagedObjectId,
    cucsEquipmentBeaconLedFsmTaskDn                                  CucsManagedObjectDn,
    cucsEquipmentBeaconLedFsmTaskRn                                  SnmpAdminString,
    cucsEquipmentBeaconLedFsmTaskCompletion                          CucsFsmCompletion,
    cucsEquipmentBeaconLedFsmTaskFlags                               CucsFsmFlags,
    cucsEquipmentBeaconLedFsmTaskItem                                CucsEquipmentBeaconLedFsmTaskItem,
    cucsEquipmentBeaconLedFsmTaskSeqId                               Gauge32
}

cucsEquipmentBeaconLedFsmTaskInstanceId OBJECT-TYPE
    SYNTAX       CucsManagedObjectId
    MAX-ACCESS   not-accessible
    STATUS       current
    DESCRIPTION
        "Instance identifier of the managed object."
    ::= { cucsEquipmentBeaconLedFsmTaskEntry 1 }

cucsEquipmentBeaconLedFsmTaskDn OBJECT-TYPE
    SYNTAX       CucsManagedObjectDn
    MAX-ACCESS   read-only
    STATUS       current
    DESCRIPTION
        "Cisco UCS equipment:BeaconLedFsmTask:dn managed object property"
    ::= { cucsEquipmentBeaconLedFsmTaskEntry 2 }

cucsEquipmentBeaconLedFsmTaskRn OBJECT-TYPE
    SYNTAX       SnmpAdminString
    MAX-ACCESS   read-only
    STATUS       current
    DESCRIPTION
        "Cisco UCS equipment:BeaconLedFsmTask:rn managed object property"
    ::= { cucsEquipmentBeaconLedFsmTaskEntry 3 }

cucsEquipmentBeaconLedFsmTaskCompletion OBJECT-TYPE
    SYNTAX       CucsFsmCompletion
    MAX-ACCESS   read-only
    STATUS       current
    DESCRIPTION
        "Cisco UCS equipment:BeaconLedFsmTask:completion
        managed object property"
    ::= { cucsEquipmentBeaconLedFsmTaskEntry 4 }

cucsEquipmentBeaconLedFsmTaskFlags OBJECT-TYPE
    SYNTAX       CucsFsmFlags
    MAX-ACCESS   read-only
    STATUS       current
    DESCRIPTION
        "Cisco UCS equipment:BeaconLedFsmTask:flags managed
        object property"
    ::= { cucsEquipmentBeaconLedFsmTaskEntry 5 }

cucsEquipmentBeaconLedFsmTaskItem OBJECT-TYPE
    SYNTAX       CucsEquipmentBeaconLedFsmTaskItem
    MAX-ACCESS   read-only
    STATUS       current
    DESCRIPTION
        "Cisco UCS equipment:BeaconLedFsmTask:item managed
        object property"
    ::= { cucsEquipmentBeaconLedFsmTaskEntry 6 }

cucsEquipmentBeaconLedFsmTaskSeqId OBJECT-TYPE
    SYNTAX       Gauge32
    MAX-ACCESS   read-only
    STATUS       current
    DESCRIPTION
        "Cisco UCS equipment:BeaconLedFsmTask:seqId managed
        object property"
    ::= { cucsEquipmentBeaconLedFsmTaskEntry 7 }

cucsEquipmentBindingTable OBJECT-TYPE
    SYNTAX           SEQUENCE OF CucsEquipmentBindingEntry
    MAX-ACCESS       not-accessible
    STATUS           current
    DESCRIPTION
        "Cisco UCS equipment:Binding managed object table"
    ::= { cucsEquipmentObjects 177 }

cucsEquipmentBindingEntry OBJECT-TYPE
    SYNTAX           CucsEquipmentBindingEntry
    MAX-ACCESS       not-accessible
    STATUS           current
    DESCRIPTION
        "Entry for the cucsEquipmentBindingTable table."
    INDEX { cucsEquipmentBindingInstanceId }
    ::= { cucsEquipmentBindingTable 1 }

CucsEquipmentBindingEntry ::= SEQUENCE {
    cucsEquipmentBindingInstanceId                                   CucsManagedObjectId,
    cucsEquipmentBindingDn                                           CucsManagedObjectDn,
    cucsEquipmentBindingRn                                           SnmpAdminString,
    cucsEquipmentBindingAssignedToDn                                 SnmpAdminString,
    cucsEquipmentBindingChassisDn                                    SnmpAdminString,
    cucsEquipmentBindingIssues                                       CucsEquipmentChassisConfigIssues,
    cucsEquipmentBindingName                                         SnmpAdminString,
    cucsEquipmentBindingOperState                                    CucsEquipmentChassisProfileBindingOperState,
    cucsEquipmentBindingRestrictMigration                            TruthValue,
    cucsEquipmentBindingPropAcl                                      Unsigned64
}

cucsEquipmentBindingInstanceId OBJECT-TYPE
    SYNTAX       CucsManagedObjectId
    MAX-ACCESS   not-accessible
    STATUS       current
    DESCRIPTION
        "Instance identifier of the managed object."
    ::= { cucsEquipmentBindingEntry 1 }

cucsEquipmentBindingDn OBJECT-TYPE
    SYNTAX       CucsManagedObjectDn
    MAX-ACCESS   read-only
    STATUS       current
    DESCRIPTION
        "Cisco UCS equipment:Binding:dn managed object property"
    ::= { cucsEquipmentBindingEntry 2 }

cucsEquipmentBindingRn OBJECT-TYPE
    SYNTAX       SnmpAdminString
    MAX-ACCESS   read-only
    STATUS       current
    DESCRIPTION
        "Cisco UCS equipment:Binding:rn managed object property"
    ::= { cucsEquipmentBindingEntry 3 }

cucsEquipmentBindingAssignedToDn OBJECT-TYPE
    SYNTAX       SnmpAdminString
    MAX-ACCESS   read-only
    STATUS       current
    DESCRIPTION
        "Cisco UCS equipment:Binding:assignedToDn managed object property"
    ::= { cucsEquipmentBindingEntry 4 }

cucsEquipmentBindingChassisDn OBJECT-TYPE
    SYNTAX       SnmpAdminString
    MAX-ACCESS   read-only
    STATUS       current
    DESCRIPTION
        "Cisco UCS equipment:Binding:chassisDn managed object property"
    ::= { cucsEquipmentBindingEntry 5 }

cucsEquipmentBindingIssues OBJECT-TYPE
    SYNTAX       CucsEquipmentChassisConfigIssues
    MAX-ACCESS   read-only
    STATUS       current
    DESCRIPTION
        "Cisco UCS equipment:Binding:issues managed object property"
    ::= { cucsEquipmentBindingEntry 6 }

cucsEquipmentBindingName OBJECT-TYPE
    SYNTAX       SnmpAdminString
    MAX-ACCESS   read-only
    STATUS       current
    DESCRIPTION
        "Cisco UCS equipment:Binding:name managed object property"
    ::= { cucsEquipmentBindingEntry 7 }

cucsEquipmentBindingOperState OBJECT-TYPE
    SYNTAX       CucsEquipmentChassisProfileBindingOperState
    MAX-ACCESS   read-only
    STATUS       current
    DESCRIPTION
        "Cisco UCS equipment:Binding:operState managed object property"
    ::= { cucsEquipmentBindingEntry 8 }

cucsEquipmentBindingRestrictMigration OBJECT-TYPE
    SYNTAX       TruthValue
    MAX-ACCESS   read-only
    STATUS       current
    DESCRIPTION
        "Cisco UCS equipment:Binding:restrictMigration
        managed object property"
    ::= { cucsEquipmentBindingEntry 9 }

cucsEquipmentBindingPropAcl OBJECT-TYPE
    SYNTAX       Unsigned64
    MAX-ACCESS   read-only
    STATUS       current
    DESCRIPTION
        "Cisco UCS equipment:Binding:propAcl managed object property"
    ::= { cucsEquipmentBindingEntry 10 }

cucsEquipmentBiosDefTable OBJECT-TYPE
    SYNTAX           SEQUENCE OF CucsEquipmentBiosDefEntry
    MAX-ACCESS       not-accessible
    STATUS           current
    DESCRIPTION
        "Cisco UCS equipment:BiosDef managed object table"
    ::= { cucsEquipmentObjects 96 }

cucsEquipmentBiosDefEntry OBJECT-TYPE
    SYNTAX           CucsEquipmentBiosDefEntry
    MAX-ACCESS       not-accessible
    STATUS           current
    DESCRIPTION
        "Entry for the cucsEquipmentBiosDefTable table."
    INDEX { cucsEquipmentBiosDefInstanceId }
    ::= { cucsEquipmentBiosDefTable 1 }

CucsEquipmentBiosDefEntry ::= SEQUENCE {
    cucsEquipmentBiosDefInstanceId                                   CucsManagedObjectId,
    cucsEquipmentBiosDefDn                                           CucsManagedObjectDn,
    cucsEquipmentBiosDefRn                                           SnmpAdminString,
    cucsEquipmentBiosDefDescr                                        SnmpAdminString,
    cucsEquipmentBiosDefIntId                                        SnmpAdminString,
    cucsEquipmentBiosDefName                                         SnmpAdminString,
    cucsEquipmentBiosDefResetOn                                      CucsEquipmentResetOn,
    cucsEquipmentBiosDefSecureBios                                   CucsEquipmentSecureBios,
    cucsEquipmentBiosDefStorageMethod                                CucsEquipmentStorageMethod,
    cucsEquipmentBiosDefUpdateMethod                                 CucsEquipmentBiosUpdateMethod,
    cucsEquipmentBiosDefPolicyLevel                                  Gauge32,
    cucsEquipmentBiosDefPolicyOwner                                  CucsPolicyPolicyOwner,
    cucsEquipmentBiosDefTpmConfigSupport                             CucsEquipmentTpmConfigSupport
}

cucsEquipmentBiosDefInstanceId OBJECT-TYPE
    SYNTAX       CucsManagedObjectId
    MAX-ACCESS   not-accessible
    STATUS       current
    DESCRIPTION
        "Instance identifier of the managed object."
    ::= { cucsEquipmentBiosDefEntry 1 }

cucsEquipmentBiosDefDn OBJECT-TYPE
    SYNTAX       CucsManagedObjectDn
    MAX-ACCESS   read-only
    STATUS       current
    DESCRIPTION
        "Cisco UCS equipment:BiosDef:dn managed object property"
    ::= { cucsEquipmentBiosDefEntry 2 }

cucsEquipmentBiosDefRn OBJECT-TYPE
    SYNTAX       SnmpAdminString
    MAX-ACCESS   read-only
    STATUS       current
    DESCRIPTION
        "Cisco UCS equipment:BiosDef:rn managed object property"
    ::= { cucsEquipmentBiosDefEntry 3 }

cucsEquipmentBiosDefDescr OBJECT-TYPE
    SYNTAX       SnmpAdminString
    MAX-ACCESS   read-only
    STATUS       current
    DESCRIPTION
        "Cisco UCS equipment:BiosDef:descr managed object property"
    ::= { cucsEquipmentBiosDefEntry 4 }

cucsEquipmentBiosDefIntId OBJECT-TYPE
    SYNTAX       SnmpAdminString
    MAX-ACCESS   read-only
    STATUS       current
    DESCRIPTION
        "Cisco UCS equipment:BiosDef:intId managed object property"
    ::= { cucsEquipmentBiosDefEntry 5 }

cucsEquipmentBiosDefName OBJECT-TYPE
    SYNTAX       SnmpAdminString
    MAX-ACCESS   read-only
    STATUS       current
    DESCRIPTION
        "Cisco UCS equipment:BiosDef:name managed object property"
    ::= { cucsEquipmentBiosDefEntry 6 }

cucsEquipmentBiosDefResetOn OBJECT-TYPE
    SYNTAX       CucsEquipmentResetOn
    MAX-ACCESS   read-only
    STATUS       current
    DESCRIPTION
        "Cisco UCS equipment:BiosDef:resetOn managed object property"
    ::= { cucsEquipmentBiosDefEntry 7 }

cucsEquipmentBiosDefSecureBios OBJECT-TYPE
    SYNTAX       CucsEquipmentSecureBios
    MAX-ACCESS   read-only
    STATUS       current
    DESCRIPTION
        "Cisco UCS equipment:BiosDef:secureBios managed object property"
    ::= { cucsEquipmentBiosDefEntry 8 }

cucsEquipmentBiosDefStorageMethod OBJECT-TYPE
    SYNTAX       CucsEquipmentStorageMethod
    MAX-ACCESS   read-only
    STATUS       current
    DESCRIPTION
        "Cisco UCS equipment:BiosDef:storageMethod managed
        object property"
    ::= { cucsEquipmentBiosDefEntry 9 }

cucsEquipmentBiosDefUpdateMethod OBJECT-TYPE
    SYNTAX       CucsEquipmentBiosUpdateMethod
    MAX-ACCESS   read-only
    STATUS       current
    DESCRIPTION
        "Cisco UCS equipment:BiosDef:updateMethod managed object property"
    ::= { cucsEquipmentBiosDefEntry 10 }

cucsEquipmentBiosDefPolicyLevel OBJECT-TYPE
    SYNTAX       Gauge32
    MAX-ACCESS   read-only
    STATUS       current
    DESCRIPTION
        "Cisco UCS equipment:BiosDef:policyLevel managed object property"
    ::= { cucsEquipmentBiosDefEntry 11 }

cucsEquipmentBiosDefPolicyOwner OBJECT-TYPE
    SYNTAX       CucsPolicyPolicyOwner
    MAX-ACCESS   read-only
    STATUS       current
    DESCRIPTION
        "Cisco UCS equipment:BiosDef:policyOwner managed object property"
    ::= { cucsEquipmentBiosDefEntry 12 }

cucsEquipmentBiosDefTpmConfigSupport OBJECT-TYPE
    SYNTAX       CucsEquipmentTpmConfigSupport
    MAX-ACCESS   read-only
    STATUS       current
    DESCRIPTION
        "Cisco UCS equipment:BiosDef:tpmConfigSupport managed
        object property"
    ::= { cucsEquipmentBiosDefEntry 13 }

cucsEquipmentBiosTokenOverrideTable OBJECT-TYPE
    SYNTAX           SEQUENCE OF CucsEquipmentBiosTokenOverrideEntry
    MAX-ACCESS       not-accessible
    STATUS           current
    DESCRIPTION
        "Cisco UCS equipment:BiosTokenOverride managed object table"
    ::= { cucsEquipmentObjects 222 }

cucsEquipmentBiosTokenOverrideEntry OBJECT-TYPE
    SYNTAX           CucsEquipmentBiosTokenOverrideEntry
    MAX-ACCESS       not-accessible
    STATUS           current
    DESCRIPTION
        "Entry for the cucsEquipmentBiosTokenOverrideTable table."
    INDEX { cucsEquipmentBiosTokenOverrideInstanceId }
    ::= { cucsEquipmentBiosTokenOverrideTable 1 }

CucsEquipmentBiosTokenOverrideEntry ::= SEQUENCE {
    cucsEquipmentBiosTokenOverrideInstanceId                         CucsManagedObjectId,
    cucsEquipmentBiosTokenOverrideDn                                 CucsManagedObjectDn,
    cucsEquipmentBiosTokenOverrideRn                                 SnmpAdminString,
    cucsEquipmentBiosTokenOverrideBiosTokenId                        CucsEquipmentBiosTokenType,
    cucsEquipmentBiosTokenOverrideBiosTokenName                      SnmpAdminString,
    cucsEquipmentBiosTokenOverrideBiosTokenValue                     SnmpAdminString,
    cucsEquipmentBiosTokenOverrideDescr                              SnmpAdminString,
    cucsEquipmentBiosTokenOverrideIntId                              SnmpAdminString,
    cucsEquipmentBiosTokenOverrideName                               SnmpAdminString,
    cucsEquipmentBiosTokenOverridePolicyLevel                        Gauge32,
    cucsEquipmentBiosTokenOverridePolicyOwner                        CucsPolicyPolicyOwner
}

cucsEquipmentBiosTokenOverrideInstanceId OBJECT-TYPE
    SYNTAX       CucsManagedObjectId
    MAX-ACCESS   not-accessible
    STATUS       current
    DESCRIPTION
        "Instance identifier of the managed object."
    ::= { cucsEquipmentBiosTokenOverrideEntry 1 }

cucsEquipmentBiosTokenOverrideDn OBJECT-TYPE
    SYNTAX       CucsManagedObjectDn
    MAX-ACCESS   read-only
    STATUS       current
    DESCRIPTION
        "Cisco UCS equipment:BiosTokenOverride:dn managed object property"
    ::= { cucsEquipmentBiosTokenOverrideEntry 2 }

cucsEquipmentBiosTokenOverrideRn OBJECT-TYPE
    SYNTAX       SnmpAdminString
    MAX-ACCESS   read-only
    STATUS       current
    DESCRIPTION
        "Cisco UCS equipment:BiosTokenOverride:rn managed object property"
    ::= { cucsEquipmentBiosTokenOverrideEntry 3 }

cucsEquipmentBiosTokenOverrideBiosTokenId OBJECT-TYPE
    SYNTAX       CucsEquipmentBiosTokenType
    MAX-ACCESS   read-only
    STATUS       current
    DESCRIPTION
        "Cisco UCS equipment:BiosTokenOverride:biosTokenId
        managed object property"
    ::= { cucsEquipmentBiosTokenOverrideEntry 4 }

cucsEquipmentBiosTokenOverrideBiosTokenName OBJECT-TYPE
    SYNTAX       SnmpAdminString
    MAX-ACCESS   read-only
    STATUS       current
    DESCRIPTION
        "Cisco UCS equipment:BiosTokenOverride:biosTokenName
        managed object property"
    ::= { cucsEquipmentBiosTokenOverrideEntry 5 }

cucsEquipmentBiosTokenOverrideBiosTokenValue OBJECT-TYPE
    SYNTAX       SnmpAdminString
    MAX-ACCESS   read-only
    STATUS       current
    DESCRIPTION
        "Cisco UCS equipment:BiosTokenOverride:biosTokenValue
        managed object property"
    ::= { cucsEquipmentBiosTokenOverrideEntry 6 }

cucsEquipmentBiosTokenOverrideDescr OBJECT-TYPE
    SYNTAX       SnmpAdminString
    MAX-ACCESS   read-only
    STATUS       current
    DESCRIPTION
        "Cisco UCS equipment:BiosTokenOverride:descr managed
        object property"
    ::= { cucsEquipmentBiosTokenOverrideEntry 7 }

cucsEquipmentBiosTokenOverrideIntId OBJECT-TYPE
    SYNTAX       SnmpAdminString
    MAX-ACCESS   read-only
    STATUS       current
    DESCRIPTION
        "Cisco UCS equipment:BiosTokenOverride:intId managed
        object property"
    ::= { cucsEquipmentBiosTokenOverrideEntry 8 }

cucsEquipmentBiosTokenOverrideName OBJECT-TYPE
    SYNTAX       SnmpAdminString
    MAX-ACCESS   read-only
    STATUS       current
    DESCRIPTION
        "Cisco UCS equipment:BiosTokenOverride:name managed
        object property"
    ::= { cucsEquipmentBiosTokenOverrideEntry 9 }

cucsEquipmentBiosTokenOverridePolicyLevel OBJECT-TYPE
    SYNTAX       Gauge32
    MAX-ACCESS   read-only
    STATUS       current
    DESCRIPTION
        "Cisco UCS equipment:BiosTokenOverride:policyLevel
        managed object property"
    ::= { cucsEquipmentBiosTokenOverrideEntry 10 }

cucsEquipmentBiosTokenOverridePolicyOwner OBJECT-TYPE
    SYNTAX       CucsPolicyPolicyOwner
    MAX-ACCESS   read-only
    STATUS       current
    DESCRIPTION
        "Cisco UCS equipment:BiosTokenOverride:policyOwner
        managed object property"
    ::= { cucsEquipmentBiosTokenOverrideEntry 11 }

cucsEquipmentBladeAGLibraryTable OBJECT-TYPE
    SYNTAX           SEQUENCE OF CucsEquipmentBladeAGLibraryEntry
    MAX-ACCESS       not-accessible
    STATUS           current
    DESCRIPTION
        "Cisco UCS equipment:BladeAGLibrary managed object table"
    ::= { cucsEquipmentObjects 73 }

cucsEquipmentBladeAGLibraryEntry OBJECT-TYPE
    SYNTAX           CucsEquipmentBladeAGLibraryEntry
    MAX-ACCESS       not-accessible
    STATUS           current
    DESCRIPTION
        "Entry for the cucsEquipmentBladeAGLibraryTable table."
    INDEX { cucsEquipmentBladeAGLibraryInstanceId }
    ::= { cucsEquipmentBladeAGLibraryTable 1 }

CucsEquipmentBladeAGLibraryEntry ::= SEQUENCE {
    cucsEquipmentBladeAGLibraryInstanceId                            CucsManagedObjectId,
    cucsEquipmentBladeAGLibraryDn                                    CucsManagedObjectDn,
    cucsEquipmentBladeAGLibraryRn                                    SnmpAdminString,
    cucsEquipmentBladeAGLibraryDescr                                 SnmpAdminString,
    cucsEquipmentBladeAGLibraryIntId                                 SnmpAdminString,
    cucsEquipmentBladeAGLibraryName                                  SnmpAdminString,
    cucsEquipmentBladeAGLibraryPolicyLevel                           Gauge32,
    cucsEquipmentBladeAGLibraryPolicyOwner                           CucsPolicyPolicyOwner
}

cucsEquipmentBladeAGLibraryInstanceId OBJECT-TYPE
    SYNTAX       CucsManagedObjectId
    MAX-ACCESS   not-accessible
    STATUS       current
    DESCRIPTION
        "Instance identifier of the managed object."
    ::= { cucsEquipmentBladeAGLibraryEntry 1 }

cucsEquipmentBladeAGLibraryDn OBJECT-TYPE
    SYNTAX       CucsManagedObjectDn
    MAX-ACCESS   read-only
    STATUS       current
    DESCRIPTION
        "Cisco UCS equipment:BladeAGLibrary:dn managed object property"
    ::= { cucsEquipmentBladeAGLibraryEntry 2 }

cucsEquipmentBladeAGLibraryRn OBJECT-TYPE
    SYNTAX       SnmpAdminString
    MAX-ACCESS   read-only
    STATUS       current
    DESCRIPTION
        "Cisco UCS equipment:BladeAGLibrary:rn managed object property"
    ::= { cucsEquipmentBladeAGLibraryEntry 3 }

cucsEquipmentBladeAGLibraryDescr OBJECT-TYPE
    SYNTAX       SnmpAdminString
    MAX-ACCESS   read-only
    STATUS       current
    DESCRIPTION
        "Cisco UCS equipment:BladeAGLibrary:descr managed object property"
    ::= { cucsEquipmentBladeAGLibraryEntry 4 }

cucsEquipmentBladeAGLibraryIntId OBJECT-TYPE
    SYNTAX       SnmpAdminString
    MAX-ACCESS   read-only
    STATUS       current
    DESCRIPTION
        "Cisco UCS equipment:BladeAGLibrary:intId managed object property"
    ::= { cucsEquipmentBladeAGLibraryEntry 5 }

cucsEquipmentBladeAGLibraryName OBJECT-TYPE
    SYNTAX       SnmpAdminString
    MAX-ACCESS   read-only
    STATUS       current
    DESCRIPTION
        "Cisco UCS equipment:BladeAGLibrary:name managed object property"
    ::= { cucsEquipmentBladeAGLibraryEntry 6 }

cucsEquipmentBladeAGLibraryPolicyLevel OBJECT-TYPE
    SYNTAX       Gauge32
    MAX-ACCESS   read-only
    STATUS       current
    DESCRIPTION
        "Cisco UCS equipment:BladeAGLibrary:policyLevel
        managed object property"
    ::= { cucsEquipmentBladeAGLibraryEntry 7 }

cucsEquipmentBladeAGLibraryPolicyOwner OBJECT-TYPE
    SYNTAX       CucsPolicyPolicyOwner
    MAX-ACCESS   read-only
    STATUS       current
    DESCRIPTION
        "Cisco UCS equipment:BladeAGLibrary:policyOwner
        managed object property"
    ::= { cucsEquipmentBladeAGLibraryEntry 8 }

cucsEquipmentBladeAggregationCapRefTable OBJECT-TYPE
    SYNTAX           SEQUENCE OF CucsEquipmentBladeAggregationCapRefEntry
    MAX-ACCESS       not-accessible
    STATUS           current
    DESCRIPTION
        "Cisco UCS equipment:BladeAggregationCapRef managed object table"
    ::= { cucsEquipmentObjects 125 }

cucsEquipmentBladeAggregationCapRefEntry OBJECT-TYPE
    SYNTAX           CucsEquipmentBladeAggregationCapRefEntry
    MAX-ACCESS       not-accessible
    STATUS           current
    DESCRIPTION
        "Entry for the cucsEquipmentBladeAggregationCapRefTable table."
    INDEX { cucsEquipmentBladeAggregationCapRefInstanceId }
    ::= { cucsEquipmentBladeAggregationCapRefTable 1 }

CucsEquipmentBladeAggregationCapRefEntry ::= SEQUENCE {
    cucsEquipmentBladeAggregationCapRefInstanceId                    CucsManagedObjectId,
    cucsEquipmentBladeAggregationCapRefDn                            CucsManagedObjectDn,
    cucsEquipmentBladeAggregationCapRefRn                            SnmpAdminString,
    cucsEquipmentBladeAggregationCapRefIsSupported                   TruthValue
}

cucsEquipmentBladeAggregationCapRefInstanceId OBJECT-TYPE
    SYNTAX       CucsManagedObjectId
    MAX-ACCESS   not-accessible
    STATUS       current
    DESCRIPTION
        "Instance identifier of the managed object."
    ::= { cucsEquipmentBladeAggregationCapRefEntry 1 }

cucsEquipmentBladeAggregationCapRefDn OBJECT-TYPE
    SYNTAX       CucsManagedObjectDn
    MAX-ACCESS   read-only
    STATUS       current
    DESCRIPTION
        "Cisco UCS equipment:BladeAggregationCapRef:dn
        managed object property"
    ::= { cucsEquipmentBladeAggregationCapRefEntry 2 }

cucsEquipmentBladeAggregationCapRefRn OBJECT-TYPE
    SYNTAX       SnmpAdminString
    MAX-ACCESS   read-only
    STATUS       current
    DESCRIPTION
        "Cisco UCS equipment:BladeAggregationCapRef:rn
        managed object property"
    ::= { cucsEquipmentBladeAggregationCapRefEntry 3 }

cucsEquipmentBladeAggregationCapRefIsSupported OBJECT-TYPE
    SYNTAX       TruthValue
    MAX-ACCESS   read-only
    STATUS       current
    DESCRIPTION
        "Cisco UCS equipment:BladeAggregationCapRef:isSupported
        managed object property"
    ::= { cucsEquipmentBladeAggregationCapRefEntry 4 }

cucsEquipmentBladeBiosCapProviderTable OBJECT-TYPE
    SYNTAX           SEQUENCE OF CucsEquipmentBladeBiosCapProviderEntry
    MAX-ACCESS       not-accessible
    STATUS           current
    DESCRIPTION
        "Cisco UCS equipment:BladeBiosCapProvider managed object table"
    ::= { cucsEquipmentObjects 3 }

cucsEquipmentBladeBiosCapProviderEntry OBJECT-TYPE
    SYNTAX           CucsEquipmentBladeBiosCapProviderEntry
    MAX-ACCESS       not-accessible
    STATUS           current
    DESCRIPTION
        "Entry for the cucsEquipmentBladeBiosCapProviderTable table."
    INDEX { cucsEquipmentBladeBiosCapProviderInstanceId }
    ::= { cucsEquipmentBladeBiosCapProviderTable 1 }

CucsEquipmentBladeBiosCapProviderEntry ::= SEQUENCE {
    cucsEquipmentBladeBiosCapProviderInstanceId                      CucsManagedObjectId,
    cucsEquipmentBladeBiosCapProviderDn                              CucsManagedObjectDn,
    cucsEquipmentBladeBiosCapProviderRn                              SnmpAdminString,
    cucsEquipmentBladeBiosCapProviderDeprecated                      TruthValue,
    cucsEquipmentBladeBiosCapProviderGencount                        Gauge32,
    cucsEquipmentBladeBiosCapProviderMgmtPlaneVer                    SnmpAdminString,
    cucsEquipmentBladeBiosCapProviderModel                           SnmpAdminString,
    cucsEquipmentBladeBiosCapProviderRevision                        SnmpAdminString,
    cucsEquipmentBladeBiosCapProviderVendor                          SnmpAdminString,
    cucsEquipmentBladeBiosCapProviderProductName                     SnmpAdminString,
    cucsEquipmentBladeBiosCapProviderPromCardType                    Gauge32,
    cucsEquipmentBladeBiosCapProviderDeleted                         TruthValue,
    cucsEquipmentBladeBiosCapProviderElementLoadFailures             Gauge32,
    cucsEquipmentBladeBiosCapProviderElementsLoaded                  Gauge32,
    cucsEquipmentBladeBiosCapProviderLoadErrors                      Gauge32,
    cucsEquipmentBladeBiosCapProviderLoadWarnings                    Gauge32
}

cucsEquipmentBladeBiosCapProviderInstanceId OBJECT-TYPE
    SYNTAX       CucsManagedObjectId
    MAX-ACCESS   not-accessible
    STATUS       current
    DESCRIPTION
        "Instance identifier of the managed object."
    ::= { cucsEquipmentBladeBiosCapProviderEntry 1 }

cucsEquipmentBladeBiosCapProviderDn OBJECT-TYPE
    SYNTAX       CucsManagedObjectDn
    MAX-ACCESS   read-only
    STATUS       current
    DESCRIPTION
        "Cisco UCS equipment:BladeBiosCapProvider:dn managed
        object property"
    ::= { cucsEquipmentBladeBiosCapProviderEntry 2 }

cucsEquipmentBladeBiosCapProviderRn OBJECT-TYPE
    SYNTAX       SnmpAdminString
    MAX-ACCESS   read-only
    STATUS       current
    DESCRIPTION
        "Cisco UCS equipment:BladeBiosCapProvider:rn managed
        object property"
    ::= { cucsEquipmentBladeBiosCapProviderEntry 3 }

cucsEquipmentBladeBiosCapProviderDeprecated OBJECT-TYPE
    SYNTAX       TruthValue
    MAX-ACCESS   read-only
    STATUS       current
    DESCRIPTION
        "Cisco UCS equipment:BladeBiosCapProvider:deprecated
        managed object property"
    ::= { cucsEquipmentBladeBiosCapProviderEntry 4 }

cucsEquipmentBladeBiosCapProviderGencount OBJECT-TYPE
    SYNTAX       Gauge32
    MAX-ACCESS   read-only
    STATUS       current
    DESCRIPTION
        "Cisco UCS equipment:BladeBiosCapProvider:gencount
        managed object property"
    ::= { cucsEquipmentBladeBiosCapProviderEntry 5 }

cucsEquipmentBladeBiosCapProviderMgmtPlaneVer OBJECT-TYPE
    SYNTAX       SnmpAdminString
    MAX-ACCESS   read-only
    STATUS       current
    DESCRIPTION
        "Cisco UCS equipment:BladeBiosCapProvider:mgmtPlaneVer
        managed object property"
    ::= { cucsEquipmentBladeBiosCapProviderEntry 6 }

cucsEquipmentBladeBiosCapProviderModel OBJECT-TYPE
    SYNTAX       SnmpAdminString
    MAX-ACCESS   read-only
    STATUS       current
    DESCRIPTION
        "Cisco UCS equipment:BladeBiosCapProvider:model
        managed object property"
    ::= { cucsEquipmentBladeBiosCapProviderEntry 7 }

cucsEquipmentBladeBiosCapProviderRevision OBJECT-TYPE
    SYNTAX       SnmpAdminString
    MAX-ACCESS   read-only
    STATUS       current
    DESCRIPTION
        "Cisco UCS equipment:BladeBiosCapProvider:revision
        managed object property"
    ::= { cucsEquipmentBladeBiosCapProviderEntry 8 }

cucsEquipmentBladeBiosCapProviderVendor OBJECT-TYPE
    SYNTAX       SnmpAdminString
    MAX-ACCESS   read-only
    STATUS       current
    DESCRIPTION
        "Cisco UCS equipment:BladeBiosCapProvider:vendor
        managed object property"
    ::= { cucsEquipmentBladeBiosCapProviderEntry 9 }

cucsEquipmentBladeBiosCapProviderProductName OBJECT-TYPE
    SYNTAX       SnmpAdminString
    MAX-ACCESS   read-only
    STATUS       current
    DESCRIPTION
        "Cisco UCS equipment:BladeBiosCapProvider:productName
        managed object property"
    ::= { cucsEquipmentBladeBiosCapProviderEntry 10 }

cucsEquipmentBladeBiosCapProviderPromCardType OBJECT-TYPE
    SYNTAX       Gauge32
    MAX-ACCESS   read-only
    STATUS       current
    DESCRIPTION
        "Cisco UCS equipment:BladeBiosCapProvider:promCardType
        managed object property"
    ::= { cucsEquipmentBladeBiosCapProviderEntry 11 }

cucsEquipmentBladeBiosCapProviderDeleted OBJECT-TYPE
    SYNTAX       TruthValue
    MAX-ACCESS   read-only
    STATUS       current
    DESCRIPTION
        "Cisco UCS equipment:BladeBiosCapProvider:deleted
        managed object property"
    ::= { cucsEquipmentBladeBiosCapProviderEntry 12 }

cucsEquipmentBladeBiosCapProviderElementLoadFailures OBJECT-TYPE
    SYNTAX       Gauge32
    MAX-ACCESS   read-only
    STATUS       current
    DESCRIPTION
        "Cisco UCS equipment:BladeBiosCapProvider:elementLoadFailures
        managed object property"
    ::= { cucsEquipmentBladeBiosCapProviderEntry 13 }

cucsEquipmentBladeBiosCapProviderElementsLoaded OBJECT-TYPE
    SYNTAX       Gauge32
    MAX-ACCESS   read-only
    STATUS       current
    DESCRIPTION
        "Cisco UCS equipment:BladeBiosCapProvider:elementsLoaded
        managed object property"
    ::= { cucsEquipmentBladeBiosCapProviderEntry 14 }

cucsEquipmentBladeBiosCapProviderLoadErrors OBJECT-TYPE
    SYNTAX       Gauge32
    MAX-ACCESS   read-only
    STATUS       current
    DESCRIPTION
        "Cisco UCS equipment:BladeBiosCapProvider:loadErrors
        managed object property"
    ::= { cucsEquipmentBladeBiosCapProviderEntry 15 }

cucsEquipmentBladeBiosCapProviderLoadWarnings OBJECT-TYPE
    SYNTAX       Gauge32
    MAX-ACCESS   read-only
    STATUS       current
    DESCRIPTION
        "Cisco UCS equipment:BladeBiosCapProvider:loadWarnings
        managed object property"
    ::= { cucsEquipmentBladeBiosCapProviderEntry 16 }

cucsEquipmentBladeCapProviderTable OBJECT-TYPE
    SYNTAX           SEQUENCE OF CucsEquipmentBladeCapProviderEntry
    MAX-ACCESS       not-accessible
    STATUS           current
    DESCRIPTION
        "Cisco UCS equipment:BladeCapProvider managed object table"
    ::= { cucsEquipmentObjects 4 }

cucsEquipmentBladeCapProviderEntry OBJECT-TYPE
    SYNTAX           CucsEquipmentBladeCapProviderEntry
    MAX-ACCESS       not-accessible
    STATUS           current
    DESCRIPTION
        "Entry for the cucsEquipmentBladeCapProviderTable table."
    INDEX { cucsEquipmentBladeCapProviderInstanceId }
    ::= { cucsEquipmentBladeCapProviderTable 1 }

CucsEquipmentBladeCapProviderEntry ::= SEQUENCE {
    cucsEquipmentBladeCapProviderInstanceId                          CucsManagedObjectId,
    cucsEquipmentBladeCapProviderDn                                  CucsManagedObjectDn,
    cucsEquipmentBladeCapProviderRn                                  SnmpAdminString,
    cucsEquipmentBladeCapProviderDeprecated                          TruthValue,
    cucsEquipmentBladeCapProviderGencount                            Gauge32,
    cucsEquipmentBladeCapProviderMgmtPlaneVer                        SnmpAdminString,
    cucsEquipmentBladeCapProviderModel                               SnmpAdminString,
    cucsEquipmentBladeCapProviderRevision                            SnmpAdminString,
    cucsEquipmentBladeCapProviderVendor                              SnmpAdminString,
    cucsEquipmentBladeCapProviderPromCardType                        Gauge32,
    cucsEquipmentBladeCapProviderDeleted                             TruthValue,
    cucsEquipmentBladeCapProviderElementLoadFailures                 Gauge32,
    cucsEquipmentBladeCapProviderElementsLoaded                      Gauge32,
    cucsEquipmentBladeCapProviderLoadErrors                          Gauge32,
    cucsEquipmentBladeCapProviderLoadWarnings                        Gauge32,
    cucsEquipmentBladeCapProviderGeneration                          Gauge32
}

cucsEquipmentBladeCapProviderInstanceId OBJECT-TYPE
    SYNTAX       CucsManagedObjectId
    MAX-ACCESS   not-accessible
    STATUS       current
    DESCRIPTION
        "Instance identifier of the managed object."
    ::= { cucsEquipmentBladeCapProviderEntry 1 }

cucsEquipmentBladeCapProviderDn OBJECT-TYPE
    SYNTAX       CucsManagedObjectDn
    MAX-ACCESS   read-only
    STATUS       current
    DESCRIPTION
        "Cisco UCS equipment:BladeCapProvider:dn managed object property"
    ::= { cucsEquipmentBladeCapProviderEntry 2 }

cucsEquipmentBladeCapProviderRn OBJECT-TYPE
    SYNTAX       SnmpAdminString
    MAX-ACCESS   read-only
    STATUS       current
    DESCRIPTION
        "Cisco UCS equipment:BladeCapProvider:rn managed object property"
    ::= { cucsEquipmentBladeCapProviderEntry 3 }

cucsEquipmentBladeCapProviderDeprecated OBJECT-TYPE
    SYNTAX       TruthValue
    MAX-ACCESS   read-only
    STATUS       current
    DESCRIPTION
        "Cisco UCS equipment:BladeCapProvider:deprecated
        managed object property"
    ::= { cucsEquipmentBladeCapProviderEntry 4 }

cucsEquipmentBladeCapProviderGencount OBJECT-TYPE
    SYNTAX       Gauge32
    MAX-ACCESS   read-only
    STATUS       current
    DESCRIPTION
        "Cisco UCS equipment:BladeCapProvider:gencount
        managed object property"
    ::= { cucsEquipmentBladeCapProviderEntry 5 }

cucsEquipmentBladeCapProviderMgmtPlaneVer OBJECT-TYPE
    SYNTAX       SnmpAdminString
    MAX-ACCESS   read-only
    STATUS       current
    DESCRIPTION
        "Cisco UCS equipment:BladeCapProvider:mgmtPlaneVer
        managed object property"
    ::= { cucsEquipmentBladeCapProviderEntry 6 }

cucsEquipmentBladeCapProviderModel OBJECT-TYPE
    SYNTAX       SnmpAdminString
    MAX-ACCESS   read-only
    STATUS       current
    DESCRIPTION
        "Cisco UCS equipment:BladeCapProvider:model managed
        object property"
    ::= { cucsEquipmentBladeCapProviderEntry 7 }

cucsEquipmentBladeCapProviderRevision OBJECT-TYPE
    SYNTAX       SnmpAdminString
    MAX-ACCESS   read-only
    STATUS       current
    DESCRIPTION
        "Cisco UCS equipment:BladeCapProvider:revision
        managed object property"
    ::= { cucsEquipmentBladeCapProviderEntry 8 }

cucsEquipmentBladeCapProviderVendor OBJECT-TYPE
    SYNTAX       SnmpAdminString
    MAX-ACCESS   read-only
    STATUS       current
    DESCRIPTION
        "Cisco UCS equipment:BladeCapProvider:vendor managed
        object property"
    ::= { cucsEquipmentBladeCapProviderEntry 9 }

cucsEquipmentBladeCapProviderPromCardType OBJECT-TYPE
    SYNTAX       Gauge32
    MAX-ACCESS   read-only
    STATUS       current
    DESCRIPTION
        "Cisco UCS equipment:BladeCapProvider:promCardType
        managed object property"
    ::= { cucsEquipmentBladeCapProviderEntry 10 }

cucsEquipmentBladeCapProviderDeleted OBJECT-TYPE
    SYNTAX       TruthValue
    MAX-ACCESS   read-only
    STATUS       current
    DESCRIPTION
        "Cisco UCS equipment:BladeCapProvider:deleted managed
        object property"
    ::= { cucsEquipmentBladeCapProviderEntry 11 }

cucsEquipmentBladeCapProviderElementLoadFailures OBJECT-TYPE
    SYNTAX       Gauge32
    MAX-ACCESS   read-only
    STATUS       current
    DESCRIPTION
        "Cisco UCS equipment:BladeCapProvider:elementLoadFailures
        managed object property"
    ::= { cucsEquipmentBladeCapProviderEntry 12 }

cucsEquipmentBladeCapProviderElementsLoaded OBJECT-TYPE
    SYNTAX       Gauge32
    MAX-ACCESS   read-only
    STATUS       current
    DESCRIPTION
        "Cisco UCS equipment:BladeCapProvider:elementsLoaded
        managed object property"
    ::= { cucsEquipmentBladeCapProviderEntry 13 }

cucsEquipmentBladeCapProviderLoadErrors OBJECT-TYPE
    SYNTAX       Gauge32
    MAX-ACCESS   read-only
    STATUS       current
    DESCRIPTION
        "Cisco UCS equipment:BladeCapProvider:loadErrors
        managed object property"
    ::= { cucsEquipmentBladeCapProviderEntry 14 }

cucsEquipmentBladeCapProviderLoadWarnings OBJECT-TYPE
    SYNTAX       Gauge32
    MAX-ACCESS   read-only
    STATUS       current
    DESCRIPTION
        "Cisco UCS equipment:BladeCapProvider:loadWarnings
        managed object property"
    ::= { cucsEquipmentBladeCapProviderEntry 15 }

cucsEquipmentBladeCapProviderGeneration OBJECT-TYPE
    SYNTAX       Gauge32
    MAX-ACCESS   read-only
    STATUS       current
    DESCRIPTION
        "Cisco UCS equipment:BladeCapProvider:generation
        managed object property"
    ::= { cucsEquipmentBladeCapProviderEntry 16 }

cucsEquipmentBladeCapProviderTypeDefTable OBJECT-TYPE
    SYNTAX           SEQUENCE OF CucsEquipmentBladeCapProviderTypeDefEntry
    MAX-ACCESS       not-accessible
    STATUS           current
    DESCRIPTION
        "Cisco UCS equipment:BladeCapProviderTypeDef managed object table"
    ::= { cucsEquipmentObjects 154 }

cucsEquipmentBladeCapProviderTypeDefEntry OBJECT-TYPE
    SYNTAX           CucsEquipmentBladeCapProviderTypeDefEntry
    MAX-ACCESS       not-accessible
    STATUS           current
    DESCRIPTION
        "Entry for the cucsEquipmentBladeCapProviderTypeDefTable table."
    INDEX { cucsEquipmentBladeCapProviderTypeDefInstanceId }
    ::= { cucsEquipmentBladeCapProviderTypeDefTable 1 }

CucsEquipmentBladeCapProviderTypeDefEntry ::= SEQUENCE {
    cucsEquipmentBladeCapProviderTypeDefInstanceId                   CucsManagedObjectId,
    cucsEquipmentBladeCapProviderTypeDefDn                           CucsManagedObjectDn,
    cucsEquipmentBladeCapProviderTypeDefRn                           SnmpAdminString,
    cucsEquipmentBladeCapProviderTypeDefNumAdapterSlots              Gauge32,
    cucsEquipmentBladeCapProviderTypeDefNumSlots                     Gauge32
}

cucsEquipmentBladeCapProviderTypeDefInstanceId OBJECT-TYPE
    SYNTAX       CucsManagedObjectId
    MAX-ACCESS   not-accessible
    STATUS       current
    DESCRIPTION
        "Instance identifier of the managed object."
    ::= { cucsEquipmentBladeCapProviderTypeDefEntry 1 }

cucsEquipmentBladeCapProviderTypeDefDn OBJECT-TYPE
    SYNTAX       CucsManagedObjectDn
    MAX-ACCESS   read-only
    STATUS       current
    DESCRIPTION
        "Cisco UCS equipment:BladeCapProviderTypeDef:dn
        managed object property"
    ::= { cucsEquipmentBladeCapProviderTypeDefEntry 2 }

cucsEquipmentBladeCapProviderTypeDefRn OBJECT-TYPE
    SYNTAX       SnmpAdminString
    MAX-ACCESS   read-only
    STATUS       current
    DESCRIPTION
        "Cisco UCS equipment:BladeCapProviderTypeDef:rn
        managed object property"
    ::= { cucsEquipmentBladeCapProviderTypeDefEntry 3 }

cucsEquipmentBladeCapProviderTypeDefNumAdapterSlots OBJECT-TYPE
    SYNTAX       Gauge32
    MAX-ACCESS   read-only
    STATUS       current
    DESCRIPTION
        "Cisco UCS equipment:BladeCapProviderTypeDef:numAdapterSlots
        managed object property"
    ::= { cucsEquipmentBladeCapProviderTypeDefEntry 4 }

cucsEquipmentBladeCapProviderTypeDefNumSlots OBJECT-TYPE
    SYNTAX       Gauge32
    MAX-ACCESS   read-only
    STATUS       current
    DESCRIPTION
        "Cisco UCS equipment:BladeCapProviderTypeDef:numSlots
        managed object property"
    ::= { cucsEquipmentBladeCapProviderTypeDefEntry 5 }

cucsEquipmentBladeConnDefTable OBJECT-TYPE
    SYNTAX           SEQUENCE OF CucsEquipmentBladeConnDefEntry
    MAX-ACCESS       not-accessible
    STATUS           current
    DESCRIPTION
        "Cisco UCS equipment:BladeConnDef managed object table"
    ::= { cucsEquipmentObjects 97 }

cucsEquipmentBladeConnDefEntry OBJECT-TYPE
    SYNTAX           CucsEquipmentBladeConnDefEntry
    MAX-ACCESS       not-accessible
    STATUS           current
    DESCRIPTION
        "Entry for the cucsEquipmentBladeConnDefTable table."
    INDEX { cucsEquipmentBladeConnDefInstanceId }
    ::= { cucsEquipmentBladeConnDefTable 1 }

CucsEquipmentBladeConnDefEntry ::= SEQUENCE {
    cucsEquipmentBladeConnDefInstanceId                              CucsManagedObjectId,
    cucsEquipmentBladeConnDefDn                                      CucsManagedObjectDn,
    cucsEquipmentBladeConnDefRn                                      SnmpAdminString,
    cucsEquipmentBladeConnDefAdaptorFamily                           SnmpAdminString,
    cucsEquipmentBladeConnDefAdaptorSlotNumber                       Gauge32,
    cucsEquipmentBladeConnDefAdaptorSlotSpan                         Gauge32,
    cucsEquipmentBladeConnDefAdaptorType                             SnmpAdminString,
    cucsEquipmentBladeConnDefDescr                                   SnmpAdminString,
    cucsEquipmentBladeConnDefIntId                                   SnmpAdminString,
    cucsEquipmentBladeConnDefName                                    SnmpAdminString,
    cucsEquipmentBladeConnDefParentAdaptorSlotNum                    Gauge32,
    cucsEquipmentBladeConnDefSwitchPortMuxOffset                     Gauge32,
    cucsEquipmentBladeConnDefPolicyLevel                             Gauge32,
    cucsEquipmentBladeConnDefPolicyOwner                             CucsPolicyPolicyOwner
}

cucsEquipmentBladeConnDefInstanceId OBJECT-TYPE
    SYNTAX       CucsManagedObjectId
    MAX-ACCESS   not-accessible
    STATUS       current
    DESCRIPTION
        "Instance identifier of the managed object."
    ::= { cucsEquipmentBladeConnDefEntry 1 }

cucsEquipmentBladeConnDefDn OBJECT-TYPE
    SYNTAX       CucsManagedObjectDn
    MAX-ACCESS   read-only
    STATUS       current
    DESCRIPTION
        "Cisco UCS equipment:BladeConnDef:dn managed object property"
    ::= { cucsEquipmentBladeConnDefEntry 2 }

cucsEquipmentBladeConnDefRn OBJECT-TYPE
    SYNTAX       SnmpAdminString
    MAX-ACCESS   read-only
    STATUS       current
    DESCRIPTION
        "Cisco UCS equipment:BladeConnDef:rn managed object property"
    ::= { cucsEquipmentBladeConnDefEntry 3 }

cucsEquipmentBladeConnDefAdaptorFamily OBJECT-TYPE
    SYNTAX       SnmpAdminString
    MAX-ACCESS   read-only
    STATUS       current
    DESCRIPTION
        "Cisco UCS equipment:BladeConnDef:adaptorFamily
        managed object property"
    ::= { cucsEquipmentBladeConnDefEntry 4 }

cucsEquipmentBladeConnDefAdaptorSlotNumber OBJECT-TYPE
    SYNTAX       Gauge32
    MAX-ACCESS   read-only
    STATUS       current
    DESCRIPTION
        "Cisco UCS equipment:BladeConnDef:adaptorSlotNumber
        managed object property"
    ::= { cucsEquipmentBladeConnDefEntry 5 }

cucsEquipmentBladeConnDefAdaptorSlotSpan OBJECT-TYPE
    SYNTAX       Gauge32
    MAX-ACCESS   read-only
    STATUS       current
    DESCRIPTION
        "Cisco UCS equipment:BladeConnDef:adaptorSlotSpan
        managed object property"
    ::= { cucsEquipmentBladeConnDefEntry 6 }

cucsEquipmentBladeConnDefAdaptorType OBJECT-TYPE
    SYNTAX       SnmpAdminString
    MAX-ACCESS   read-only
    STATUS       current
    DESCRIPTION
        "Cisco UCS equipment:BladeConnDef:adaptorType managed
        object property"
    ::= { cucsEquipmentBladeConnDefEntry 7 }

cucsEquipmentBladeConnDefDescr OBJECT-TYPE
    SYNTAX       SnmpAdminString
    MAX-ACCESS   read-only
    STATUS       current
    DESCRIPTION
        "Cisco UCS equipment:BladeConnDef:descr managed object property"
    ::= { cucsEquipmentBladeConnDefEntry 8 }

cucsEquipmentBladeConnDefIntId OBJECT-TYPE
    SYNTAX       SnmpAdminString
    MAX-ACCESS   read-only
    STATUS       current
    DESCRIPTION
        "Cisco UCS equipment:BladeConnDef:intId managed object property"
    ::= { cucsEquipmentBladeConnDefEntry 9 }

cucsEquipmentBladeConnDefName OBJECT-TYPE
    SYNTAX       SnmpAdminString
    MAX-ACCESS   read-only
    STATUS       current
    DESCRIPTION
        "Cisco UCS equipment:BladeConnDef:name managed object property"
    ::= { cucsEquipmentBladeConnDefEntry 10 }

cucsEquipmentBladeConnDefParentAdaptorSlotNum OBJECT-TYPE
    SYNTAX       Gauge32
    MAX-ACCESS   read-only
    STATUS       current
    DESCRIPTION
        "Cisco UCS equipment:BladeConnDef:parentAdaptorSlotNum
        managed object property"
    ::= { cucsEquipmentBladeConnDefEntry 11 }

cucsEquipmentBladeConnDefSwitchPortMuxOffset OBJECT-TYPE
    SYNTAX       Gauge32
    MAX-ACCESS   read-only
    STATUS       current
    DESCRIPTION
        "Cisco UCS equipment:BladeConnDef:switchPortMuxOffset
        managed object property"
    ::= { cucsEquipmentBladeConnDefEntry 12 }

cucsEquipmentBladeConnDefPolicyLevel OBJECT-TYPE
    SYNTAX       Gauge32
    MAX-ACCESS   read-only
    STATUS       current
    DESCRIPTION
        "Cisco UCS equipment:BladeConnDef:policyLevel managed
        object property"
    ::= { cucsEquipmentBladeConnDefEntry 13 }

cucsEquipmentBladeConnDefPolicyOwner OBJECT-TYPE
    SYNTAX       CucsPolicyPolicyOwner
    MAX-ACCESS   read-only
    STATUS       current
    DESCRIPTION
        "Cisco UCS equipment:BladeConnDef:policyOwner managed
        object property"
    ::= { cucsEquipmentBladeConnDefEntry 14 }

cucsEquipmentBladeIOMConnDefTable OBJECT-TYPE
    SYNTAX           SEQUENCE OF CucsEquipmentBladeIOMConnDefEntry
    MAX-ACCESS       not-accessible
    STATUS           current
    DESCRIPTION
        "Cisco UCS equipment:BladeIOMConnDef managed object table"
    ::= { cucsEquipmentObjects 98 }

cucsEquipmentBladeIOMConnDefEntry OBJECT-TYPE
    SYNTAX           CucsEquipmentBladeIOMConnDefEntry
    MAX-ACCESS       not-accessible
    STATUS           current
    DESCRIPTION
        "Entry for the cucsEquipmentBladeIOMConnDefTable table."
    INDEX { cucsEquipmentBladeIOMConnDefInstanceId }
    ::= { cucsEquipmentBladeIOMConnDefTable 1 }

CucsEquipmentBladeIOMConnDefEntry ::= SEQUENCE {
    cucsEquipmentBladeIOMConnDefInstanceId                           CucsManagedObjectId,
    cucsEquipmentBladeIOMConnDefDn                                   CucsManagedObjectDn,
    cucsEquipmentBladeIOMConnDefRn                                   SnmpAdminString,
    cucsEquipmentBladeIOMConnDefDescr                                SnmpAdminString,
    cucsEquipmentBladeIOMConnDefIntId                                SnmpAdminString,
    cucsEquipmentBladeIOMConnDefIocardType                           SnmpAdminString,
    cucsEquipmentBladeIOMConnDefName                                 SnmpAdminString,
    cucsEquipmentBladeIOMConnDefPortBandwidth                        CucsPortEthSpeed,
    cucsEquipmentBladeIOMConnDefPolicyLevel                          Gauge32,
    cucsEquipmentBladeIOMConnDefPolicyOwner                          CucsPolicyPolicyOwner
}

cucsEquipmentBladeIOMConnDefInstanceId OBJECT-TYPE
    SYNTAX       CucsManagedObjectId
    MAX-ACCESS   not-accessible
    STATUS       current
    DESCRIPTION
        "Instance identifier of the managed object."
    ::= { cucsEquipmentBladeIOMConnDefEntry 1 }

cucsEquipmentBladeIOMConnDefDn OBJECT-TYPE
    SYNTAX       CucsManagedObjectDn
    MAX-ACCESS   read-only
    STATUS       current
    DESCRIPTION
        "Cisco UCS equipment:BladeIOMConnDef:dn managed object property"
    ::= { cucsEquipmentBladeIOMConnDefEntry 2 }

cucsEquipmentBladeIOMConnDefRn OBJECT-TYPE
    SYNTAX       SnmpAdminString
    MAX-ACCESS   read-only
    STATUS       current
    DESCRIPTION
        "Cisco UCS equipment:BladeIOMConnDef:rn managed object property"
    ::= { cucsEquipmentBladeIOMConnDefEntry 3 }

cucsEquipmentBladeIOMConnDefDescr OBJECT-TYPE
    SYNTAX       SnmpAdminString
    MAX-ACCESS   read-only
    STATUS       current
    DESCRIPTION
        "Cisco UCS equipment:BladeIOMConnDef:descr managed
        object property"
    ::= { cucsEquipmentBladeIOMConnDefEntry 4 }

cucsEquipmentBladeIOMConnDefIntId OBJECT-TYPE
    SYNTAX       SnmpAdminString
    MAX-ACCESS   read-only
    STATUS       current
    DESCRIPTION
        "Cisco UCS equipment:BladeIOMConnDef:intId managed
        object property"
    ::= { cucsEquipmentBladeIOMConnDefEntry 5 }

cucsEquipmentBladeIOMConnDefIocardType OBJECT-TYPE
    SYNTAX       SnmpAdminString
    MAX-ACCESS   read-only
    STATUS       current
    DESCRIPTION
        "Cisco UCS equipment:BladeIOMConnDef:iocardType
        managed object property"
    ::= { cucsEquipmentBladeIOMConnDefEntry 6 }

cucsEquipmentBladeIOMConnDefName OBJECT-TYPE
    SYNTAX       SnmpAdminString
    MAX-ACCESS   read-only
    STATUS       current
    DESCRIPTION
        "Cisco UCS equipment:BladeIOMConnDef:name managed object property"
    ::= { cucsEquipmentBladeIOMConnDefEntry 7 }

cucsEquipmentBladeIOMConnDefPortBandwidth OBJECT-TYPE
    SYNTAX       CucsPortEthSpeed
    MAX-ACCESS   read-only
    STATUS       current
    DESCRIPTION
        "Cisco UCS equipment:BladeIOMConnDef:portBandwidth
        managed object property"
    ::= { cucsEquipmentBladeIOMConnDefEntry 8 }

cucsEquipmentBladeIOMConnDefPolicyLevel OBJECT-TYPE
    SYNTAX       Gauge32
    MAX-ACCESS   read-only
    STATUS       current
    DESCRIPTION
        "Cisco UCS equipment:BladeIOMConnDef:policyLevel
        managed object property"
    ::= { cucsEquipmentBladeIOMConnDefEntry 9 }

cucsEquipmentBladeIOMConnDefPolicyOwner OBJECT-TYPE
    SYNTAX       CucsPolicyPolicyOwner
    MAX-ACCESS   read-only
    STATUS       current
    DESCRIPTION
        "Cisco UCS equipment:BladeIOMConnDef:policyOwner
        managed object property"
    ::= { cucsEquipmentBladeIOMConnDefEntry 10 }

cucsEquipmentBladeSwitchConnDefTable OBJECT-TYPE
    SYNTAX           SEQUENCE OF CucsEquipmentBladeSwitchConnDefEntry
    MAX-ACCESS       not-accessible
    STATUS           current
    DESCRIPTION
        "Cisco UCS equipment:BladeSwitchConnDef managed object table"
    ::= { cucsEquipmentObjects 130 }

cucsEquipmentBladeSwitchConnDefEntry OBJECT-TYPE
    SYNTAX           CucsEquipmentBladeSwitchConnDefEntry
    MAX-ACCESS       not-accessible
    STATUS           current
    DESCRIPTION
        "Entry for the cucsEquipmentBladeSwitchConnDefTable table."
    INDEX { cucsEquipmentBladeSwitchConnDefInstanceId }
    ::= { cucsEquipmentBladeSwitchConnDefTable 1 }

CucsEquipmentBladeSwitchConnDefEntry ::= SEQUENCE {
    cucsEquipmentBladeSwitchConnDefInstanceId                        CucsManagedObjectId,
    cucsEquipmentBladeSwitchConnDefDn                                CucsManagedObjectDn,
    cucsEquipmentBladeSwitchConnDefRn                                SnmpAdminString,
    cucsEquipmentBladeSwitchConnDefDescr                             SnmpAdminString,
    cucsEquipmentBladeSwitchConnDefIntId                             SnmpAdminString,
    cucsEquipmentBladeSwitchConnDefName                              SnmpAdminString,
    cucsEquipmentBladeSwitchConnDefPolicyLevel                       Gauge32,
    cucsEquipmentBladeSwitchConnDefPolicyOwner                       CucsPolicyPolicyOwner,
    cucsEquipmentBladeSwitchConnDefPortBandwidth                     CucsPortEthSpeed,
    cucsEquipmentBladeSwitchConnDefSwitchType                        SnmpAdminString
}

cucsEquipmentBladeSwitchConnDefInstanceId OBJECT-TYPE
    SYNTAX       CucsManagedObjectId
    MAX-ACCESS   not-accessible
    STATUS       current
    DESCRIPTION
        "Instance identifier of the managed object."
    ::= { cucsEquipmentBladeSwitchConnDefEntry 1 }

cucsEquipmentBladeSwitchConnDefDn OBJECT-TYPE
    SYNTAX       CucsManagedObjectDn
    MAX-ACCESS   read-only
    STATUS       current
    DESCRIPTION
        "Cisco UCS equipment:BladeSwitchConnDef:dn managed
        object property"
    ::= { cucsEquipmentBladeSwitchConnDefEntry 2 }

cucsEquipmentBladeSwitchConnDefRn OBJECT-TYPE
    SYNTAX       SnmpAdminString
    MAX-ACCESS   read-only
    STATUS       current
    DESCRIPTION
        "Cisco UCS equipment:BladeSwitchConnDef:rn managed
        object property"
    ::= { cucsEquipmentBladeSwitchConnDefEntry 3 }

cucsEquipmentBladeSwitchConnDefDescr OBJECT-TYPE
    SYNTAX       SnmpAdminString
    MAX-ACCESS   read-only
    STATUS       current
    DESCRIPTION
        "Cisco UCS equipment:BladeSwitchConnDef:descr managed
        object property"
    ::= { cucsEquipmentBladeSwitchConnDefEntry 4 }

cucsEquipmentBladeSwitchConnDefIntId OBJECT-TYPE
    SYNTAX       SnmpAdminString
    MAX-ACCESS   read-only
    STATUS       current
    DESCRIPTION
        "Cisco UCS equipment:BladeSwitchConnDef:intId managed
        object property"
    ::= { cucsEquipmentBladeSwitchConnDefEntry 5 }

cucsEquipmentBladeSwitchConnDefName OBJECT-TYPE
    SYNTAX       SnmpAdminString
    MAX-ACCESS   read-only
    STATUS       current
    DESCRIPTION
        "Cisco UCS equipment:BladeSwitchConnDef:name managed
        object property"
    ::= { cucsEquipmentBladeSwitchConnDefEntry 6 }

cucsEquipmentBladeSwitchConnDefPolicyLevel OBJECT-TYPE
    SYNTAX       Gauge32
    MAX-ACCESS   read-only
    STATUS       current
    DESCRIPTION
        "Cisco UCS equipment:BladeSwitchConnDef:policyLevel
        managed object property"
    ::= { cucsEquipmentBladeSwitchConnDefEntry 7 }

cucsEquipmentBladeSwitchConnDefPolicyOwner OBJECT-TYPE
    SYNTAX       CucsPolicyPolicyOwner
    MAX-ACCESS   read-only
    STATUS       current
    DESCRIPTION
        "Cisco UCS equipment:BladeSwitchConnDef:policyOwner
        managed object property"
    ::= { cucsEquipmentBladeSwitchConnDefEntry 8 }

cucsEquipmentBladeSwitchConnDefPortBandwidth OBJECT-TYPE
    SYNTAX       CucsPortEthSpeed
    MAX-ACCESS   read-only
    STATUS       current
    DESCRIPTION
        "Cisco UCS equipment:BladeSwitchConnDef:portBandwidth
        managed object property"
    ::= { cucsEquipmentBladeSwitchConnDefEntry 9 }

cucsEquipmentBladeSwitchConnDefSwitchType OBJECT-TYPE
    SYNTAX       SnmpAdminString
    MAX-ACCESS   read-only
    STATUS       current
    DESCRIPTION
        "Cisco UCS equipment:BladeSwitchConnDef:switchType
        managed object property"
    ::= { cucsEquipmentBladeSwitchConnDefEntry 10 }

cucsEquipmentBoardControllerDefTable OBJECT-TYPE
    SYNTAX           SEQUENCE OF CucsEquipmentBoardControllerDefEntry
    MAX-ACCESS       not-accessible
    STATUS           current
    DESCRIPTION
        "Cisco UCS equipment:BoardControllerDef managed object table"
    ::= { cucsEquipmentObjects 5 }

cucsEquipmentBoardControllerDefEntry OBJECT-TYPE
    SYNTAX           CucsEquipmentBoardControllerDefEntry
    MAX-ACCESS       not-accessible
    STATUS           current
    DESCRIPTION
        "Entry for the cucsEquipmentBoardControllerDefTable table."
    INDEX { cucsEquipmentBoardControllerDefInstanceId }
    ::= { cucsEquipmentBoardControllerDefTable 1 }

CucsEquipmentBoardControllerDefEntry ::= SEQUENCE {
    cucsEquipmentBoardControllerDefInstanceId                        CucsManagedObjectId,
    cucsEquipmentBoardControllerDefDn                                CucsManagedObjectDn,
    cucsEquipmentBoardControllerDefRn                                SnmpAdminString,
    cucsEquipmentBoardControllerDefDescr                             SnmpAdminString,
    cucsEquipmentBoardControllerDefIntId                             SnmpAdminString,
    cucsEquipmentBoardControllerDefName                              SnmpAdminString,
    cucsEquipmentBoardControllerDefPolicyLevel                       Gauge32,
    cucsEquipmentBoardControllerDefPolicyOwner                       CucsPolicyPolicyOwner
}

cucsEquipmentBoardControllerDefInstanceId OBJECT-TYPE
    SYNTAX       CucsManagedObjectId
    MAX-ACCESS   not-accessible
    STATUS       current
    DESCRIPTION
        "Instance identifier of the managed object."
    ::= { cucsEquipmentBoardControllerDefEntry 1 }

cucsEquipmentBoardControllerDefDn OBJECT-TYPE
    SYNTAX       CucsManagedObjectDn
    MAX-ACCESS   read-only
    STATUS       current
    DESCRIPTION
        "Cisco UCS equipment:BoardControllerDef:dn managed
        object property"
    ::= { cucsEquipmentBoardControllerDefEntry 2 }

cucsEquipmentBoardControllerDefRn OBJECT-TYPE
    SYNTAX       SnmpAdminString
    MAX-ACCESS   read-only
    STATUS       current
    DESCRIPTION
        "Cisco UCS equipment:BoardControllerDef:rn managed
        object property"
    ::= { cucsEquipmentBoardControllerDefEntry 3 }

cucsEquipmentBoardControllerDefDescr OBJECT-TYPE
    SYNTAX       SnmpAdminString
    MAX-ACCESS   read-only
    STATUS       current
    DESCRIPTION
        "Cisco UCS equipment:BoardControllerDef:descr managed
        object property"
    ::= { cucsEquipmentBoardControllerDefEntry 4 }

cucsEquipmentBoardControllerDefIntId OBJECT-TYPE
    SYNTAX       SnmpAdminString
    MAX-ACCESS   read-only
    STATUS       current
    DESCRIPTION
        "Cisco UCS equipment:BoardControllerDef:intId managed
        object property"
    ::= { cucsEquipmentBoardControllerDefEntry 5 }

cucsEquipmentBoardControllerDefName OBJECT-TYPE
    SYNTAX       SnmpAdminString
    MAX-ACCESS   read-only
    STATUS       current
    DESCRIPTION
        "Cisco UCS equipment:BoardControllerDef:name managed
        object property"
    ::= { cucsEquipmentBoardControllerDefEntry 6 }

cucsEquipmentBoardControllerDefPolicyLevel OBJECT-TYPE
    SYNTAX       Gauge32
    MAX-ACCESS   read-only
    STATUS       current
    DESCRIPTION
        "Cisco UCS equipment:BoardControllerDef:policyLevel
        managed object property"
    ::= { cucsEquipmentBoardControllerDefEntry 7 }

cucsEquipmentBoardControllerDefPolicyOwner OBJECT-TYPE
    SYNTAX       CucsPolicyPolicyOwner
    MAX-ACCESS   read-only
    STATUS       current
    DESCRIPTION
        "Cisco UCS equipment:BoardControllerDef:policyOwner
        managed object property"
    ::= { cucsEquipmentBoardControllerDefEntry 8 }

cucsEquipmentBootDeviceConstraintsTable OBJECT-TYPE
    SYNTAX           SEQUENCE OF CucsEquipmentBootDeviceConstraintsEntry
    MAX-ACCESS       not-accessible
    STATUS           current
    DESCRIPTION
        "Cisco UCS equipment:BootDeviceConstraints managed object table"
    ::= { cucsEquipmentObjects 204 }

cucsEquipmentBootDeviceConstraintsEntry OBJECT-TYPE
    SYNTAX           CucsEquipmentBootDeviceConstraintsEntry
    MAX-ACCESS       not-accessible
    STATUS           current
    DESCRIPTION
        "Entry for the cucsEquipmentBootDeviceConstraintsTable table."
    INDEX { cucsEquipmentBootDeviceConstraintsInstanceId }
    ::= { cucsEquipmentBootDeviceConstraintsTable 1 }

CucsEquipmentBootDeviceConstraintsEntry ::= SEQUENCE {
    cucsEquipmentBootDeviceConstraintsInstanceId                     CucsManagedObjectId,
    cucsEquipmentBootDeviceConstraintsDn                             CucsManagedObjectDn,
    cucsEquipmentBootDeviceConstraintsRn                             SnmpAdminString,
    cucsEquipmentBootDeviceConstraintsBootDevType                    CucsEquipmentBootDeviceType,
    cucsEquipmentBootDeviceConstraintsDescr                          SnmpAdminString,
    cucsEquipmentBootDeviceConstraintsIntId                          SnmpAdminString,
    cucsEquipmentBootDeviceConstraintsIsSupported                    TruthValue,
    cucsEquipmentBootDeviceConstraintsName                           SnmpAdminString,
    cucsEquipmentBootDeviceConstraintsPolicyLevel                    Gauge32,
    cucsEquipmentBootDeviceConstraintsPolicyOwner                    CucsPolicyPolicyOwner
}

cucsEquipmentBootDeviceConstraintsInstanceId OBJECT-TYPE
    SYNTAX       CucsManagedObjectId
    MAX-ACCESS   not-accessible
    STATUS       current
    DESCRIPTION
        "Instance identifier of the managed object."
    ::= { cucsEquipmentBootDeviceConstraintsEntry 1 }

cucsEquipmentBootDeviceConstraintsDn OBJECT-TYPE
    SYNTAX       CucsManagedObjectDn
    MAX-ACCESS   read-only
    STATUS       current
    DESCRIPTION
        "Cisco UCS equipment:BootDeviceConstraints:dn managed
        object property"
    ::= { cucsEquipmentBootDeviceConstraintsEntry 2 }

cucsEquipmentBootDeviceConstraintsRn OBJECT-TYPE
    SYNTAX       SnmpAdminString
    MAX-ACCESS   read-only
    STATUS       current
    DESCRIPTION
        "Cisco UCS equipment:BootDeviceConstraints:rn managed
        object property"
    ::= { cucsEquipmentBootDeviceConstraintsEntry 3 }

cucsEquipmentBootDeviceConstraintsBootDevType OBJECT-TYPE
    SYNTAX       CucsEquipmentBootDeviceType
    MAX-ACCESS   read-only
    STATUS       current
    DESCRIPTION
        "Cisco UCS equipment:BootDeviceConstraints:bootDevType
        managed object property"
    ::= { cucsEquipmentBootDeviceConstraintsEntry 4 }

cucsEquipmentBootDeviceConstraintsDescr OBJECT-TYPE
    SYNTAX       SnmpAdminString
    MAX-ACCESS   read-only
    STATUS       current
    DESCRIPTION
        "Cisco UCS equipment:BootDeviceConstraints:descr
        managed object property"
    ::= { cucsEquipmentBootDeviceConstraintsEntry 5 }

cucsEquipmentBootDeviceConstraintsIntId OBJECT-TYPE
    SYNTAX       SnmpAdminString
    MAX-ACCESS   read-only
    STATUS       current
    DESCRIPTION
        "Cisco UCS equipment:BootDeviceConstraints:intId
        managed object property"
    ::= { cucsEquipmentBootDeviceConstraintsEntry 6 }

cucsEquipmentBootDeviceConstraintsIsSupported OBJECT-TYPE
    SYNTAX       TruthValue
    MAX-ACCESS   read-only
    STATUS       current
    DESCRIPTION
        "Cisco UCS equipment:BootDeviceConstraints:isSupported
        managed object property"
    ::= { cucsEquipmentBootDeviceConstraintsEntry 7 }

cucsEquipmentBootDeviceConstraintsName OBJECT-TYPE
    SYNTAX       SnmpAdminString
    MAX-ACCESS   read-only
    STATUS       current
    DESCRIPTION
        "Cisco UCS equipment:BootDeviceConstraints:name
        managed object property"
    ::= { cucsEquipmentBootDeviceConstraintsEntry 8 }

cucsEquipmentBootDeviceConstraintsPolicyLevel OBJECT-TYPE
    SYNTAX       Gauge32
    MAX-ACCESS   read-only
    STATUS       current
    DESCRIPTION
        "Cisco UCS equipment:BootDeviceConstraints:policyLevel
        managed object property"
    ::= { cucsEquipmentBootDeviceConstraintsEntry 9 }

cucsEquipmentBootDeviceConstraintsPolicyOwner OBJECT-TYPE
    SYNTAX       CucsPolicyPolicyOwner
    MAX-ACCESS   read-only
    STATUS       current
    DESCRIPTION
        "Cisco UCS equipment:BootDeviceConstraints:policyOwner
        managed object property"
    ::= { cucsEquipmentBootDeviceConstraintsEntry 10 }

cucsEquipmentBreakoutCapTable OBJECT-TYPE
    SYNTAX           SEQUENCE OF CucsEquipmentBreakoutCapEntry
    MAX-ACCESS       not-accessible
    STATUS           current
    DESCRIPTION
        "Cisco UCS equipment:BreakoutCap managed object table"
    ::= { cucsEquipmentObjects 159 }

cucsEquipmentBreakoutCapEntry OBJECT-TYPE
    SYNTAX           CucsEquipmentBreakoutCapEntry
    MAX-ACCESS       not-accessible
    STATUS           current
    DESCRIPTION
        "Entry for the cucsEquipmentBreakoutCapTable table."
    INDEX { cucsEquipmentBreakoutCapInstanceId }
    ::= { cucsEquipmentBreakoutCapTable 1 }

CucsEquipmentBreakoutCapEntry ::= SEQUENCE {
    cucsEquipmentBreakoutCapInstanceId                               CucsManagedObjectId,
    cucsEquipmentBreakoutCapDn                                       CucsManagedObjectDn,
    cucsEquipmentBreakoutCapRn                                       SnmpAdminString,
    cucsEquipmentBreakoutCapName                                     SnmpAdminString,
    cucsEquipmentBreakoutCapPhyPortBitmask                           CucsEquipmentPortBitmask,
    cucsEquipmentBreakoutCapDescr                                    SnmpAdminString,
    cucsEquipmentBreakoutCapIntId                                    SnmpAdminString,
    cucsEquipmentBreakoutCapPolicyLevel                              Gauge32,
    cucsEquipmentBreakoutCapPolicyOwner                              CucsPolicyPolicyOwner
}

cucsEquipmentBreakoutCapInstanceId OBJECT-TYPE
    SYNTAX       CucsManagedObjectId
    MAX-ACCESS   not-accessible
    STATUS       current
    DESCRIPTION
        "Instance identifier of the managed object."
    ::= { cucsEquipmentBreakoutCapEntry 1 }

cucsEquipmentBreakoutCapDn OBJECT-TYPE
    SYNTAX       CucsManagedObjectDn
    MAX-ACCESS   read-only
    STATUS       current
    DESCRIPTION
        "Cisco UCS equipment:BreakoutCap:dn managed object property"
    ::= { cucsEquipmentBreakoutCapEntry 2 }

cucsEquipmentBreakoutCapRn OBJECT-TYPE
    SYNTAX       SnmpAdminString
    MAX-ACCESS   read-only
    STATUS       current
    DESCRIPTION
        "Cisco UCS equipment:BreakoutCap:rn managed object property"
    ::= { cucsEquipmentBreakoutCapEntry 3 }

cucsEquipmentBreakoutCapName OBJECT-TYPE
    SYNTAX       SnmpAdminString
    MAX-ACCESS   read-only
    STATUS       current
    DESCRIPTION
        "Cisco UCS equipment:BreakoutCap:name managed object property"
    ::= { cucsEquipmentBreakoutCapEntry 4 }

cucsEquipmentBreakoutCapPhyPortBitmask OBJECT-TYPE
    SYNTAX       CucsEquipmentPortBitmask
    MAX-ACCESS   read-only
    STATUS       current
    DESCRIPTION
        "Cisco UCS equipment:BreakoutCap:phyPortBitmask
        managed object property"
    ::= { cucsEquipmentBreakoutCapEntry 5 }

cucsEquipmentBreakoutCapDescr OBJECT-TYPE
    SYNTAX       SnmpAdminString
    MAX-ACCESS   read-only
    STATUS       current
    DESCRIPTION
        "Cisco UCS equipment:BreakoutCap:descr managed object property"
    ::= { cucsEquipmentBreakoutCapEntry 6 }

cucsEquipmentBreakoutCapIntId OBJECT-TYPE
    SYNTAX       SnmpAdminString
    MAX-ACCESS   read-only
    STATUS       current
    DESCRIPTION
        "Cisco UCS equipment:BreakoutCap:intId managed object property"
    ::= { cucsEquipmentBreakoutCapEntry 7 }

cucsEquipmentBreakoutCapPolicyLevel OBJECT-TYPE
    SYNTAX       Gauge32
    MAX-ACCESS   read-only
    STATUS       current
    DESCRIPTION
        "Cisco UCS equipment:BreakoutCap:policyLevel managed
        object property"
    ::= { cucsEquipmentBreakoutCapEntry 8 }

cucsEquipmentBreakoutCapPolicyOwner OBJECT-TYPE
    SYNTAX       CucsPolicyPolicyOwner
    MAX-ACCESS   read-only
    STATUS       current
    DESCRIPTION
        "Cisco UCS equipment:BreakoutCap:policyOwner managed
        object property"
    ::= { cucsEquipmentBreakoutCapEntry 9 }

cucsEquipmentCapModSpecTable OBJECT-TYPE
    SYNTAX           SEQUENCE OF CucsEquipmentCapModSpecEntry
    MAX-ACCESS       not-accessible
    STATUS           current
    DESCRIPTION
        "Cisco UCS equipment:CapModSpec managed object table"
    ::= { cucsEquipmentObjects 173 }

cucsEquipmentCapModSpecEntry OBJECT-TYPE
    SYNTAX           CucsEquipmentCapModSpecEntry
    MAX-ACCESS       not-accessible
    STATUS           current
    DESCRIPTION
        "Entry for the cucsEquipmentCapModSpecTable table."
    INDEX { cucsEquipmentCapModSpecInstanceId }
    ::= { cucsEquipmentCapModSpecTable 1 }

CucsEquipmentCapModSpecEntry ::= SEQUENCE {
    cucsEquipmentCapModSpecInstanceId                                CucsManagedObjectId,
    cucsEquipmentCapModSpecDn                                        CucsManagedObjectDn,
    cucsEquipmentCapModSpecRn                                        SnmpAdminString,
    cucsEquipmentCapModSpecPath                                      SnmpAdminString
}

cucsEquipmentCapModSpecInstanceId OBJECT-TYPE
    SYNTAX       CucsManagedObjectId
    MAX-ACCESS   not-accessible
    STATUS       current
    DESCRIPTION
        "Instance identifier of the managed object."
    ::= { cucsEquipmentCapModSpecEntry 1 }

cucsEquipmentCapModSpecDn OBJECT-TYPE
    SYNTAX       CucsManagedObjectDn
    MAX-ACCESS   read-only
    STATUS       current
    DESCRIPTION
        "Cisco UCS equipment:CapModSpec:dn managed object property"
    ::= { cucsEquipmentCapModSpecEntry 2 }

cucsEquipmentCapModSpecRn OBJECT-TYPE
    SYNTAX       SnmpAdminString
    MAX-ACCESS   read-only
    STATUS       current
    DESCRIPTION
        "Cisco UCS equipment:CapModSpec:rn managed object property"
    ::= { cucsEquipmentCapModSpecEntry 3 }

cucsEquipmentCapModSpecPath OBJECT-TYPE
    SYNTAX       SnmpAdminString
    MAX-ACCESS   read-only
    STATUS       current
    DESCRIPTION
        "Cisco UCS equipment:CapModSpec:path managed object property"
    ::= { cucsEquipmentCapModSpecEntry 4 }

cucsEquipmentCatalogCapProviderTable OBJECT-TYPE
    SYNTAX           SEQUENCE OF CucsEquipmentCatalogCapProviderEntry
    MAX-ACCESS       not-accessible
    STATUS           current
    DESCRIPTION
        "Cisco UCS equipment:CatalogCapProvider managed object table"
    ::= { cucsEquipmentObjects 6 }

cucsEquipmentCatalogCapProviderEntry OBJECT-TYPE
    SYNTAX           CucsEquipmentCatalogCapProviderEntry
    MAX-ACCESS       not-accessible
    STATUS           current
    DESCRIPTION
        "Entry for the cucsEquipmentCatalogCapProviderTable table."
    INDEX { cucsEquipmentCatalogCapProviderInstanceId }
    ::= { cucsEquipmentCatalogCapProviderTable 1 }

CucsEquipmentCatalogCapProviderEntry ::= SEQUENCE {
    cucsEquipmentCatalogCapProviderInstanceId                        CucsManagedObjectId,
    cucsEquipmentCatalogCapProviderDn                                CucsManagedObjectDn,
    cucsEquipmentCatalogCapProviderRn                                SnmpAdminString,
    cucsEquipmentCatalogCapProviderDeprecated                        TruthValue,
    cucsEquipmentCatalogCapProviderGencount                          Gauge32,
    cucsEquipmentCatalogCapProviderMgmtPlaneVer                      SnmpAdminString,
    cucsEquipmentCatalogCapProviderModel                             SnmpAdminString,
    cucsEquipmentCatalogCapProviderRevision                          SnmpAdminString,
    cucsEquipmentCatalogCapProviderVendor                            SnmpAdminString,
    cucsEquipmentCatalogCapProviderPromCardType                      Gauge32,
    cucsEquipmentCatalogCapProviderDeleted                           TruthValue,
    cucsEquipmentCatalogCapProviderElementLoadFailures               Gauge32,
    cucsEquipmentCatalogCapProviderElementsLoaded                    Gauge32,
    cucsEquipmentCatalogCapProviderLoadErrors                        Gauge32,
    cucsEquipmentCatalogCapProviderLoadWarnings                      Gauge32
}

cucsEquipmentCatalogCapProviderInstanceId OBJECT-TYPE
    SYNTAX       CucsManagedObjectId
    MAX-ACCESS   not-accessible
    STATUS       current
    DESCRIPTION
        "Instance identifier of the managed object."
    ::= { cucsEquipmentCatalogCapProviderEntry 1 }

cucsEquipmentCatalogCapProviderDn OBJECT-TYPE
    SYNTAX       CucsManagedObjectDn
    MAX-ACCESS   read-only
    STATUS       current
    DESCRIPTION
        "Cisco UCS equipment:CatalogCapProvider:dn managed
        object property"
    ::= { cucsEquipmentCatalogCapProviderEntry 2 }

cucsEquipmentCatalogCapProviderRn OBJECT-TYPE
    SYNTAX       SnmpAdminString
    MAX-ACCESS   read-only
    STATUS       current
    DESCRIPTION
        "Cisco UCS equipment:CatalogCapProvider:rn managed
        object property"
    ::= { cucsEquipmentCatalogCapProviderEntry 3 }

cucsEquipmentCatalogCapProviderDeprecated OBJECT-TYPE
    SYNTAX       TruthValue
    MAX-ACCESS   read-only
    STATUS       current
    DESCRIPTION
        "Cisco UCS equipment:CatalogCapProvider:deprecated
        managed object property"
    ::= { cucsEquipmentCatalogCapProviderEntry 4 }

cucsEquipmentCatalogCapProviderGencount OBJECT-TYPE
    SYNTAX       Gauge32
    MAX-ACCESS   read-only
    STATUS       current
    DESCRIPTION
        "Cisco UCS equipment:CatalogCapProvider:gencount
        managed object property"
    ::= { cucsEquipmentCatalogCapProviderEntry 5 }

cucsEquipmentCatalogCapProviderMgmtPlaneVer OBJECT-TYPE
    SYNTAX       SnmpAdminString
    MAX-ACCESS   read-only
    STATUS       current
    DESCRIPTION
        "Cisco UCS equipment:CatalogCapProvider:mgmtPlaneVer
        managed object property"
    ::= { cucsEquipmentCatalogCapProviderEntry 6 }

cucsEquipmentCatalogCapProviderModel OBJECT-TYPE
    SYNTAX       SnmpAdminString
    MAX-ACCESS   read-only
    STATUS       current
    DESCRIPTION
        "Cisco UCS equipment:CatalogCapProvider:model managed
        object property"
    ::= { cucsEquipmentCatalogCapProviderEntry 7 }

cucsEquipmentCatalogCapProviderRevision OBJECT-TYPE
    SYNTAX       SnmpAdminString
    MAX-ACCESS   read-only
    STATUS       current
    DESCRIPTION
        "Cisco UCS equipment:CatalogCapProvider:revision
        managed object property"
    ::= { cucsEquipmentCatalogCapProviderEntry 8 }

cucsEquipmentCatalogCapProviderVendor OBJECT-TYPE
    SYNTAX       SnmpAdminString
    MAX-ACCESS   read-only
    STATUS       current
    DESCRIPTION
        "Cisco UCS equipment:CatalogCapProvider:vendor
        managed object property"
    ::= { cucsEquipmentCatalogCapProviderEntry 9 }

cucsEquipmentCatalogCapProviderPromCardType OBJECT-TYPE
    SYNTAX       Gauge32
    MAX-ACCESS   read-only
    STATUS       current
    DESCRIPTION
        "Cisco UCS equipment:CatalogCapProvider:promCardType
        managed object property"
    ::= { cucsEquipmentCatalogCapProviderEntry 10 }

cucsEquipmentCatalogCapProviderDeleted OBJECT-TYPE
    SYNTAX       TruthValue
    MAX-ACCESS   read-only
    STATUS       current
    DESCRIPTION
        "Cisco UCS equipment:CatalogCapProvider:deleted
        managed object property"
    ::= { cucsEquipmentCatalogCapProviderEntry 11 }

cucsEquipmentCatalogCapProviderElementLoadFailures OBJECT-TYPE
    SYNTAX       Gauge32
    MAX-ACCESS   read-only
    STATUS       current
    DESCRIPTION
        "Cisco UCS equipment:CatalogCapProvider:elementLoadFailures
        managed object property"
    ::= { cucsEquipmentCatalogCapProviderEntry 12 }

cucsEquipmentCatalogCapProviderElementsLoaded OBJECT-TYPE
    SYNTAX       Gauge32
    MAX-ACCESS   read-only
    STATUS       current
    DESCRIPTION
        "Cisco UCS equipment:CatalogCapProvider:elementsLoaded
        managed object property"
    ::= { cucsEquipmentCatalogCapProviderEntry 13 }

cucsEquipmentCatalogCapProviderLoadErrors OBJECT-TYPE
    SYNTAX       Gauge32
    MAX-ACCESS   read-only
    STATUS       current
    DESCRIPTION
        "Cisco UCS equipment:CatalogCapProvider:loadErrors
        managed object property"
    ::= { cucsEquipmentCatalogCapProviderEntry 14 }

cucsEquipmentCatalogCapProviderLoadWarnings OBJECT-TYPE
    SYNTAX       Gauge32
    MAX-ACCESS   read-only
    STATUS       current
    DESCRIPTION
        "Cisco UCS equipment:CatalogCapProvider:loadWarnings
        managed object property"
    ::= { cucsEquipmentCatalogCapProviderEntry 15 }

cucsEquipmentChassisTable OBJECT-TYPE
    SYNTAX           SEQUENCE OF CucsEquipmentChassisEntry
    MAX-ACCESS       not-accessible
    STATUS           current
    DESCRIPTION
        "Cisco UCS equipment:Chassis managed object table"
    ::= { cucsEquipmentObjects 7 }

cucsEquipmentChassisEntry OBJECT-TYPE
    SYNTAX           CucsEquipmentChassisEntry
    MAX-ACCESS       not-accessible
    STATUS           current
    DESCRIPTION
        "Entry for the cucsEquipmentChassisTable table."
    INDEX { cucsEquipmentChassisInstanceId }
    ::= { cucsEquipmentChassisTable 1 }

CucsEquipmentChassisEntry ::= SEQUENCE {
    cucsEquipmentChassisInstanceId                                   CucsManagedObjectId,
    cucsEquipmentChassisDn                                           CucsManagedObjectDn,
    cucsEquipmentChassisRn                                           SnmpAdminString,
    cucsEquipmentChassisAdminState                                   CucsEquipmentChassisAdminState,
    cucsEquipmentChassisConfigState                                  CucsEquipmentChassisConfigState,
    cucsEquipmentChassisConnPath                                     CucsEquipmentConnectionStatus,
    cucsEquipmentChassisConnStatus                                   CucsEquipmentConnectionStatus,
    cucsEquipmentChassisFabricEpDn                                   SnmpAdminString,
    cucsEquipmentChassisFltAggr                                      Unsigned64,
    cucsEquipmentChassisFsmDescr                                     SnmpAdminString,
    cucsEquipmentChassisFsmPrev                                      SnmpAdminString,
    cucsEquipmentChassisFsmProgr                                     Gauge32,
    cucsEquipmentChassisFsmRmtInvErrCode                             Gauge32,
    cucsEquipmentChassisFsmRmtInvErrDescr                            SnmpAdminString,
    cucsEquipmentChassisFsmRmtInvRslt                                CucsConditionRemoteInvRslt,
    cucsEquipmentChassisFsmStageDescr                                SnmpAdminString,
    cucsEquipmentChassisFsmStamp                                     DateAndTime,
    cucsEquipmentChassisFsmStatus                                    SnmpAdminString,
    cucsEquipmentChassisFsmTry                                       Gauge32,
    cucsEquipmentChassisId                                           CucsEquipmentChassisId,
    cucsEquipmentChassisLcTs                                         DateAndTime,
    cucsEquipmentChassisLicGP                                        Unsigned64,
    cucsEquipmentChassisLicState                                     CucsLicenseState,
    cucsEquipmentChassisManagingInst                                 CucsNetworkSwitchId,
    cucsEquipmentChassisModel                                        SnmpAdminString,
    cucsEquipmentChassisOperQualifier                                CucsEquipmentChassisIssues,
    cucsEquipmentChassisOperState                                    CucsEquipmentOperability,
    cucsEquipmentChassisOperability                                  CucsEquipmentOperability,
    cucsEquipmentChassisPower                                        CucsEquipmentChassisPowerOperState,
    cucsEquipmentChassisPresence                                     CucsEquipmentPresence,
    cucsEquipmentChassisRevision                                     SnmpAdminString,
    cucsEquipmentChassisSerial                                       SnmpAdminString,
    cucsEquipmentChassisThermal                                      CucsEquipmentSensorThresholdStatus,
    cucsEquipmentChassisUsrLbl                                       SnmpAdminString,
    cucsEquipmentChassisVendor                                       SnmpAdminString,
    cucsEquipmentChassisVersionHolder                                TruthValue,
    cucsEquipmentChassisAckProgressIndicator                         CucsEquipmentChassisConfigProgressIndicator,
    cucsEquipmentChassisSeepromOperState                             CucsEquipmentOperability,
    cucsEquipmentChassisMfgTime                                      DateAndTime,
    cucsEquipmentChassisThermalStateQualifier                        SnmpAdminString,
    cucsEquipmentChassisOperQualifierReason                          SnmpAdminString,
    cucsEquipmentChassisPartNumber                                   SnmpAdminString,
    cucsEquipmentChassisVid                                          SnmpAdminString,
    cucsEquipmentChassisDiscoveryStatus                              CucsEquipmentConnectionStatus,
    cucsEquipmentChassisFsmFlags                                     SnmpAdminString,
    cucsEquipmentChassisAssignedToDn                                 SnmpAdminString,
    cucsEquipmentChassisAssociation                                  CucsEquipmentAssociation,
    cucsEquipmentChassisAvailability                                 CucsEquipmentAvailability,
    cucsEquipmentChassisDiscovery                                    CucsEquipmentDiscovery,
    cucsEquipmentChassisServiceState                                 CucsEquipmentServiceState,
    cucsEquipmentChassisAssetTag                                     SnmpAdminString
}

cucsEquipmentChassisInstanceId OBJECT-TYPE
    SYNTAX       CucsManagedObjectId
    MAX-ACCESS   not-accessible
    STATUS       current
    DESCRIPTION
        "Instance identifier of the managed object."
    ::= { cucsEquipmentChassisEntry 1 }

cucsEquipmentChassisDn OBJECT-TYPE
    SYNTAX       CucsManagedObjectDn
    MAX-ACCESS   read-only
    STATUS       current
    DESCRIPTION
        "Cisco UCS equipment:Chassis:dn managed object property"
    ::= { cucsEquipmentChassisEntry 2 }

cucsEquipmentChassisRn OBJECT-TYPE
    SYNTAX       SnmpAdminString
    MAX-ACCESS   read-only
    STATUS       current
    DESCRIPTION
        "Cisco UCS equipment:Chassis:rn managed object property"
    ::= { cucsEquipmentChassisEntry 3 }

cucsEquipmentChassisAdminState OBJECT-TYPE
    SYNTAX       CucsEquipmentChassisAdminState
    MAX-ACCESS   read-only
    STATUS       current
    DESCRIPTION
        "Cisco UCS equipment:Chassis:adminState managed object property"
    ::= { cucsEquipmentChassisEntry 4 }

cucsEquipmentChassisConfigState OBJECT-TYPE
    SYNTAX       CucsEquipmentChassisConfigState
    MAX-ACCESS   read-only
    STATUS       current
    DESCRIPTION
        "Cisco UCS equipment:Chassis:configState managed object property"
    ::= { cucsEquipmentChassisEntry 5 }

cucsEquipmentChassisConnPath OBJECT-TYPE
    SYNTAX       CucsEquipmentConnectionStatus
    MAX-ACCESS   read-only
    STATUS       current
    DESCRIPTION
        "Cisco UCS equipment:Chassis:connPath managed object property"
    ::= { cucsEquipmentChassisEntry 6 }

cucsEquipmentChassisConnStatus OBJECT-TYPE
    SYNTAX       CucsEquipmentConnectionStatus
    MAX-ACCESS   read-only
    STATUS       current
    DESCRIPTION
        "Cisco UCS equipment:Chassis:connStatus managed object property"
    ::= { cucsEquipmentChassisEntry 7 }

cucsEquipmentChassisFabricEpDn OBJECT-TYPE
    SYNTAX       SnmpAdminString
    MAX-ACCESS   read-only
    STATUS       current
    DESCRIPTION
        "Cisco UCS equipment:Chassis:fabricEpDn managed object property"
    ::= { cucsEquipmentChassisEntry 8 }

cucsEquipmentChassisFltAggr OBJECT-TYPE
    SYNTAX       Unsigned64
    MAX-ACCESS   read-only
    STATUS       current
    DESCRIPTION
        "Cisco UCS equipment:Chassis:fltAggr managed object property"
    ::= { cucsEquipmentChassisEntry 9 }

cucsEquipmentChassisFsmDescr OBJECT-TYPE
    SYNTAX       SnmpAdminString
    MAX-ACCESS   read-only
    STATUS       current
    DESCRIPTION
        "Cisco UCS equipment:Chassis:fsmDescr managed object property"
    ::= { cucsEquipmentChassisEntry 10 }

cucsEquipmentChassisFsmPrev OBJECT-TYPE
    SYNTAX       SnmpAdminString
    MAX-ACCESS   read-only
    STATUS       current
    DESCRIPTION
        "Cisco UCS equipment:Chassis:fsmPrev managed object property"
    ::= { cucsEquipmentChassisEntry 11 }

cucsEquipmentChassisFsmProgr OBJECT-TYPE
    SYNTAX       Gauge32
    MAX-ACCESS   read-only
    STATUS       current
    DESCRIPTION
        "Cisco UCS equipment:Chassis:fsmProgr managed object property"
    ::= { cucsEquipmentChassisEntry 12 }

cucsEquipmentChassisFsmRmtInvErrCode OBJECT-TYPE
    SYNTAX       Gauge32
    MAX-ACCESS   read-only
    STATUS       current
    DESCRIPTION
        "Cisco UCS equipment:Chassis:fsmRmtInvErrCode managed
        object property"
    ::= { cucsEquipmentChassisEntry 13 }

cucsEquipmentChassisFsmRmtInvErrDescr OBJECT-TYPE
    SYNTAX       SnmpAdminString
    MAX-ACCESS   read-only
    STATUS       current
    DESCRIPTION
        "Cisco UCS equipment:Chassis:fsmRmtInvErrDescr
        managed object property"
    ::= { cucsEquipmentChassisEntry 14 }

cucsEquipmentChassisFsmRmtInvRslt OBJECT-TYPE
    SYNTAX       CucsConditionRemoteInvRslt
    MAX-ACCESS   read-only
    STATUS       current
    DESCRIPTION
        "Cisco UCS equipment:Chassis:fsmRmtInvRslt managed
        object property"
    ::= { cucsEquipmentChassisEntry 15 }

cucsEquipmentChassisFsmStageDescr OBJECT-TYPE
    SYNTAX       SnmpAdminString
    MAX-ACCESS   read-only
    STATUS       current
    DESCRIPTION
        "Cisco UCS equipment:Chassis:fsmStageDescr managed
        object property"
    ::= { cucsEquipmentChassisEntry 16 }

cucsEquipmentChassisFsmStamp OBJECT-TYPE
    SYNTAX       DateAndTime
    MAX-ACCESS   read-only
    STATUS       current
    DESCRIPTION
        "Cisco UCS equipment:Chassis:fsmStamp managed object property"
    ::= { cucsEquipmentChassisEntry 17 }

cucsEquipmentChassisFsmStatus OBJECT-TYPE
    SYNTAX       SnmpAdminString
    MAX-ACCESS   read-only
    STATUS       current
    DESCRIPTION
        "Cisco UCS equipment:Chassis:fsmStatus managed object property"
    ::= { cucsEquipmentChassisEntry 18 }

cucsEquipmentChassisFsmTry OBJECT-TYPE
    SYNTAX       Gauge32
    MAX-ACCESS   read-only
    STATUS       current
    DESCRIPTION
        "Cisco UCS equipment:Chassis:fsmTry managed object property"
    ::= { cucsEquipmentChassisEntry 19 }

cucsEquipmentChassisId OBJECT-TYPE
    SYNTAX       CucsEquipmentChassisId
    MAX-ACCESS   read-only
    STATUS       current
    DESCRIPTION
        "Cisco UCS equipment:Chassis:id managed object property"
    ::= { cucsEquipmentChassisEntry 20 }

cucsEquipmentChassisLcTs OBJECT-TYPE
    SYNTAX       DateAndTime
    MAX-ACCESS   read-only
    STATUS       current
    DESCRIPTION
        "Cisco UCS equipment:Chassis:lcTs managed object property"
    ::= { cucsEquipmentChassisEntry 21 }

cucsEquipmentChassisLicGP OBJECT-TYPE
    SYNTAX       Unsigned64
    MAX-ACCESS   read-only
    STATUS       current
    DESCRIPTION
        "Cisco UCS equipment:Chassis:licGP managed object property"
    ::= { cucsEquipmentChassisEntry 22 }

cucsEquipmentChassisLicState OBJECT-TYPE
    SYNTAX       CucsLicenseState
    MAX-ACCESS   read-only
    STATUS       current
    DESCRIPTION
        "Cisco UCS equipment:Chassis:licState managed object property"
    ::= { cucsEquipmentChassisEntry 23 }

cucsEquipmentChassisManagingInst OBJECT-TYPE
    SYNTAX       CucsNetworkSwitchId
    MAX-ACCESS   read-only
    STATUS       current
    DESCRIPTION
        "Cisco UCS equipment:Chassis:managingInst managed object property"
    ::= { cucsEquipmentChassisEntry 24 }

cucsEquipmentChassisModel OBJECT-TYPE
    SYNTAX       SnmpAdminString
    MAX-ACCESS   read-only
    STATUS       current
    DESCRIPTION
        "Cisco UCS equipment:Chassis:model managed object property"
    ::= { cucsEquipmentChassisEntry 25 }

cucsEquipmentChassisOperQualifier OBJECT-TYPE
    SYNTAX       CucsEquipmentChassisIssues
    MAX-ACCESS   read-only
    STATUS       current
    DESCRIPTION
        "Cisco UCS equipment:Chassis:operQualifier managed
        object property"
    ::= { cucsEquipmentChassisEntry 26 }

cucsEquipmentChassisOperState OBJECT-TYPE
    SYNTAX       CucsEquipmentOperability
    MAX-ACCESS   read-only
    STATUS       current
    DESCRIPTION
        "Cisco UCS equipment:Chassis:operState managed object property"
    ::= { cucsEquipmentChassisEntry 27 }

cucsEquipmentChassisOperability OBJECT-TYPE
    SYNTAX       CucsEquipmentOperability
    MAX-ACCESS   read-only
    STATUS       current
    DESCRIPTION
        "Cisco UCS equipment:Chassis:operability managed object property"
    ::= { cucsEquipmentChassisEntry 28 }

cucsEquipmentChassisPower OBJECT-TYPE
    SYNTAX       CucsEquipmentChassisPowerOperState
    MAX-ACCESS   read-only
    STATUS       current
    DESCRIPTION
        "Cisco UCS equipment:Chassis:power managed object property"
    ::= { cucsEquipmentChassisEntry 29 }

cucsEquipmentChassisPresence OBJECT-TYPE
    SYNTAX       CucsEquipmentPresence
    MAX-ACCESS   read-only
    STATUS       current
    DESCRIPTION
        "Cisco UCS equipment:Chassis:presence managed object property"
    ::= { cucsEquipmentChassisEntry 30 }

cucsEquipmentChassisRevision OBJECT-TYPE
    SYNTAX       SnmpAdminString
    MAX-ACCESS   read-only
    STATUS       current
    DESCRIPTION
        "Cisco UCS equipment:Chassis:revision managed object property"
    ::= { cucsEquipmentChassisEntry 31 }

cucsEquipmentChassisSerial OBJECT-TYPE
    SYNTAX       SnmpAdminString
    MAX-ACCESS   read-only
    STATUS       current
    DESCRIPTION
        "Cisco UCS equipment:Chassis:serial managed object property"
    ::= { cucsEquipmentChassisEntry 32 }

cucsEquipmentChassisThermal OBJECT-TYPE
    SYNTAX       CucsEquipmentSensorThresholdStatus
    MAX-ACCESS   read-only
    STATUS       current
    DESCRIPTION
        "Cisco UCS equipment:Chassis:thermal managed object property"
    ::= { cucsEquipmentChassisEntry 33 }

cucsEquipmentChassisUsrLbl OBJECT-TYPE
    SYNTAX       SnmpAdminString
    MAX-ACCESS   read-only
    STATUS       current
    DESCRIPTION
        "Cisco UCS equipment:Chassis:usrLbl managed object property"
    ::= { cucsEquipmentChassisEntry 34 }

cucsEquipmentChassisVendor OBJECT-TYPE
    SYNTAX       SnmpAdminString
    MAX-ACCESS   read-only
    STATUS       current
    DESCRIPTION
        "Cisco UCS equipment:Chassis:vendor managed object property"
    ::= { cucsEquipmentChassisEntry 35 }

cucsEquipmentChassisVersionHolder OBJECT-TYPE
    SYNTAX       TruthValue
    MAX-ACCESS   read-only
    STATUS       current
    DESCRIPTION
        "Cisco UCS equipment:Chassis:versionHolder managed
        object property"
    ::= { cucsEquipmentChassisEntry 36 }

cucsEquipmentChassisAckProgressIndicator OBJECT-TYPE
    SYNTAX       CucsEquipmentChassisConfigProgressIndicator
    MAX-ACCESS   read-only
    STATUS       current
    DESCRIPTION
        "Cisco UCS equipment:Chassis:ackProgressIndicator
        managed object property"
    ::= { cucsEquipmentChassisEntry 37 }

cucsEquipmentChassisSeepromOperState OBJECT-TYPE
    SYNTAX       CucsEquipmentOperability
    MAX-ACCESS   read-only
    STATUS       current
    DESCRIPTION
        "Cisco UCS equipment:Chassis:seepromOperState managed
        object property"
    ::= { cucsEquipmentChassisEntry 38 }

cucsEquipmentChassisMfgTime OBJECT-TYPE
    SYNTAX       DateAndTime
    MAX-ACCESS   read-only
    STATUS       current
    DESCRIPTION
        "Cisco UCS equipment:Chassis:mfgTime managed object property"
    ::= { cucsEquipmentChassisEntry 39 }

cucsEquipmentChassisThermalStateQualifier OBJECT-TYPE
    SYNTAX       SnmpAdminString
    MAX-ACCESS   read-only
    STATUS       current
    DESCRIPTION
        "Cisco UCS equipment:Chassis:thermalStateQualifier
        managed object property"
    ::= { cucsEquipmentChassisEntry 40 }

cucsEquipmentChassisOperQualifierReason OBJECT-TYPE
    SYNTAX       SnmpAdminString
    MAX-ACCESS   read-only
    STATUS       current
    DESCRIPTION
        "Cisco UCS equipment:Chassis:operQualifierReason
        managed object property"
    ::= { cucsEquipmentChassisEntry 41 }

cucsEquipmentChassisPartNumber OBJECT-TYPE
    SYNTAX       SnmpAdminString
    MAX-ACCESS   read-only
    STATUS       current
    DESCRIPTION
        "Cisco UCS equipment:Chassis:partNumber managed object property"
    ::= { cucsEquipmentChassisEntry 42 }

cucsEquipmentChassisVid OBJECT-TYPE
    SYNTAX       SnmpAdminString
    MAX-ACCESS   read-only
    STATUS       current
    DESCRIPTION
        "Cisco UCS equipment:Chassis:vid managed object property"
    ::= { cucsEquipmentChassisEntry 43 }

cucsEquipmentChassisDiscoveryStatus OBJECT-TYPE
    SYNTAX       CucsEquipmentConnectionStatus
    MAX-ACCESS   read-only
    STATUS       current
    DESCRIPTION
        "Cisco UCS equipment:Chassis:discoveryStatus managed
        object property"
    ::= { cucsEquipmentChassisEntry 44 }

cucsEquipmentChassisFsmFlags OBJECT-TYPE
    SYNTAX       SnmpAdminString
    MAX-ACCESS   read-only
    STATUS       current
    DESCRIPTION
        "Cisco UCS equipment:Chassis:fsmFlags managed object property"
    ::= { cucsEquipmentChassisEntry 45 }

cucsEquipmentChassisAssignedToDn OBJECT-TYPE
    SYNTAX       SnmpAdminString
    MAX-ACCESS   read-only
    STATUS       current
    DESCRIPTION
        "Cisco UCS equipment:Chassis:assignedToDn managed object property"
    ::= { cucsEquipmentChassisEntry 46 }

cucsEquipmentChassisAssociation OBJECT-TYPE
    SYNTAX       CucsEquipmentAssociation
    MAX-ACCESS   read-only
    STATUS       current
    DESCRIPTION
        "Cisco UCS equipment:Chassis:association managed object property"
    ::= { cucsEquipmentChassisEntry 47 }

cucsEquipmentChassisAvailability OBJECT-TYPE
    SYNTAX       CucsEquipmentAvailability
    MAX-ACCESS   read-only
    STATUS       current
    DESCRIPTION
        "Cisco UCS equipment:Chassis:availability managed object property"
    ::= { cucsEquipmentChassisEntry 48 }

cucsEquipmentChassisDiscovery OBJECT-TYPE
    SYNTAX       CucsEquipmentDiscovery
    MAX-ACCESS   read-only
    STATUS       current
    DESCRIPTION
        "Cisco UCS equipment:Chassis:discovery managed object property"
    ::= { cucsEquipmentChassisEntry 49 }

cucsEquipmentChassisServiceState OBJECT-TYPE
    SYNTAX       CucsEquipmentServiceState
    MAX-ACCESS   read-only
    STATUS       current
    DESCRIPTION
        "Cisco UCS equipment:Chassis:serviceState managed object property"
    ::= { cucsEquipmentChassisEntry 50 }

cucsEquipmentChassisAssetTag OBJECT-TYPE
    SYNTAX       SnmpAdminString
    MAX-ACCESS   read-only
    STATUS       current
    DESCRIPTION
        "Cisco UCS equipment:Chassis:assetTag managed object property"
    ::= { cucsEquipmentChassisEntry 51 }

cucsEquipmentChassisAssocCtxTable OBJECT-TYPE
    SYNTAX           SEQUENCE OF CucsEquipmentChassisAssocCtxEntry
    MAX-ACCESS       not-accessible
    STATUS           current
    DESCRIPTION
        "Cisco UCS equipment:ChassisAssocCtx managed object table"
    ::= { cucsEquipmentObjects 179 }

cucsEquipmentChassisAssocCtxEntry OBJECT-TYPE
    SYNTAX           CucsEquipmentChassisAssocCtxEntry
    MAX-ACCESS       not-accessible
    STATUS           current
    DESCRIPTION
        "Entry for the cucsEquipmentChassisAssocCtxTable table."
    INDEX { cucsEquipmentChassisAssocCtxInstanceId }
    ::= { cucsEquipmentChassisAssocCtxTable 1 }

CucsEquipmentChassisAssocCtxEntry ::= SEQUENCE {
    cucsEquipmentChassisAssocCtxInstanceId                           CucsManagedObjectId,
    cucsEquipmentChassisAssocCtxDn                                   CucsManagedObjectDn,
    cucsEquipmentChassisAssocCtxRn                                   SnmpAdminString,
    cucsEquipmentChassisAssocCtxFruCapDn                             SnmpAdminString
}

cucsEquipmentChassisAssocCtxInstanceId OBJECT-TYPE
    SYNTAX       CucsManagedObjectId
    MAX-ACCESS   not-accessible
    STATUS       current
    DESCRIPTION
        "Instance identifier of the managed object."
    ::= { cucsEquipmentChassisAssocCtxEntry 1 }

cucsEquipmentChassisAssocCtxDn OBJECT-TYPE
    SYNTAX       CucsManagedObjectDn
    MAX-ACCESS   read-only
    STATUS       current
    DESCRIPTION
        "Cisco UCS equipment:ChassisAssocCtx:dn managed object property"
    ::= { cucsEquipmentChassisAssocCtxEntry 2 }

cucsEquipmentChassisAssocCtxRn OBJECT-TYPE
    SYNTAX       SnmpAdminString
    MAX-ACCESS   read-only
    STATUS       current
    DESCRIPTION
        "Cisco UCS equipment:ChassisAssocCtx:rn managed object property"
    ::= { cucsEquipmentChassisAssocCtxEntry 3 }

cucsEquipmentChassisAssocCtxFruCapDn OBJECT-TYPE
    SYNTAX       SnmpAdminString
    MAX-ACCESS   read-only
    STATUS       current
    DESCRIPTION
        "Cisco UCS equipment:ChassisAssocCtx:fruCapDn managed
        object property"
    ::= { cucsEquipmentChassisAssocCtxEntry 4 }

cucsEquipmentChassisCapProviderTable OBJECT-TYPE
    SYNTAX           SEQUENCE OF CucsEquipmentChassisCapProviderEntry
    MAX-ACCESS       not-accessible
    STATUS           current
    DESCRIPTION
        "Cisco UCS equipment:ChassisCapProvider managed object table"
    ::= { cucsEquipmentObjects 8 }

cucsEquipmentChassisCapProviderEntry OBJECT-TYPE
    SYNTAX           CucsEquipmentChassisCapProviderEntry
    MAX-ACCESS       not-accessible
    STATUS           current
    DESCRIPTION
        "Entry for the cucsEquipmentChassisCapProviderTable table."
    INDEX { cucsEquipmentChassisCapProviderInstanceId }
    ::= { cucsEquipmentChassisCapProviderTable 1 }

CucsEquipmentChassisCapProviderEntry ::= SEQUENCE {
    cucsEquipmentChassisCapProviderInstanceId                        CucsManagedObjectId,
    cucsEquipmentChassisCapProviderDn                                CucsManagedObjectDn,
    cucsEquipmentChassisCapProviderRn                                SnmpAdminString,
    cucsEquipmentChassisCapProviderDeprecated                        TruthValue,
    cucsEquipmentChassisCapProviderGencount                          Gauge32,
    cucsEquipmentChassisCapProviderMgmtPlaneVer                      SnmpAdminString,
    cucsEquipmentChassisCapProviderModel                             SnmpAdminString,
    cucsEquipmentChassisCapProviderRevision                          SnmpAdminString,
    cucsEquipmentChassisCapProviderVendor                            SnmpAdminString,
    cucsEquipmentChassisCapProviderPromCardType                      Gauge32,
    cucsEquipmentChassisCapProviderDeleted                           TruthValue,
    cucsEquipmentChassisCapProviderElementLoadFailures               Gauge32,
    cucsEquipmentChassisCapProviderElementsLoaded                    Gauge32,
    cucsEquipmentChassisCapProviderLoadErrors                        Gauge32,
    cucsEquipmentChassisCapProviderLoadWarnings                      Gauge32
}

cucsEquipmentChassisCapProviderInstanceId OBJECT-TYPE
    SYNTAX       CucsManagedObjectId
    MAX-ACCESS   not-accessible
    STATUS       current
    DESCRIPTION
        "Instance identifier of the managed object."
    ::= { cucsEquipmentChassisCapProviderEntry 1 }

cucsEquipmentChassisCapProviderDn OBJECT-TYPE
    SYNTAX       CucsManagedObjectDn
    MAX-ACCESS   read-only
    STATUS       current
    DESCRIPTION
        "Cisco UCS equipment:ChassisCapProvider:dn managed
        object property"
    ::= { cucsEquipmentChassisCapProviderEntry 2 }

cucsEquipmentChassisCapProviderRn OBJECT-TYPE
    SYNTAX       SnmpAdminString
    MAX-ACCESS   read-only
    STATUS       current
    DESCRIPTION
        "Cisco UCS equipment:ChassisCapProvider:rn managed
        object property"
    ::= { cucsEquipmentChassisCapProviderEntry 3 }

cucsEquipmentChassisCapProviderDeprecated OBJECT-TYPE
    SYNTAX       TruthValue
    MAX-ACCESS   read-only
    STATUS       current
    DESCRIPTION
        "Cisco UCS equipment:ChassisCapProvider:deprecated
        managed object property"
    ::= { cucsEquipmentChassisCapProviderEntry 4 }

cucsEquipmentChassisCapProviderGencount OBJECT-TYPE
    SYNTAX       Gauge32
    MAX-ACCESS   read-only
    STATUS       current
    DESCRIPTION
        "Cisco UCS equipment:ChassisCapProvider:gencount
        managed object property"
    ::= { cucsEquipmentChassisCapProviderEntry 5 }

cucsEquipmentChassisCapProviderMgmtPlaneVer OBJECT-TYPE
    SYNTAX       SnmpAdminString
    MAX-ACCESS   read-only
    STATUS       current
    DESCRIPTION
        "Cisco UCS equipment:ChassisCapProvider:mgmtPlaneVer
        managed object property"
    ::= { cucsEquipmentChassisCapProviderEntry 6 }

cucsEquipmentChassisCapProviderModel OBJECT-TYPE
    SYNTAX       SnmpAdminString
    MAX-ACCESS   read-only
    STATUS       current
    DESCRIPTION
        "Cisco UCS equipment:ChassisCapProvider:model managed
        object property"
    ::= { cucsEquipmentChassisCapProviderEntry 7 }

cucsEquipmentChassisCapProviderRevision OBJECT-TYPE
    SYNTAX       SnmpAdminString
    MAX-ACCESS   read-only
    STATUS       current
    DESCRIPTION
        "Cisco UCS equipment:ChassisCapProvider:revision
        managed object property"
    ::= { cucsEquipmentChassisCapProviderEntry 8 }

cucsEquipmentChassisCapProviderVendor OBJECT-TYPE
    SYNTAX       SnmpAdminString
    MAX-ACCESS   read-only
    STATUS       current
    DESCRIPTION
        "Cisco UCS equipment:ChassisCapProvider:vendor
        managed object property"
    ::= { cucsEquipmentChassisCapProviderEntry 9 }

cucsEquipmentChassisCapProviderPromCardType OBJECT-TYPE
    SYNTAX       Gauge32
    MAX-ACCESS   read-only
    STATUS       current
    DESCRIPTION
        "Cisco UCS equipment:ChassisCapProvider:promCardType
        managed object property"
    ::= { cucsEquipmentChassisCapProviderEntry 10 }

cucsEquipmentChassisCapProviderDeleted OBJECT-TYPE
    SYNTAX       TruthValue
    MAX-ACCESS   read-only
    STATUS       current
    DESCRIPTION
        "Cisco UCS equipment:ChassisCapProvider:deleted
        managed object property"
    ::= { cucsEquipmentChassisCapProviderEntry 11 }

cucsEquipmentChassisCapProviderElementLoadFailures OBJECT-TYPE
    SYNTAX       Gauge32
    MAX-ACCESS   read-only
    STATUS       current
    DESCRIPTION
        "Cisco UCS equipment:ChassisCapProvider:elementLoadFailures
        managed object property"
    ::= { cucsEquipmentChassisCapProviderEntry 12 }

cucsEquipmentChassisCapProviderElementsLoaded OBJECT-TYPE
    SYNTAX       Gauge32
    MAX-ACCESS   read-only
    STATUS       current
    DESCRIPTION
        "Cisco UCS equipment:ChassisCapProvider:elementsLoaded
        managed object property"
    ::= { cucsEquipmentChassisCapProviderEntry 13 }

cucsEquipmentChassisCapProviderLoadErrors OBJECT-TYPE
    SYNTAX       Gauge32
    MAX-ACCESS   read-only
    STATUS       current
    DESCRIPTION
        "Cisco UCS equipment:ChassisCapProvider:loadErrors
        managed object property"
    ::= { cucsEquipmentChassisCapProviderEntry 14 }

cucsEquipmentChassisCapProviderLoadWarnings OBJECT-TYPE
    SYNTAX       Gauge32
    MAX-ACCESS   read-only
    STATUS       current
    DESCRIPTION
        "Cisco UCS equipment:ChassisCapProvider:loadWarnings
        managed object property"
    ::= { cucsEquipmentChassisCapProviderEntry 15 }

cucsEquipmentChassisFsmTable OBJECT-TYPE
    SYNTAX           SEQUENCE OF CucsEquipmentChassisFsmEntry
    MAX-ACCESS       not-accessible
    STATUS           current
    DESCRIPTION
        "Cisco UCS equipment:ChassisFsm managed object table"
    ::= { cucsEquipmentObjects 105 }

cucsEquipmentChassisFsmEntry OBJECT-TYPE
    SYNTAX           CucsEquipmentChassisFsmEntry
    MAX-ACCESS       not-accessible
    STATUS           current
    DESCRIPTION
        "Entry for the cucsEquipmentChassisFsmTable table."
    INDEX { cucsEquipmentChassisFsmInstanceId }
    ::= { cucsEquipmentChassisFsmTable 1 }

CucsEquipmentChassisFsmEntry ::= SEQUENCE {
    cucsEquipmentChassisFsmInstanceId                                CucsManagedObjectId,
    cucsEquipmentChassisFsmDn                                        CucsManagedObjectDn,
    cucsEquipmentChassisFsmRn                                        SnmpAdminString,
    cucsEquipmentChassisFsmCompletionTime                            DateAndTime,
    cucsEquipmentChassisFsmCurrentFsm                                CucsEquipmentChassisFsmCurrentFsm,
    cucsEquipmentChassisFsmDescrData                                 SnmpAdminString,
    cucsEquipmentChassisFsmFsmStatus                                 CucsFsmFsmStageStatus,
    cucsEquipmentChassisFsmProgress                                  Gauge32,
    cucsEquipmentChassisFsmRmtErrCode                                Gauge32,
    cucsEquipmentChassisFsmRmtErrDescr                               SnmpAdminString,
    cucsEquipmentChassisFsmRmtRslt                                   CucsConditionRemoteInvRslt
}

cucsEquipmentChassisFsmInstanceId OBJECT-TYPE
    SYNTAX       CucsManagedObjectId
    MAX-ACCESS   not-accessible
    STATUS       current
    DESCRIPTION
        "Instance identifier of the managed object."
    ::= { cucsEquipmentChassisFsmEntry 1 }

cucsEquipmentChassisFsmDn OBJECT-TYPE
    SYNTAX       CucsManagedObjectDn
    MAX-ACCESS   read-only
    STATUS       current
    DESCRIPTION
        "Cisco UCS equipment:ChassisFsm:dn managed object property"
    ::= { cucsEquipmentChassisFsmEntry 2 }

cucsEquipmentChassisFsmRn OBJECT-TYPE
    SYNTAX       SnmpAdminString
    MAX-ACCESS   read-only
    STATUS       current
    DESCRIPTION
        "Cisco UCS equipment:ChassisFsm:rn managed object property"
    ::= { cucsEquipmentChassisFsmEntry 3 }

cucsEquipmentChassisFsmCompletionTime OBJECT-TYPE
    SYNTAX       DateAndTime
    MAX-ACCESS   read-only
    STATUS       current
    DESCRIPTION
        "Cisco UCS equipment:ChassisFsm:completionTime
        managed object property"
    ::= { cucsEquipmentChassisFsmEntry 4 }

cucsEquipmentChassisFsmCurrentFsm OBJECT-TYPE
    SYNTAX       CucsEquipmentChassisFsmCurrentFsm
    MAX-ACCESS   read-only
    STATUS       current
    DESCRIPTION
        "Cisco UCS equipment:ChassisFsm:currentFsm managed
        object property"
    ::= { cucsEquipmentChassisFsmEntry 5 }

cucsEquipmentChassisFsmDescrData OBJECT-TYPE
    SYNTAX       SnmpAdminString
    MAX-ACCESS   read-only
    STATUS       current
    DESCRIPTION
        "Cisco UCS equipment:ChassisFsm:descr managed object property"
    ::= { cucsEquipmentChassisFsmEntry 6 }

cucsEquipmentChassisFsmFsmStatus OBJECT-TYPE
    SYNTAX       CucsFsmFsmStageStatus
    MAX-ACCESS   read-only
    STATUS       current
    DESCRIPTION
        "Cisco UCS equipment:ChassisFsm:fsmStatus managed object property"
    ::= { cucsEquipmentChassisFsmEntry 7 }

cucsEquipmentChassisFsmProgress OBJECT-TYPE
    SYNTAX       Gauge32
    MAX-ACCESS   read-only
    STATUS       current
    DESCRIPTION
        "Cisco UCS equipment:ChassisFsm:progress managed object property"
    ::= { cucsEquipmentChassisFsmEntry 8 }

cucsEquipmentChassisFsmRmtErrCode OBJECT-TYPE
    SYNTAX       Gauge32
    MAX-ACCESS   read-only
    STATUS       current
    DESCRIPTION
        "Cisco UCS equipment:ChassisFsm:rmtErrCode managed
        object property"
    ::= { cucsEquipmentChassisFsmEntry 9 }

cucsEquipmentChassisFsmRmtErrDescr OBJECT-TYPE
    SYNTAX       SnmpAdminString
    MAX-ACCESS   read-only
    STATUS       current
    DESCRIPTION
        "Cisco UCS equipment:ChassisFsm:rmtErrDescr managed
        object property"
    ::= { cucsEquipmentChassisFsmEntry 10 }

cucsEquipmentChassisFsmRmtRslt OBJECT-TYPE
    SYNTAX       CucsConditionRemoteInvRslt
    MAX-ACCESS   read-only
    STATUS       current
    DESCRIPTION
        "Cisco UCS equipment:ChassisFsm:rmtRslt managed object property"
    ::= { cucsEquipmentChassisFsmEntry 11 }

cucsEquipmentChassisFsmStageTable OBJECT-TYPE
    SYNTAX           SEQUENCE OF CucsEquipmentChassisFsmStageEntry
    MAX-ACCESS       not-accessible
    STATUS           current
    DESCRIPTION
        "Cisco UCS equipment:ChassisFsmStage managed object table"
    ::= { cucsEquipmentObjects 106 }

cucsEquipmentChassisFsmStageEntry OBJECT-TYPE
    SYNTAX           CucsEquipmentChassisFsmStageEntry
    MAX-ACCESS       not-accessible
    STATUS           current
    DESCRIPTION
        "Entry for the cucsEquipmentChassisFsmStageTable table."
    INDEX { cucsEquipmentChassisFsmStageInstanceId }
    ::= { cucsEquipmentChassisFsmStageTable 1 }

CucsEquipmentChassisFsmStageEntry ::= SEQUENCE {
    cucsEquipmentChassisFsmStageInstanceId                           CucsManagedObjectId,
    cucsEquipmentChassisFsmStageDn                                   CucsManagedObjectDn,
    cucsEquipmentChassisFsmStageRn                                   SnmpAdminString,
    cucsEquipmentChassisFsmStageDescrData                            SnmpAdminString,
    cucsEquipmentChassisFsmStageLastUpdateTime                       DateAndTime,
    cucsEquipmentChassisFsmStageName                                 CucsEquipmentChassisFsmStageName,
    cucsEquipmentChassisFsmStageOrder                                Gauge32,
    cucsEquipmentChassisFsmStageRetry                                Gauge32,
    cucsEquipmentChassisFsmStageStageStatus                          CucsFsmFsmStageStatus
}

cucsEquipmentChassisFsmStageInstanceId OBJECT-TYPE
    SYNTAX       CucsManagedObjectId
    MAX-ACCESS   not-accessible
    STATUS       current
    DESCRIPTION
        "Instance identifier of the managed object."
    ::= { cucsEquipmentChassisFsmStageEntry 1 }

cucsEquipmentChassisFsmStageDn OBJECT-TYPE
    SYNTAX       CucsManagedObjectDn
    MAX-ACCESS   read-only
    STATUS       current
    DESCRIPTION
        "Cisco UCS equipment:ChassisFsmStage:dn managed object property"
    ::= { cucsEquipmentChassisFsmStageEntry 2 }

cucsEquipmentChassisFsmStageRn OBJECT-TYPE
    SYNTAX       SnmpAdminString
    MAX-ACCESS   read-only
    STATUS       current
    DESCRIPTION
        "Cisco UCS equipment:ChassisFsmStage:rn managed object property"
    ::= { cucsEquipmentChassisFsmStageEntry 3 }

cucsEquipmentChassisFsmStageDescrData OBJECT-TYPE
    SYNTAX       SnmpAdminString
    MAX-ACCESS   read-only
    STATUS       current
    DESCRIPTION
        "Cisco UCS equipment:ChassisFsmStage:descr managed
        object property"
    ::= { cucsEquipmentChassisFsmStageEntry 4 }

cucsEquipmentChassisFsmStageLastUpdateTime OBJECT-TYPE
    SYNTAX       DateAndTime
    MAX-ACCESS   read-only
    STATUS       current
    DESCRIPTION
        "Cisco UCS equipment:ChassisFsmStage:lastUpdateTime
        managed object property"
    ::= { cucsEquipmentChassisFsmStageEntry 5 }

cucsEquipmentChassisFsmStageName OBJECT-TYPE
    SYNTAX       CucsEquipmentChassisFsmStageName
    MAX-ACCESS   read-only
    STATUS       current
    DESCRIPTION
        "Cisco UCS equipment:ChassisFsmStage:name managed object property"
    ::= { cucsEquipmentChassisFsmStageEntry 6 }

cucsEquipmentChassisFsmStageOrder OBJECT-TYPE
    SYNTAX       Gauge32
    MAX-ACCESS   read-only
    STATUS       current
    DESCRIPTION
        "Cisco UCS equipment:ChassisFsmStage:order managed
        object property"
    ::= { cucsEquipmentChassisFsmStageEntry 7 }

cucsEquipmentChassisFsmStageRetry OBJECT-TYPE
    SYNTAX       Gauge32
    MAX-ACCESS   read-only
    STATUS       current
    DESCRIPTION
        "Cisco UCS equipment:ChassisFsmStage:retry managed
        object property"
    ::= { cucsEquipmentChassisFsmStageEntry 8 }

cucsEquipmentChassisFsmStageStageStatus OBJECT-TYPE
    SYNTAX       CucsFsmFsmStageStatus
    MAX-ACCESS   read-only
    STATUS       current
    DESCRIPTION
        "Cisco UCS equipment:ChassisFsmStage:stageStatus
        managed object property"
    ::= { cucsEquipmentChassisFsmStageEntry 9 }

cucsEquipmentChassisFsmTaskTable OBJECT-TYPE
    SYNTAX           SEQUENCE OF CucsEquipmentChassisFsmTaskEntry
    MAX-ACCESS       not-accessible
    STATUS           current
    DESCRIPTION
        "Cisco UCS equipment:ChassisFsmTask managed object table"
    ::= { cucsEquipmentObjects 9 }

cucsEquipmentChassisFsmTaskEntry OBJECT-TYPE
    SYNTAX           CucsEquipmentChassisFsmTaskEntry
    MAX-ACCESS       not-accessible
    STATUS           current
    DESCRIPTION
        "Entry for the cucsEquipmentChassisFsmTaskTable table."
    INDEX { cucsEquipmentChassisFsmTaskInstanceId }
    ::= { cucsEquipmentChassisFsmTaskTable 1 }

CucsEquipmentChassisFsmTaskEntry ::= SEQUENCE {
    cucsEquipmentChassisFsmTaskInstanceId                            CucsManagedObjectId,
    cucsEquipmentChassisFsmTaskDn                                    CucsManagedObjectDn,
    cucsEquipmentChassisFsmTaskRn                                    SnmpAdminString,
    cucsEquipmentChassisFsmTaskCompletion                            CucsFsmCompletion,
    cucsEquipmentChassisFsmTaskFlags                                 CucsEquipmentChassisFsmTaskFlags,
    cucsEquipmentChassisFsmTaskItem                                  CucsEquipmentChassisFsmTaskItem,
    cucsEquipmentChassisFsmTaskSeqId                                 Gauge32
}

cucsEquipmentChassisFsmTaskInstanceId OBJECT-TYPE
    SYNTAX       CucsManagedObjectId
    MAX-ACCESS   not-accessible
    STATUS       current
    DESCRIPTION
        "Instance identifier of the managed object."
    ::= { cucsEquipmentChassisFsmTaskEntry 1 }

cucsEquipmentChassisFsmTaskDn OBJECT-TYPE
    SYNTAX       CucsManagedObjectDn
    MAX-ACCESS   read-only
    STATUS       current
    DESCRIPTION
        "Cisco UCS equipment:ChassisFsmTask:dn managed object property"
    ::= { cucsEquipmentChassisFsmTaskEntry 2 }

cucsEquipmentChassisFsmTaskRn OBJECT-TYPE
    SYNTAX       SnmpAdminString
    MAX-ACCESS   read-only
    STATUS       current
    DESCRIPTION
        "Cisco UCS equipment:ChassisFsmTask:rn managed object property"
    ::= { cucsEquipmentChassisFsmTaskEntry 3 }

cucsEquipmentChassisFsmTaskCompletion OBJECT-TYPE
    SYNTAX       CucsFsmCompletion
    MAX-ACCESS   read-only
    STATUS       current
    DESCRIPTION
        "Cisco UCS equipment:ChassisFsmTask:completion
        managed object property"
    ::= { cucsEquipmentChassisFsmTaskEntry 4 }

cucsEquipmentChassisFsmTaskFlags OBJECT-TYPE
    SYNTAX       CucsEquipmentChassisFsmTaskFlags
    MAX-ACCESS   read-only
    STATUS       current
    DESCRIPTION
        "Cisco UCS equipment:ChassisFsmTask:flags managed object property"
    ::= { cucsEquipmentChassisFsmTaskEntry 5 }

cucsEquipmentChassisFsmTaskItem OBJECT-TYPE
    SYNTAX       CucsEquipmentChassisFsmTaskItem
    MAX-ACCESS   read-only
    STATUS       current
    DESCRIPTION
        "Cisco UCS equipment:ChassisFsmTask:item managed object property"
    ::= { cucsEquipmentChassisFsmTaskEntry 6 }

cucsEquipmentChassisFsmTaskSeqId OBJECT-TYPE
    SYNTAX       Gauge32
    MAX-ACCESS   read-only
    STATUS       current
    DESCRIPTION
        "Cisco UCS equipment:ChassisFsmTask:seqId managed object property"
    ::= { cucsEquipmentChassisFsmTaskEntry 7 }

cucsEquipmentChassisInheritPolicyTable OBJECT-TYPE
    SYNTAX           SEQUENCE OF CucsEquipmentChassisInheritPolicyEntry
    MAX-ACCESS       not-accessible
    STATUS           current
    DESCRIPTION
        "Cisco UCS equipment:ChassisInheritPolicy managed object table"
    ::= { cucsEquipmentObjects 205 }

cucsEquipmentChassisInheritPolicyEntry OBJECT-TYPE
    SYNTAX           CucsEquipmentChassisInheritPolicyEntry
    MAX-ACCESS       not-accessible
    STATUS           current
    DESCRIPTION
        "Entry for the cucsEquipmentChassisInheritPolicyTable table."
    INDEX { cucsEquipmentChassisInheritPolicyInstanceId }
    ::= { cucsEquipmentChassisInheritPolicyTable 1 }

CucsEquipmentChassisInheritPolicyEntry ::= SEQUENCE {
    cucsEquipmentChassisInheritPolicyInstanceId                      CucsManagedObjectId,
    cucsEquipmentChassisInheritPolicyDn                              CucsManagedObjectDn,
    cucsEquipmentChassisInheritPolicyRn                              SnmpAdminString,
    cucsEquipmentChassisInheritPolicyDescr                           SnmpAdminString,
    cucsEquipmentChassisInheritPolicyDstDn                           SnmpAdminString,
    cucsEquipmentChassisInheritPolicyIntId                           SnmpAdminString,
    cucsEquipmentChassisInheritPolicyName                            SnmpAdminString,
    cucsEquipmentChassisInheritPolicyOperQualifier                   SnmpAdminString,
    cucsEquipmentChassisInheritPolicyPolicyLevel                     Gauge32,
    cucsEquipmentChassisInheritPolicyPolicyOwner                     CucsPolicyPolicyOwner,
    cucsEquipmentChassisInheritPolicyQualifier                       SnmpAdminString
}

cucsEquipmentChassisInheritPolicyInstanceId OBJECT-TYPE
    SYNTAX       CucsManagedObjectId
    MAX-ACCESS   not-accessible
    STATUS       current
    DESCRIPTION
        "Instance identifier of the managed object."
    ::= { cucsEquipmentChassisInheritPolicyEntry 1 }

cucsEquipmentChassisInheritPolicyDn OBJECT-TYPE
    SYNTAX       CucsManagedObjectDn
    MAX-ACCESS   read-only
    STATUS       current
    DESCRIPTION
        "Cisco UCS equipment:ChassisInheritPolicy:dn managed
        object property"
    ::= { cucsEquipmentChassisInheritPolicyEntry 2 }

cucsEquipmentChassisInheritPolicyRn OBJECT-TYPE
    SYNTAX       SnmpAdminString
    MAX-ACCESS   read-only
    STATUS       current
    DESCRIPTION
        "Cisco UCS equipment:ChassisInheritPolicy:rn managed
        object property"
    ::= { cucsEquipmentChassisInheritPolicyEntry 3 }

cucsEquipmentChassisInheritPolicyDescr OBJECT-TYPE
    SYNTAX       SnmpAdminString
    MAX-ACCESS   read-only
    STATUS       current
    DESCRIPTION
        "Cisco UCS equipment:ChassisInheritPolicy:descr
        managed object property"
    ::= { cucsEquipmentChassisInheritPolicyEntry 4 }

cucsEquipmentChassisInheritPolicyDstDn OBJECT-TYPE
    SYNTAX       SnmpAdminString
    MAX-ACCESS   read-only
    STATUS       current
    DESCRIPTION
        "Cisco UCS equipment:ChassisInheritPolicy:dstDn
        managed object property"
    ::= { cucsEquipmentChassisInheritPolicyEntry 5 }

cucsEquipmentChassisInheritPolicyIntId OBJECT-TYPE
    SYNTAX       SnmpAdminString
    MAX-ACCESS   read-only
    STATUS       current
    DESCRIPTION
        "Cisco UCS equipment:ChassisInheritPolicy:intId
        managed object property"
    ::= { cucsEquipmentChassisInheritPolicyEntry 6 }

cucsEquipmentChassisInheritPolicyName OBJECT-TYPE
    SYNTAX       SnmpAdminString
    MAX-ACCESS   read-only
    STATUS       current
    DESCRIPTION
        "Cisco UCS equipment:ChassisInheritPolicy:name
        managed object property"
    ::= { cucsEquipmentChassisInheritPolicyEntry 7 }

cucsEquipmentChassisInheritPolicyOperQualifier OBJECT-TYPE
    SYNTAX       SnmpAdminString
    MAX-ACCESS   read-only
    STATUS       current
    DESCRIPTION
        "Cisco UCS equipment:ChassisInheritPolicy:operQualifier
        managed object property"
    ::= { cucsEquipmentChassisInheritPolicyEntry 8 }

cucsEquipmentChassisInheritPolicyPolicyLevel OBJECT-TYPE
    SYNTAX       Gauge32
    MAX-ACCESS   read-only
    STATUS       current
    DESCRIPTION
        "Cisco UCS equipment:ChassisInheritPolicy:policyLevel
        managed object property"
    ::= { cucsEquipmentChassisInheritPolicyEntry 9 }

cucsEquipmentChassisInheritPolicyPolicyOwner OBJECT-TYPE
    SYNTAX       CucsPolicyPolicyOwner
    MAX-ACCESS   read-only
    STATUS       current
    DESCRIPTION
        "Cisco UCS equipment:ChassisInheritPolicy:policyOwner
        managed object property"
    ::= { cucsEquipmentChassisInheritPolicyEntry 10 }

cucsEquipmentChassisInheritPolicyQualifier OBJECT-TYPE
    SYNTAX       SnmpAdminString
    MAX-ACCESS   read-only
    STATUS       current
    DESCRIPTION
        "Cisco UCS equipment:ChassisInheritPolicy:qualifier
        managed object property"
    ::= { cucsEquipmentChassisInheritPolicyEntry 11 }

cucsEquipmentChassisIssuesTable OBJECT-TYPE
    SYNTAX           SEQUENCE OF CucsEquipmentChassisIssuesEntry
    MAX-ACCESS       not-accessible
    STATUS           current
    DESCRIPTION
        "Cisco UCS equipment:ChassisIssues managed object table"
    ::= { cucsEquipmentObjects 180 }

cucsEquipmentChassisIssuesEntry OBJECT-TYPE
    SYNTAX           CucsEquipmentChassisIssuesEntry
    MAX-ACCESS       not-accessible
    STATUS           current
    DESCRIPTION
        "Entry for the cucsEquipmentChassisIssuesTable table."
    INDEX { cucsEquipmentChassisIssuesInstanceId }
    ::= { cucsEquipmentChassisIssuesTable 1 }

CucsEquipmentChassisIssuesEntry ::= SEQUENCE {
    cucsEquipmentChassisIssuesInstanceId                             CucsManagedObjectId,
    cucsEquipmentChassisIssuesDn                                     CucsManagedObjectDn,
    cucsEquipmentChassisIssuesRn                                     SnmpAdminString,
    cucsEquipmentChassisIssuesChassisConfigIssues                    CucsEquipmentChassisConfigIssues,
    cucsEquipmentChassisIssuesConfigWarnings                         CucsEquipmentConfigWarnings,
    cucsEquipmentChassisIssuesStorageConfigIssues                    CucsStorageConfigIssues,
    cucsEquipmentChassisIssuesPropAcl                                Unsigned64
}

cucsEquipmentChassisIssuesInstanceId OBJECT-TYPE
    SYNTAX       CucsManagedObjectId
    MAX-ACCESS   not-accessible
    STATUS       current
    DESCRIPTION
        "Instance identifier of the managed object."
    ::= { cucsEquipmentChassisIssuesEntry 1 }

cucsEquipmentChassisIssuesDn OBJECT-TYPE
    SYNTAX       CucsManagedObjectDn
    MAX-ACCESS   read-only
    STATUS       current
    DESCRIPTION
        "Cisco UCS equipment:ChassisIssues:dn managed object property"
    ::= { cucsEquipmentChassisIssuesEntry 2 }

cucsEquipmentChassisIssuesRn OBJECT-TYPE
    SYNTAX       SnmpAdminString
    MAX-ACCESS   read-only
    STATUS       current
    DESCRIPTION
        "Cisco UCS equipment:ChassisIssues:rn managed object property"
    ::= { cucsEquipmentChassisIssuesEntry 3 }

cucsEquipmentChassisIssuesChassisConfigIssues OBJECT-TYPE
    SYNTAX       CucsEquipmentChassisConfigIssues
    MAX-ACCESS   read-only
    STATUS       current
    DESCRIPTION
        "Cisco UCS equipment:ChassisIssues:chassisConfigIssues
        managed object property"
    ::= { cucsEquipmentChassisIssuesEntry 4 }

cucsEquipmentChassisIssuesConfigWarnings OBJECT-TYPE
    SYNTAX       CucsEquipmentConfigWarnings
    MAX-ACCESS   read-only
    STATUS       current
    DESCRIPTION
        "Cisco UCS equipment:ChassisIssues:configWarnings
        managed object property"
    ::= { cucsEquipmentChassisIssuesEntry 5 }

cucsEquipmentChassisIssuesStorageConfigIssues OBJECT-TYPE
    SYNTAX       CucsStorageConfigIssues
    MAX-ACCESS   read-only
    STATUS       current
    DESCRIPTION
        "Cisco UCS equipment:ChassisIssues:storageConfigIssues
        managed object property"
    ::= { cucsEquipmentChassisIssuesEntry 6 }

cucsEquipmentChassisIssuesPropAcl OBJECT-TYPE
    SYNTAX       Unsigned64
    MAX-ACCESS   read-only
    STATUS       current
    DESCRIPTION
        "Cisco UCS equipment:ChassisIssues:propAcl managed
        object property"
    ::= { cucsEquipmentChassisIssuesEntry 7 }

cucsEquipmentChassisProfileTable OBJECT-TYPE
    SYNTAX           SEQUENCE OF CucsEquipmentChassisProfileEntry
    MAX-ACCESS       not-accessible
    STATUS           current
    DESCRIPTION
        "Cisco UCS equipment:ChassisProfile managed object table"
    ::= { cucsEquipmentObjects 181 }

cucsEquipmentChassisProfileEntry OBJECT-TYPE
    SYNTAX           CucsEquipmentChassisProfileEntry
    MAX-ACCESS       not-accessible
    STATUS           current
    DESCRIPTION
        "Entry for the cucsEquipmentChassisProfileTable table."
    INDEX { cucsEquipmentChassisProfileInstanceId }
    ::= { cucsEquipmentChassisProfileTable 1 }

CucsEquipmentChassisProfileEntry ::= SEQUENCE {
    cucsEquipmentChassisProfileInstanceId                            CucsManagedObjectId,
    cucsEquipmentChassisProfileDn                                    CucsManagedObjectDn,
    cucsEquipmentChassisProfileRn                                    SnmpAdminString,
    cucsEquipmentChassisProfileAssignState                           CucsEquipmentAssignment,
    cucsEquipmentChassisProfileAssocState                            CucsEquipmentChassisAssocState,
    cucsEquipmentChassisProfileChassisDn                             SnmpAdminString,
    cucsEquipmentChassisProfileChassisFwPolicyName                   SnmpAdminString,
    cucsEquipmentChassisProfileConfigQualifier                       CucsEquipmentChassisConfigIssues,
    cucsEquipmentChassisProfileConfigState                           CucsEquipmentChassisProfileConfigState,
    cucsEquipmentChassisProfileDescr                                 SnmpAdminString,
    cucsEquipmentChassisProfileDiskZoningPolicyName                  SnmpAdminString,
    cucsEquipmentChassisProfileFltAggr                               Unsigned64,
    cucsEquipmentChassisProfileFsmDescr                              SnmpAdminString,
    cucsEquipmentChassisProfileFsmFlags                              SnmpAdminString,
    cucsEquipmentChassisProfileFsmPrev                               SnmpAdminString,
    cucsEquipmentChassisProfileFsmProgr                              Gauge32,
    cucsEquipmentChassisProfileFsmRmtInvErrCode                      Gauge32,
    cucsEquipmentChassisProfileFsmRmtInvErrDescr                     SnmpAdminString,
    cucsEquipmentChassisProfileFsmRmtInvRslt                         CucsConditionRemoteInvRslt,
    cucsEquipmentChassisProfileFsmStageDescr                         SnmpAdminString,
    cucsEquipmentChassisProfileFsmStamp                              DateAndTime,
    cucsEquipmentChassisProfileFsmStatus                             SnmpAdminString,
    cucsEquipmentChassisProfileFsmTry                                Gauge32,
    cucsEquipmentChassisProfileIntId                                 SnmpAdminString,
    cucsEquipmentChassisProfileMaintPolicyName                       SnmpAdminString,
    cucsEquipmentChassisProfileName                                  SnmpAdminString,
    cucsEquipmentChassisProfileOperChassisFwPolicyName               SnmpAdminString,
    cucsEquipmentChassisProfileOperDiskZoningPolicyName              SnmpAdminString,
    cucsEquipmentChassisProfileOperMaintPolicyName                   SnmpAdminString,
    cucsEquipmentChassisProfileOperSrcTemplName                      SnmpAdminString,
    cucsEquipmentChassisProfileOperState                             CucsEquipmentChassisProfileOperState,
    cucsEquipmentChassisProfileOwner                                 CucsEquipmentOwner,
    cucsEquipmentChassisProfilePolicyLevel                           Gauge32,
    cucsEquipmentChassisProfilePolicyOwner                           CucsPolicyPolicyOwner,
    cucsEquipmentChassisProfileResolveRemote                         CucsEquipmentResolveFromRemoteServer,
    cucsEquipmentChassisProfileSrcTemplName                          SnmpAdminString,
    cucsEquipmentChassisProfileType                                  CucsEquipmentType,
    cucsEquipmentChassisProfileUsrLbl                                SnmpAdminString,
    cucsEquipmentChassisProfileUuid                                  SnmpAdminString,
    cucsEquipmentChassisProfilePropAcl                               Unsigned64,
    cucsEquipmentChassisProfileComputeConnPolicyName                 SnmpAdminString,
    cucsEquipmentChassisProfileOperComputeConnPolicyName             SnmpAdminString
}

cucsEquipmentChassisProfileInstanceId OBJECT-TYPE
    SYNTAX       CucsManagedObjectId
    MAX-ACCESS   not-accessible
    STATUS       current
    DESCRIPTION
        "Instance identifier of the managed object."
    ::= { cucsEquipmentChassisProfileEntry 1 }

cucsEquipmentChassisProfileDn OBJECT-TYPE
    SYNTAX       CucsManagedObjectDn
    MAX-ACCESS   read-only
    STATUS       current
    DESCRIPTION
        "Cisco UCS equipment:ChassisProfile:dn managed object property"
    ::= { cucsEquipmentChassisProfileEntry 2 }

cucsEquipmentChassisProfileRn OBJECT-TYPE
    SYNTAX       SnmpAdminString
    MAX-ACCESS   read-only
    STATUS       current
    DESCRIPTION
        "Cisco UCS equipment:ChassisProfile:rn managed object property"
    ::= { cucsEquipmentChassisProfileEntry 3 }

cucsEquipmentChassisProfileAssignState OBJECT-TYPE
    SYNTAX       CucsEquipmentAssignment
    MAX-ACCESS   read-only
    STATUS       current
    DESCRIPTION
        "Cisco UCS equipment:ChassisProfile:assignState
        managed object property"
    ::= { cucsEquipmentChassisProfileEntry 4 }

cucsEquipmentChassisProfileAssocState OBJECT-TYPE
    SYNTAX       CucsEquipmentChassisAssocState
    MAX-ACCESS   read-only
    STATUS       current
    DESCRIPTION
        "Cisco UCS equipment:ChassisProfile:assocState
        managed object property"
    ::= { cucsEquipmentChassisProfileEntry 5 }

cucsEquipmentChassisProfileChassisDn OBJECT-TYPE
    SYNTAX       SnmpAdminString
    MAX-ACCESS   read-only
    STATUS       current
    DESCRIPTION
        "Cisco UCS equipment:ChassisProfile:chassisDn managed
        object property"
    ::= { cucsEquipmentChassisProfileEntry 6 }

cucsEquipmentChassisProfileChassisFwPolicyName OBJECT-TYPE
    SYNTAX       SnmpAdminString
    MAX-ACCESS   read-only
    STATUS       current
    DESCRIPTION
        "Cisco UCS equipment:ChassisProfile:chassisFwPolicyName
        managed object property"
    ::= { cucsEquipmentChassisProfileEntry 7 }

cucsEquipmentChassisProfileConfigQualifier OBJECT-TYPE
    SYNTAX       CucsEquipmentChassisConfigIssues
    MAX-ACCESS   read-only
    STATUS       current
    DESCRIPTION
        "Cisco UCS equipment:ChassisProfile:configQualifier
        managed object property"
    ::= { cucsEquipmentChassisProfileEntry 8 }

cucsEquipmentChassisProfileConfigState OBJECT-TYPE
    SYNTAX       CucsEquipmentChassisProfileConfigState
    MAX-ACCESS   read-only
    STATUS       current
    DESCRIPTION
        "Cisco UCS equipment:ChassisProfile:configState
        managed object property"
    ::= { cucsEquipmentChassisProfileEntry 9 }

cucsEquipmentChassisProfileDescr OBJECT-TYPE
    SYNTAX       SnmpAdminString
    MAX-ACCESS   read-only
    STATUS       current
    DESCRIPTION
        "Cisco UCS equipment:ChassisProfile:descr managed object property"
    ::= { cucsEquipmentChassisProfileEntry 10 }

cucsEquipmentChassisProfileDiskZoningPolicyName OBJECT-TYPE
    SYNTAX       SnmpAdminString
    MAX-ACCESS   read-only
    STATUS       current
    DESCRIPTION
        "Cisco UCS equipment:ChassisProfile:diskZoningPolicyName
        managed object property"
    ::= { cucsEquipmentChassisProfileEntry 11 }

cucsEquipmentChassisProfileFltAggr OBJECT-TYPE
    SYNTAX       Unsigned64
    MAX-ACCESS   read-only
    STATUS       current
    DESCRIPTION
        "Cisco UCS equipment:ChassisProfile:fltAggr managed
        object property"
    ::= { cucsEquipmentChassisProfileEntry 16 }

cucsEquipmentChassisProfileFsmDescr OBJECT-TYPE
    SYNTAX       SnmpAdminString
    MAX-ACCESS   read-only
    STATUS       current
    DESCRIPTION
        "Cisco UCS equipment:ChassisProfile:fsmDescr managed
        object property"
    ::= { cucsEquipmentChassisProfileEntry 17 }

cucsEquipmentChassisProfileFsmFlags OBJECT-TYPE
    SYNTAX       SnmpAdminString
    MAX-ACCESS   read-only
    STATUS       current
    DESCRIPTION
        "Cisco UCS equipment:ChassisProfile:fsmFlags managed
        object property"
    ::= { cucsEquipmentChassisProfileEntry 18 }

cucsEquipmentChassisProfileFsmPrev OBJECT-TYPE
    SYNTAX       SnmpAdminString
    MAX-ACCESS   read-only
    STATUS       current
    DESCRIPTION
        "Cisco UCS equipment:ChassisProfile:fsmPrev managed
        object property"
    ::= { cucsEquipmentChassisProfileEntry 19 }

cucsEquipmentChassisProfileFsmProgr OBJECT-TYPE
    SYNTAX       Gauge32
    MAX-ACCESS   read-only
    STATUS       current
    DESCRIPTION
        "Cisco UCS equipment:ChassisProfile:fsmProgr managed
        object property"
    ::= { cucsEquipmentChassisProfileEntry 20 }

cucsEquipmentChassisProfileFsmRmtInvErrCode OBJECT-TYPE
    SYNTAX       Gauge32
    MAX-ACCESS   read-only
    STATUS       current
    DESCRIPTION
        "Cisco UCS equipment:ChassisProfile:fsmRmtInvErrCode
        managed object property"
    ::= { cucsEquipmentChassisProfileEntry 21 }

cucsEquipmentChassisProfileFsmRmtInvErrDescr OBJECT-TYPE
    SYNTAX       SnmpAdminString
    MAX-ACCESS   read-only
    STATUS       current
    DESCRIPTION
        "Cisco UCS equipment:ChassisProfile:fsmRmtInvErrDescr
        managed object property"
    ::= { cucsEquipmentChassisProfileEntry 22 }

cucsEquipmentChassisProfileFsmRmtInvRslt OBJECT-TYPE
    SYNTAX       CucsConditionRemoteInvRslt
    MAX-ACCESS   read-only
    STATUS       current
    DESCRIPTION
        "Cisco UCS equipment:ChassisProfile:fsmRmtInvRslt
        managed object property"
    ::= { cucsEquipmentChassisProfileEntry 23 }

cucsEquipmentChassisProfileFsmStageDescr OBJECT-TYPE
    SYNTAX       SnmpAdminString
    MAX-ACCESS   read-only
    STATUS       current
    DESCRIPTION
        "Cisco UCS equipment:ChassisProfile:fsmStageDescr
        managed object property"
    ::= { cucsEquipmentChassisProfileEntry 24 }

cucsEquipmentChassisProfileFsmStamp OBJECT-TYPE
    SYNTAX       DateAndTime
    MAX-ACCESS   read-only
    STATUS       current
    DESCRIPTION
        "Cisco UCS equipment:ChassisProfile:fsmStamp managed
        object property"
    ::= { cucsEquipmentChassisProfileEntry 25 }

cucsEquipmentChassisProfileFsmStatus OBJECT-TYPE
    SYNTAX       SnmpAdminString
    MAX-ACCESS   read-only
    STATUS       current
    DESCRIPTION
        "Cisco UCS equipment:ChassisProfile:fsmStatus managed
        object property"
    ::= { cucsEquipmentChassisProfileEntry 26 }

cucsEquipmentChassisProfileFsmTry OBJECT-TYPE
    SYNTAX       Gauge32
    MAX-ACCESS   read-only
    STATUS       current
    DESCRIPTION
        "Cisco UCS equipment:ChassisProfile:fsmTry managed
        object property"
    ::= { cucsEquipmentChassisProfileEntry 27 }

cucsEquipmentChassisProfileIntId OBJECT-TYPE
    SYNTAX       SnmpAdminString
    MAX-ACCESS   read-only
    STATUS       current
    DESCRIPTION
        "Cisco UCS equipment:ChassisProfile:intId managed object property"
    ::= { cucsEquipmentChassisProfileEntry 29 }

cucsEquipmentChassisProfileMaintPolicyName OBJECT-TYPE
    SYNTAX       SnmpAdminString
    MAX-ACCESS   read-only
    STATUS       current
    DESCRIPTION
        "Cisco UCS equipment:ChassisProfile:maintPolicyName
        managed object property"
    ::= { cucsEquipmentChassisProfileEntry 31 }

cucsEquipmentChassisProfileName OBJECT-TYPE
    SYNTAX       SnmpAdminString
    MAX-ACCESS   read-only
    STATUS       current
    DESCRIPTION
        "Cisco UCS equipment:ChassisProfile:name managed object property"
    ::= { cucsEquipmentChassisProfileEntry 32 }

cucsEquipmentChassisProfileOperChassisFwPolicyName OBJECT-TYPE
    SYNTAX       SnmpAdminString
    MAX-ACCESS   read-only
    STATUS       current
    DESCRIPTION
        "Cisco UCS equipment:ChassisProfile:operChassisFwPolicyName
        managed object property"
    ::= { cucsEquipmentChassisProfileEntry 33 }

cucsEquipmentChassisProfileOperDiskZoningPolicyName OBJECT-TYPE
    SYNTAX       SnmpAdminString
    MAX-ACCESS   read-only
    STATUS       current
    DESCRIPTION
        "Cisco UCS equipment:ChassisProfile:operDiskZoningPolicyName
        managed object property"
    ::= { cucsEquipmentChassisProfileEntry 34 }

cucsEquipmentChassisProfileOperMaintPolicyName OBJECT-TYPE
    SYNTAX       SnmpAdminString
    MAX-ACCESS   read-only
    STATUS       current
    DESCRIPTION
        "Cisco UCS equipment:ChassisProfile:operMaintPolicyName
        managed object property"
    ::= { cucsEquipmentChassisProfileEntry 35 }

cucsEquipmentChassisProfileOperSrcTemplName OBJECT-TYPE
    SYNTAX       SnmpAdminString
    MAX-ACCESS   read-only
    STATUS       current
    DESCRIPTION
        "Cisco UCS equipment:ChassisProfile:operSrcTemplName
        managed object property"
    ::= { cucsEquipmentChassisProfileEntry 36 }

cucsEquipmentChassisProfileOperState OBJECT-TYPE
    SYNTAX       CucsEquipmentChassisProfileOperState
    MAX-ACCESS   read-only
    STATUS       current
    DESCRIPTION
        "Cisco UCS equipment:ChassisProfile:operState managed
        object property"
    ::= { cucsEquipmentChassisProfileEntry 37 }

cucsEquipmentChassisProfileOwner OBJECT-TYPE
    SYNTAX       CucsEquipmentOwner
    MAX-ACCESS   read-only
    STATUS       current
    DESCRIPTION
        "Cisco UCS equipment:ChassisProfile:owner managed object property"
    ::= { cucsEquipmentChassisProfileEntry 38 }

cucsEquipmentChassisProfilePolicyLevel OBJECT-TYPE
    SYNTAX       Gauge32
    MAX-ACCESS   read-only
    STATUS       current
    DESCRIPTION
        "Cisco UCS equipment:ChassisProfile:policyLevel
        managed object property"
    ::= { cucsEquipmentChassisProfileEntry 40 }

cucsEquipmentChassisProfilePolicyOwner OBJECT-TYPE
    SYNTAX       CucsPolicyPolicyOwner
    MAX-ACCESS   read-only
    STATUS       current
    DESCRIPTION
        "Cisco UCS equipment:ChassisProfile:policyOwner
        managed object property"
    ::= { cucsEquipmentChassisProfileEntry 41 }

cucsEquipmentChassisProfileResolveRemote OBJECT-TYPE
    SYNTAX       CucsEquipmentResolveFromRemoteServer
    MAX-ACCESS   read-only
    STATUS       current
    DESCRIPTION
        "Cisco UCS equipment:ChassisProfile:resolveRemote
        managed object property"
    ::= { cucsEquipmentChassisProfileEntry 42 }

cucsEquipmentChassisProfileSrcTemplName OBJECT-TYPE
    SYNTAX       SnmpAdminString
    MAX-ACCESS   read-only
    STATUS       current
    DESCRIPTION
        "Cisco UCS equipment:ChassisProfile:srcTemplName
        managed object property"
    ::= { cucsEquipmentChassisProfileEntry 43 }

cucsEquipmentChassisProfileType OBJECT-TYPE
    SYNTAX       CucsEquipmentType
    MAX-ACCESS   read-only
    STATUS       current
    DESCRIPTION
        "Cisco UCS equipment:ChassisProfile:type managed object property"
    ::= { cucsEquipmentChassisProfileEntry 44 }

cucsEquipmentChassisProfileUsrLbl OBJECT-TYPE
    SYNTAX       SnmpAdminString
    MAX-ACCESS   read-only
    STATUS       current
    DESCRIPTION
        "Cisco UCS equipment:ChassisProfile:usrLbl managed
        object property"
    ::= { cucsEquipmentChassisProfileEntry 45 }

cucsEquipmentChassisProfileUuid OBJECT-TYPE
    SYNTAX       SnmpAdminString
    MAX-ACCESS   read-only
    STATUS       current
    DESCRIPTION
        "Cisco UCS equipment:ChassisProfile:uuid managed object property"
    ::= { cucsEquipmentChassisProfileEntry 46 }

cucsEquipmentChassisProfilePropAcl OBJECT-TYPE
    SYNTAX       Unsigned64
    MAX-ACCESS   read-only
    STATUS       current
    DESCRIPTION
        "Cisco UCS equipment:ChassisProfile:propAcl managed
        object property"
    ::= { cucsEquipmentChassisProfileEntry 47 }

cucsEquipmentChassisProfileComputeConnPolicyName OBJECT-TYPE
    SYNTAX       SnmpAdminString
    MAX-ACCESS   read-only
    STATUS       current
    DESCRIPTION
        "Cisco UCS equipment:ChassisProfile:computeConnPolicyName
        managed object property"
    ::= { cucsEquipmentChassisProfileEntry 48 }

cucsEquipmentChassisProfileOperComputeConnPolicyName OBJECT-TYPE
    SYNTAX       SnmpAdminString
    MAX-ACCESS   read-only
    STATUS       current
    DESCRIPTION
        "Cisco UCS equipment:ChassisProfile:operComputeConnPolicyName
        managed object property"
    ::= { cucsEquipmentChassisProfileEntry 49 }

cucsEquipmentChassisProfileAssocCtxTable OBJECT-TYPE
    SYNTAX           SEQUENCE OF CucsEquipmentChassisProfileAssocCtxEntry
    MAX-ACCESS       not-accessible
    STATUS           current
    DESCRIPTION
        "Cisco UCS equipment:ChassisProfileAssocCtx managed object table"
    ::= { cucsEquipmentObjects 182 }

cucsEquipmentChassisProfileAssocCtxEntry OBJECT-TYPE
    SYNTAX           CucsEquipmentChassisProfileAssocCtxEntry
    MAX-ACCESS       not-accessible
    STATUS           current
    DESCRIPTION
        "Entry for the cucsEquipmentChassisProfileAssocCtxTable table."
    INDEX { cucsEquipmentChassisProfileAssocCtxInstanceId }
    ::= { cucsEquipmentChassisProfileAssocCtxTable 1 }

CucsEquipmentChassisProfileAssocCtxEntry ::= SEQUENCE {
    cucsEquipmentChassisProfileAssocCtxInstanceId                    CucsManagedObjectId,
    cucsEquipmentChassisProfileAssocCtxDn                            CucsManagedObjectDn,
    cucsEquipmentChassisProfileAssocCtxRn                            SnmpAdminString,
    cucsEquipmentChassisProfileAssocCtxPropAcl                       Unsigned64
}

cucsEquipmentChassisProfileAssocCtxInstanceId OBJECT-TYPE
    SYNTAX       CucsManagedObjectId
    MAX-ACCESS   not-accessible
    STATUS       current
    DESCRIPTION
        "Instance identifier of the managed object."
    ::= { cucsEquipmentChassisProfileAssocCtxEntry 1 }

cucsEquipmentChassisProfileAssocCtxDn OBJECT-TYPE
    SYNTAX       CucsManagedObjectDn
    MAX-ACCESS   read-only
    STATUS       current
    DESCRIPTION
        "Cisco UCS equipment:ChassisProfileAssocCtx:dn
        managed object property"
    ::= { cucsEquipmentChassisProfileAssocCtxEntry 2 }

cucsEquipmentChassisProfileAssocCtxRn OBJECT-TYPE
    SYNTAX       SnmpAdminString
    MAX-ACCESS   read-only
    STATUS       current
    DESCRIPTION
        "Cisco UCS equipment:ChassisProfileAssocCtx:rn
        managed object property"
    ::= { cucsEquipmentChassisProfileAssocCtxEntry 3 }

cucsEquipmentChassisProfileAssocCtxPropAcl OBJECT-TYPE
    SYNTAX       Unsigned64
    MAX-ACCESS   read-only
    STATUS       current
    DESCRIPTION
        "Cisco UCS equipment:ChassisProfileAssocCtx:propAcl
        managed object property"
    ::= { cucsEquipmentChassisProfileAssocCtxEntry 4 }

cucsEquipmentChassisProfileFsmTable OBJECT-TYPE
    SYNTAX           SEQUENCE OF CucsEquipmentChassisProfileFsmEntry
    MAX-ACCESS       not-accessible
    STATUS           current
    DESCRIPTION
        "Cisco UCS equipment:ChassisProfileFsm managed object table"
    ::= { cucsEquipmentObjects 183 }

cucsEquipmentChassisProfileFsmEntry OBJECT-TYPE
    SYNTAX           CucsEquipmentChassisProfileFsmEntry
    MAX-ACCESS       not-accessible
    STATUS           current
    DESCRIPTION
        "Entry for the cucsEquipmentChassisProfileFsmTable table."
    INDEX { cucsEquipmentChassisProfileFsmInstanceId }
    ::= { cucsEquipmentChassisProfileFsmTable 1 }

CucsEquipmentChassisProfileFsmEntry ::= SEQUENCE {
    cucsEquipmentChassisProfileFsmInstanceId                         CucsManagedObjectId,
    cucsEquipmentChassisProfileFsmDn                                 CucsManagedObjectDn,
    cucsEquipmentChassisProfileFsmRn                                 SnmpAdminString,
    cucsEquipmentChassisProfileFsmCompletionTime                     DateAndTime,
    cucsEquipmentChassisProfileFsmCurrentFsm                         CucsEquipmentChassisProfileFsmCurrentFsm,
    cucsEquipmentChassisProfileFsmDescrData                          SnmpAdminString,
    cucsEquipmentChassisProfileFsmFsmStatus                          CucsFsmFsmStageStatus,
    cucsEquipmentChassisProfileFsmProgress                           Gauge32,
    cucsEquipmentChassisProfileFsmRmtErrCode                         Gauge32,
    cucsEquipmentChassisProfileFsmRmtErrDescr                        SnmpAdminString,
    cucsEquipmentChassisProfileFsmRmtRslt                            CucsConditionRemoteInvRslt
}

cucsEquipmentChassisProfileFsmInstanceId OBJECT-TYPE
    SYNTAX       CucsManagedObjectId
    MAX-ACCESS   not-accessible
    STATUS       current
    DESCRIPTION
        "Instance identifier of the managed object."
    ::= { cucsEquipmentChassisProfileFsmEntry 1 }

cucsEquipmentChassisProfileFsmDn OBJECT-TYPE
    SYNTAX       CucsManagedObjectDn
    MAX-ACCESS   read-only
    STATUS       current
    DESCRIPTION
        "Cisco UCS equipment:ChassisProfileFsm:dn managed object property"
    ::= { cucsEquipmentChassisProfileFsmEntry 2 }

cucsEquipmentChassisProfileFsmRn OBJECT-TYPE
    SYNTAX       SnmpAdminString
    MAX-ACCESS   read-only
    STATUS       current
    DESCRIPTION
        "Cisco UCS equipment:ChassisProfileFsm:rn managed object property"
    ::= { cucsEquipmentChassisProfileFsmEntry 3 }

cucsEquipmentChassisProfileFsmCompletionTime OBJECT-TYPE
    SYNTAX       DateAndTime
    MAX-ACCESS   read-only
    STATUS       current
    DESCRIPTION
        "Cisco UCS equipment:ChassisProfileFsm:completionTime
        managed object property"
    ::= { cucsEquipmentChassisProfileFsmEntry 4 }

cucsEquipmentChassisProfileFsmCurrentFsm OBJECT-TYPE
    SYNTAX       CucsEquipmentChassisProfileFsmCurrentFsm
    MAX-ACCESS   read-only
    STATUS       current
    DESCRIPTION
        "Cisco UCS equipment:ChassisProfileFsm:currentFsm
        managed object property"
    ::= { cucsEquipmentChassisProfileFsmEntry 5 }

cucsEquipmentChassisProfileFsmDescrData OBJECT-TYPE
    SYNTAX       SnmpAdminString
    MAX-ACCESS   read-only
    STATUS       current
    DESCRIPTION
        "Cisco UCS equipment:ChassisProfileFsm:descr managed
        object property"
    ::= { cucsEquipmentChassisProfileFsmEntry 6 }

cucsEquipmentChassisProfileFsmFsmStatus OBJECT-TYPE
    SYNTAX       CucsFsmFsmStageStatus
    MAX-ACCESS   read-only
    STATUS       current
    DESCRIPTION
        "Cisco UCS equipment:ChassisProfileFsm:fsmStatus
        managed object property"
    ::= { cucsEquipmentChassisProfileFsmEntry 8 }

cucsEquipmentChassisProfileFsmProgress OBJECT-TYPE
    SYNTAX       Gauge32
    MAX-ACCESS   read-only
    STATUS       current
    DESCRIPTION
        "Cisco UCS equipment:ChassisProfileFsm:progress
        managed object property"
    ::= { cucsEquipmentChassisProfileFsmEntry 9 }

cucsEquipmentChassisProfileFsmRmtErrCode OBJECT-TYPE
    SYNTAX       Gauge32
    MAX-ACCESS   read-only
    STATUS       current
    DESCRIPTION
        "Cisco UCS equipment:ChassisProfileFsm:rmtErrCode
        managed object property"
    ::= { cucsEquipmentChassisProfileFsmEntry 10 }

cucsEquipmentChassisProfileFsmRmtErrDescr OBJECT-TYPE
    SYNTAX       SnmpAdminString
    MAX-ACCESS   read-only
    STATUS       current
    DESCRIPTION
        "Cisco UCS equipment:ChassisProfileFsm:rmtErrDescr
        managed object property"
    ::= { cucsEquipmentChassisProfileFsmEntry 11 }

cucsEquipmentChassisProfileFsmRmtRslt OBJECT-TYPE
    SYNTAX       CucsConditionRemoteInvRslt
    MAX-ACCESS   read-only
    STATUS       current
    DESCRIPTION
        "Cisco UCS equipment:ChassisProfileFsm:rmtRslt
        managed object property"
    ::= { cucsEquipmentChassisProfileFsmEntry 12 }

cucsEquipmentChassisProfileFsmStageTable OBJECT-TYPE
    SYNTAX           SEQUENCE OF CucsEquipmentChassisProfileFsmStageEntry
    MAX-ACCESS       not-accessible
    STATUS           current
    DESCRIPTION
        "Cisco UCS equipment:ChassisProfileFsmStage managed object table"
    ::= { cucsEquipmentObjects 184 }

cucsEquipmentChassisProfileFsmStageEntry OBJECT-TYPE
    SYNTAX           CucsEquipmentChassisProfileFsmStageEntry
    MAX-ACCESS       not-accessible
    STATUS           current
    DESCRIPTION
        "Entry for the cucsEquipmentChassisProfileFsmStageTable table."
    INDEX { cucsEquipmentChassisProfileFsmStageInstanceId }
    ::= { cucsEquipmentChassisProfileFsmStageTable 1 }

CucsEquipmentChassisProfileFsmStageEntry ::= SEQUENCE {
    cucsEquipmentChassisProfileFsmStageInstanceId                    CucsManagedObjectId,
    cucsEquipmentChassisProfileFsmStageDn                            CucsManagedObjectDn,
    cucsEquipmentChassisProfileFsmStageRn                            SnmpAdminString,
    cucsEquipmentChassisProfileFsmStageDescrData                     SnmpAdminString,
    cucsEquipmentChassisProfileFsmStageLastUpdateTime                DateAndTime,
    cucsEquipmentChassisProfileFsmStageName                          CucsEquipmentChassisProfileFsmStageName,
    cucsEquipmentChassisProfileFsmStageOrder                         Gauge32,
    cucsEquipmentChassisProfileFsmStageRetry                         Gauge32,
    cucsEquipmentChassisProfileFsmStageStageStatus                   CucsFsmFsmStageStatus
}

cucsEquipmentChassisProfileFsmStageInstanceId OBJECT-TYPE
    SYNTAX       CucsManagedObjectId
    MAX-ACCESS   not-accessible
    STATUS       current
    DESCRIPTION
        "Instance identifier of the managed object."
    ::= { cucsEquipmentChassisProfileFsmStageEntry 1 }

cucsEquipmentChassisProfileFsmStageDn OBJECT-TYPE
    SYNTAX       CucsManagedObjectDn
    MAX-ACCESS   read-only
    STATUS       current
    DESCRIPTION
        "Cisco UCS equipment:ChassisProfileFsmStage:dn
        managed object property"
    ::= { cucsEquipmentChassisProfileFsmStageEntry 2 }

cucsEquipmentChassisProfileFsmStageRn OBJECT-TYPE
    SYNTAX       SnmpAdminString
    MAX-ACCESS   read-only
    STATUS       current
    DESCRIPTION
        "Cisco UCS equipment:ChassisProfileFsmStage:rn
        managed object property"
    ::= { cucsEquipmentChassisProfileFsmStageEntry 3 }

cucsEquipmentChassisProfileFsmStageDescrData OBJECT-TYPE
    SYNTAX       SnmpAdminString
    MAX-ACCESS   read-only
    STATUS       current
    DESCRIPTION
        "Cisco UCS equipment:ChassisProfileFsmStage:descr
        managed object property"
    ::= { cucsEquipmentChassisProfileFsmStageEntry 4 }

cucsEquipmentChassisProfileFsmStageLastUpdateTime OBJECT-TYPE
    SYNTAX       DateAndTime
    MAX-ACCESS   read-only
    STATUS       current
    DESCRIPTION
        "Cisco UCS equipment:ChassisProfileFsmStage:lastUpdateTime
        managed object property"
    ::= { cucsEquipmentChassisProfileFsmStageEntry 5 }

cucsEquipmentChassisProfileFsmStageName OBJECT-TYPE
    SYNTAX       CucsEquipmentChassisProfileFsmStageName
    MAX-ACCESS   read-only
    STATUS       current
    DESCRIPTION
        "Cisco UCS equipment:ChassisProfileFsmStage:name
        managed object property"
    ::= { cucsEquipmentChassisProfileFsmStageEntry 6 }

cucsEquipmentChassisProfileFsmStageOrder OBJECT-TYPE
    SYNTAX       Gauge32
    MAX-ACCESS   read-only
    STATUS       current
    DESCRIPTION
        "Cisco UCS equipment:ChassisProfileFsmStage:order
        managed object property"
    ::= { cucsEquipmentChassisProfileFsmStageEntry 7 }

cucsEquipmentChassisProfileFsmStageRetry OBJECT-TYPE
    SYNTAX       Gauge32
    MAX-ACCESS   read-only
    STATUS       current
    DESCRIPTION
        "Cisco UCS equipment:ChassisProfileFsmStage:retry
        managed object property"
    ::= { cucsEquipmentChassisProfileFsmStageEntry 8 }

cucsEquipmentChassisProfileFsmStageStageStatus OBJECT-TYPE
    SYNTAX       CucsFsmFsmStageStatus
    MAX-ACCESS   read-only
    STATUS       current
    DESCRIPTION
        "Cisco UCS equipment:ChassisProfileFsmStage:stageStatus
        managed object property"
    ::= { cucsEquipmentChassisProfileFsmStageEntry 9 }

cucsEquipmentChassisProfileFsmTaskTable OBJECT-TYPE
    SYNTAX           SEQUENCE OF CucsEquipmentChassisProfileFsmTaskEntry
    MAX-ACCESS       not-accessible
    STATUS           current
    DESCRIPTION
        "Cisco UCS equipment:ChassisProfileFsmTask managed object table"
    ::= { cucsEquipmentObjects 185 }

cucsEquipmentChassisProfileFsmTaskEntry OBJECT-TYPE
    SYNTAX           CucsEquipmentChassisProfileFsmTaskEntry
    MAX-ACCESS       not-accessible
    STATUS           current
    DESCRIPTION
        "Entry for the cucsEquipmentChassisProfileFsmTaskTable table."
    INDEX { cucsEquipmentChassisProfileFsmTaskInstanceId }
    ::= { cucsEquipmentChassisProfileFsmTaskTable 1 }

CucsEquipmentChassisProfileFsmTaskEntry ::= SEQUENCE {
    cucsEquipmentChassisProfileFsmTaskInstanceId                     CucsManagedObjectId,
    cucsEquipmentChassisProfileFsmTaskDn                             CucsManagedObjectDn,
    cucsEquipmentChassisProfileFsmTaskRn                             SnmpAdminString,
    cucsEquipmentChassisProfileFsmTaskCompletion                     CucsFsmCompletion,
    cucsEquipmentChassisProfileFsmTaskFlags                          CucsEquipmentChassisProfileFsmTaskFlags,
    cucsEquipmentChassisProfileFsmTaskItem                           CucsEquipmentChassisProfileFsmTaskItem,
    cucsEquipmentChassisProfileFsmTaskSeqId                          Gauge32
}

cucsEquipmentChassisProfileFsmTaskInstanceId OBJECT-TYPE
    SYNTAX       CucsManagedObjectId
    MAX-ACCESS   not-accessible
    STATUS       current
    DESCRIPTION
        "Instance identifier of the managed object."
    ::= { cucsEquipmentChassisProfileFsmTaskEntry 1 }

cucsEquipmentChassisProfileFsmTaskDn OBJECT-TYPE
    SYNTAX       CucsManagedObjectDn
    MAX-ACCESS   read-only
    STATUS       current
    DESCRIPTION
        "Cisco UCS equipment:ChassisProfileFsmTask:dn managed
        object property"
    ::= { cucsEquipmentChassisProfileFsmTaskEntry 2 }

cucsEquipmentChassisProfileFsmTaskRn OBJECT-TYPE
    SYNTAX       SnmpAdminString
    MAX-ACCESS   read-only
    STATUS       current
    DESCRIPTION
        "Cisco UCS equipment:ChassisProfileFsmTask:rn managed
        object property"
    ::= { cucsEquipmentChassisProfileFsmTaskEntry 3 }

cucsEquipmentChassisProfileFsmTaskCompletion OBJECT-TYPE
    SYNTAX       CucsFsmCompletion
    MAX-ACCESS   read-only
    STATUS       current
    DESCRIPTION
        "Cisco UCS equipment:ChassisProfileFsmTask:completion
        managed object property"
    ::= { cucsEquipmentChassisProfileFsmTaskEntry 4 }

cucsEquipmentChassisProfileFsmTaskFlags OBJECT-TYPE
    SYNTAX       CucsEquipmentChassisProfileFsmTaskFlags
    MAX-ACCESS   read-only
    STATUS       current
    DESCRIPTION
        "Cisco UCS equipment:ChassisProfileFsmTask:flags
        managed object property"
    ::= { cucsEquipmentChassisProfileFsmTaskEntry 5 }

cucsEquipmentChassisProfileFsmTaskItem OBJECT-TYPE
    SYNTAX       CucsEquipmentChassisProfileFsmTaskItem
    MAX-ACCESS   read-only
    STATUS       current
    DESCRIPTION
        "Cisco UCS equipment:ChassisProfileFsmTask:item
        managed object property"
    ::= { cucsEquipmentChassisProfileFsmTaskEntry 6 }

cucsEquipmentChassisProfileFsmTaskSeqId OBJECT-TYPE
    SYNTAX       Gauge32
    MAX-ACCESS   read-only
    STATUS       current
    DESCRIPTION
        "Cisco UCS equipment:ChassisProfileFsmTask:seqId
        managed object property"
    ::= { cucsEquipmentChassisProfileFsmTaskEntry 7 }

cucsEquipmentChassisQualTable OBJECT-TYPE
    SYNTAX           SEQUENCE OF CucsEquipmentChassisQualEntry
    MAX-ACCESS       not-accessible
    STATUS           current
    DESCRIPTION
        "Cisco UCS equipment:ChassisQual managed object table"
    ::= { cucsEquipmentObjects 186 }

cucsEquipmentChassisQualEntry OBJECT-TYPE
    SYNTAX           CucsEquipmentChassisQualEntry
    MAX-ACCESS       not-accessible
    STATUS           current
    DESCRIPTION
        "Entry for the cucsEquipmentChassisQualTable table."
    INDEX { cucsEquipmentChassisQualInstanceId }
    ::= { cucsEquipmentChassisQualTable 1 }

CucsEquipmentChassisQualEntry ::= SEQUENCE {
    cucsEquipmentChassisQualInstanceId                               CucsManagedObjectId,
    cucsEquipmentChassisQualDn                                       CucsManagedObjectDn,
    cucsEquipmentChassisQualRn                                       SnmpAdminString,
    cucsEquipmentChassisQualMaxId                                    CucsEquipmentChassisQualMaxId,
    cucsEquipmentChassisQualMinId                                    CucsEquipmentChassisQualMinId
}

cucsEquipmentChassisQualInstanceId OBJECT-TYPE
    SYNTAX       CucsManagedObjectId
    MAX-ACCESS   not-accessible
    STATUS       current
    DESCRIPTION
        "Instance identifier of the managed object."
    ::= { cucsEquipmentChassisQualEntry 1 }

cucsEquipmentChassisQualDn OBJECT-TYPE
    SYNTAX       CucsManagedObjectDn
    MAX-ACCESS   read-only
    STATUS       current
    DESCRIPTION
        "Cisco UCS equipment:ChassisQual:dn managed object property"
    ::= { cucsEquipmentChassisQualEntry 2 }

cucsEquipmentChassisQualRn OBJECT-TYPE
    SYNTAX       SnmpAdminString
    MAX-ACCESS   read-only
    STATUS       current
    DESCRIPTION
        "Cisco UCS equipment:ChassisQual:rn managed object property"
    ::= { cucsEquipmentChassisQualEntry 3 }

cucsEquipmentChassisQualMaxId OBJECT-TYPE
    SYNTAX       CucsEquipmentChassisQualMaxId
    MAX-ACCESS   read-only
    STATUS       current
    DESCRIPTION
        "Cisco UCS equipment:ChassisQual:maxId managed object property"
    ::= { cucsEquipmentChassisQualEntry 4 }

cucsEquipmentChassisQualMinId OBJECT-TYPE
    SYNTAX       CucsEquipmentChassisQualMinId
    MAX-ACCESS   read-only
    STATUS       current
    DESCRIPTION
        "Cisco UCS equipment:ChassisQual:minId managed object property"
    ::= { cucsEquipmentChassisQualEntry 5 }

cucsEquipmentChassisStatsTable OBJECT-TYPE
    SYNTAX           SEQUENCE OF CucsEquipmentChassisStatsEntry
    MAX-ACCESS       not-accessible
    STATUS           current
    DESCRIPTION
        "Cisco UCS equipment:ChassisStats managed object table"
    ::= { cucsEquipmentObjects 10 }

cucsEquipmentChassisStatsEntry OBJECT-TYPE
    SYNTAX           CucsEquipmentChassisStatsEntry
    MAX-ACCESS       not-accessible
    STATUS           current
    DESCRIPTION
        "Entry for the cucsEquipmentChassisStatsTable table."
    INDEX { cucsEquipmentChassisStatsInstanceId }
    ::= { cucsEquipmentChassisStatsTable 1 }

CucsEquipmentChassisStatsEntry ::= SEQUENCE {
    cucsEquipmentChassisStatsInstanceId                              CucsManagedObjectId,
    cucsEquipmentChassisStatsDn                                      CucsManagedObjectDn,
    cucsEquipmentChassisStatsRn                                      SnmpAdminString,
    cucsEquipmentChassisStatsInputPower                              INTEGER,
    cucsEquipmentChassisStatsInputPowerAvg                           INTEGER,
    cucsEquipmentChassisStatsInputPowerMax                           INTEGER,
    cucsEquipmentChassisStatsInputPowerMin                           INTEGER,
    cucsEquipmentChassisStatsIntervals                               Gauge32,
    cucsEquipmentChassisStatsOutputPower                             INTEGER,
    cucsEquipmentChassisStatsOutputPowerAvg                          INTEGER,
    cucsEquipmentChassisStatsOutputPowerMax                          INTEGER,
    cucsEquipmentChassisStatsOutputPowerMin                          INTEGER,
    cucsEquipmentChassisStatsSuspect                                 TruthValue,
    cucsEquipmentChassisStatsThresholded                             CucsEquipmentChassisStatsThresholded,
    cucsEquipmentChassisStatsTimeCollected                           DateAndTime,
    cucsEquipmentChassisStatsUpdate                                  Gauge32,
    cucsEquipmentChassisStatsChassisI2CErrors                        Unsigned64,
    cucsEquipmentChassisStatsChassisI2CErrorsAvg                     Unsigned64,
    cucsEquipmentChassisStatsChassisI2CErrorsMax                     Unsigned64,
    cucsEquipmentChassisStatsChassisI2CErrorsMin                     Unsigned64
}

cucsEquipmentChassisStatsInstanceId OBJECT-TYPE
    SYNTAX       CucsManagedObjectId
    MAX-ACCESS   not-accessible
    STATUS       current
    DESCRIPTION
        "Instance identifier of the managed object."
    ::= { cucsEquipmentChassisStatsEntry 1 }

cucsEquipmentChassisStatsDn OBJECT-TYPE
    SYNTAX       CucsManagedObjectDn
    MAX-ACCESS   read-only
    STATUS       current
    DESCRIPTION
        "Cisco UCS equipment:ChassisStats:dn managed object property"
    ::= { cucsEquipmentChassisStatsEntry 2 }

cucsEquipmentChassisStatsRn OBJECT-TYPE
    SYNTAX       SnmpAdminString
    MAX-ACCESS   read-only
    STATUS       current
    DESCRIPTION
        "Cisco UCS equipment:ChassisStats:rn managed object property"
    ::= { cucsEquipmentChassisStatsEntry 3 }

cucsEquipmentChassisStatsInputPower OBJECT-TYPE
    SYNTAX       INTEGER
    MAX-ACCESS   read-only
    STATUS       current
    DESCRIPTION
        "Cisco UCS equipment:ChassisStats:inputPower managed
        object property"
    ::= { cucsEquipmentChassisStatsEntry 4 }

cucsEquipmentChassisStatsInputPowerAvg OBJECT-TYPE
    SYNTAX       INTEGER
    MAX-ACCESS   read-only
    STATUS       current
    DESCRIPTION
        "Cisco UCS equipment:ChassisStats:inputPowerAvg
        managed object property"
    ::= { cucsEquipmentChassisStatsEntry 5 }

cucsEquipmentChassisStatsInputPowerMax OBJECT-TYPE
    SYNTAX       INTEGER
    MAX-ACCESS   read-only
    STATUS       current
    DESCRIPTION
        "Cisco UCS equipment:ChassisStats:inputPowerMax
        managed object property"
    ::= { cucsEquipmentChassisStatsEntry 6 }

cucsEquipmentChassisStatsInputPowerMin OBJECT-TYPE
    SYNTAX       INTEGER
    MAX-ACCESS   read-only
    STATUS       current
    DESCRIPTION
        "Cisco UCS equipment:ChassisStats:inputPowerMin
        managed object property"
    ::= { cucsEquipmentChassisStatsEntry 7 }

cucsEquipmentChassisStatsIntervals OBJECT-TYPE
    SYNTAX       Gauge32
    MAX-ACCESS   read-only
    STATUS       current
    DESCRIPTION
        "Cisco UCS equipment:ChassisStats:intervals managed
        object property"
    ::= { cucsEquipmentChassisStatsEntry 8 }

cucsEquipmentChassisStatsOutputPower OBJECT-TYPE
    SYNTAX       INTEGER
    MAX-ACCESS   read-only
    STATUS       current
    DESCRIPTION
        "Cisco UCS equipment:ChassisStats:outputPower managed
        object property"
    ::= { cucsEquipmentChassisStatsEntry 9 }

cucsEquipmentChassisStatsOutputPowerAvg OBJECT-TYPE
    SYNTAX       INTEGER
    MAX-ACCESS   read-only
    STATUS       current
    DESCRIPTION
        "Cisco UCS equipment:ChassisStats:outputPowerAvg
        managed object property"
    ::= { cucsEquipmentChassisStatsEntry 10 }

cucsEquipmentChassisStatsOutputPowerMax OBJECT-TYPE
    SYNTAX       INTEGER
    MAX-ACCESS   read-only
    STATUS       current
    DESCRIPTION
        "Cisco UCS equipment:ChassisStats:outputPowerMax
        managed object property"
    ::= { cucsEquipmentChassisStatsEntry 11 }

cucsEquipmentChassisStatsOutputPowerMin OBJECT-TYPE
    SYNTAX       INTEGER
    MAX-ACCESS   read-only
    STATUS       current
    DESCRIPTION
        "Cisco UCS equipment:ChassisStats:outputPowerMin
        managed object property"
    ::= { cucsEquipmentChassisStatsEntry 12 }

cucsEquipmentChassisStatsSuspect OBJECT-TYPE
    SYNTAX       TruthValue
    MAX-ACCESS   read-only
    STATUS       current
    DESCRIPTION
        "Cisco UCS equipment:ChassisStats:suspect managed object property"
    ::= { cucsEquipmentChassisStatsEntry 13 }

cucsEquipmentChassisStatsThresholded OBJECT-TYPE
    SYNTAX       CucsEquipmentChassisStatsThresholded
    MAX-ACCESS   read-only
    STATUS       current
    DESCRIPTION
        "Cisco UCS equipment:ChassisStats:thresholded managed
        object property"
    ::= { cucsEquipmentChassisStatsEntry 14 }

cucsEquipmentChassisStatsTimeCollected OBJECT-TYPE
    SYNTAX       DateAndTime
    MAX-ACCESS   read-only
    STATUS       current
    DESCRIPTION
        "Cisco UCS equipment:ChassisStats:timeCollected
        managed object property"
    ::= { cucsEquipmentChassisStatsEntry 15 }

cucsEquipmentChassisStatsUpdate OBJECT-TYPE
    SYNTAX       Gauge32
    MAX-ACCESS   read-only
    STATUS       current
    DESCRIPTION
        "Cisco UCS equipment:ChassisStats:update managed object property"
    ::= { cucsEquipmentChassisStatsEntry 16 }

cucsEquipmentChassisStatsChassisI2CErrors OBJECT-TYPE
    SYNTAX       Unsigned64
    MAX-ACCESS   read-only
    STATUS       current
    DESCRIPTION
        "Cisco UCS equipment:ChassisStats:ChassisI2CErrors
        managed object property"
    ::= { cucsEquipmentChassisStatsEntry 17 }

cucsEquipmentChassisStatsChassisI2CErrorsAvg OBJECT-TYPE
    SYNTAX       Unsigned64
    MAX-ACCESS   read-only
    STATUS       current
    DESCRIPTION
        "Cisco UCS equipment:ChassisStats:ChassisI2CErrorsAvg
        managed object property"
    ::= { cucsEquipmentChassisStatsEntry 24 }

cucsEquipmentChassisStatsChassisI2CErrorsMax OBJECT-TYPE
    SYNTAX       Unsigned64
    MAX-ACCESS   read-only
    STATUS       current
    DESCRIPTION
        "Cisco UCS equipment:ChassisStats:ChassisI2CErrorsMax
        managed object property"
    ::= { cucsEquipmentChassisStatsEntry 25 }

cucsEquipmentChassisStatsChassisI2CErrorsMin OBJECT-TYPE
    SYNTAX       Unsigned64
    MAX-ACCESS   read-only
    STATUS       current
    DESCRIPTION
        "Cisco UCS equipment:ChassisStats:ChassisI2CErrorsMin
        managed object property"
    ::= { cucsEquipmentChassisStatsEntry 26 }

cucsEquipmentChassisStatsHistTable OBJECT-TYPE
    SYNTAX           SEQUENCE OF CucsEquipmentChassisStatsHistEntry
    MAX-ACCESS       not-accessible
    STATUS           current
    DESCRIPTION
        "Cisco UCS equipment:ChassisStatsHist managed object table"
    ::= { cucsEquipmentObjects 11 }

cucsEquipmentChassisStatsHistEntry OBJECT-TYPE
    SYNTAX           CucsEquipmentChassisStatsHistEntry
    MAX-ACCESS       not-accessible
    STATUS           current
    DESCRIPTION
        "Entry for the cucsEquipmentChassisStatsHistTable table."
    INDEX { cucsEquipmentChassisStatsHistInstanceId }
    ::= { cucsEquipmentChassisStatsHistTable 1 }

CucsEquipmentChassisStatsHistEntry ::= SEQUENCE {
    cucsEquipmentChassisStatsHistInstanceId                          CucsManagedObjectId,
    cucsEquipmentChassisStatsHistDn                                  CucsManagedObjectDn,
    cucsEquipmentChassisStatsHistRn                                  SnmpAdminString,
    cucsEquipmentChassisStatsHistId                                  Unsigned64,
    cucsEquipmentChassisStatsHistInputPower                          INTEGER,
    cucsEquipmentChassisStatsHistInputPowerAvg                       INTEGER,
    cucsEquipmentChassisStatsHistInputPowerMax                       INTEGER,
    cucsEquipmentChassisStatsHistInputPowerMin                       INTEGER,
    cucsEquipmentChassisStatsHistMostRecent                          TruthValue,
    cucsEquipmentChassisStatsHistOutputPower                         INTEGER,
    cucsEquipmentChassisStatsHistOutputPowerAvg                      INTEGER,
    cucsEquipmentChassisStatsHistOutputPowerMax                      INTEGER,
    cucsEquipmentChassisStatsHistOutputPowerMin                      INTEGER,
    cucsEquipmentChassisStatsHistSuspect                             TruthValue,
    cucsEquipmentChassisStatsHistThresholded                         CucsEquipmentChassisStatsHistThresholded,
    cucsEquipmentChassisStatsHistTimeCollected                       DateAndTime,
    cucsEquipmentChassisStatsHistChassisI2CErrors                    Unsigned64,
    cucsEquipmentChassisStatsHistChassisI2CErrorsAvg                 Unsigned64,
    cucsEquipmentChassisStatsHistChassisI2CErrorsMax                 Unsigned64,
    cucsEquipmentChassisStatsHistChassisI2CErrorsMin                 Unsigned64
}

cucsEquipmentChassisStatsHistInstanceId OBJECT-TYPE
    SYNTAX       CucsManagedObjectId
    MAX-ACCESS   not-accessible
    STATUS       current
    DESCRIPTION
        "Instance identifier of the managed object."
    ::= { cucsEquipmentChassisStatsHistEntry 1 }

cucsEquipmentChassisStatsHistDn OBJECT-TYPE
    SYNTAX       CucsManagedObjectDn
    MAX-ACCESS   read-only
    STATUS       current
    DESCRIPTION
        "Cisco UCS equipment:ChassisStatsHist:dn managed object property"
    ::= { cucsEquipmentChassisStatsHistEntry 2 }

cucsEquipmentChassisStatsHistRn OBJECT-TYPE
    SYNTAX       SnmpAdminString
    MAX-ACCESS   read-only
    STATUS       current
    DESCRIPTION
        "Cisco UCS equipment:ChassisStatsHist:rn managed object property"
    ::= { cucsEquipmentChassisStatsHistEntry 3 }

cucsEquipmentChassisStatsHistId OBJECT-TYPE
    SYNTAX       Unsigned64
    MAX-ACCESS   read-only
    STATUS       current
    DESCRIPTION
        "Cisco UCS equipment:ChassisStatsHist:id managed object property"
    ::= { cucsEquipmentChassisStatsHistEntry 4 }

cucsEquipmentChassisStatsHistInputPower OBJECT-TYPE
    SYNTAX       INTEGER
    MAX-ACCESS   read-only
    STATUS       current
    DESCRIPTION
        "Cisco UCS equipment:ChassisStatsHist:inputPower
        managed object property"
    ::= { cucsEquipmentChassisStatsHistEntry 5 }

cucsEquipmentChassisStatsHistInputPowerAvg OBJECT-TYPE
    SYNTAX       INTEGER
    MAX-ACCESS   read-only
    STATUS       current
    DESCRIPTION
        "Cisco UCS equipment:ChassisStatsHist:inputPowerAvg
        managed object property"
    ::= { cucsEquipmentChassisStatsHistEntry 6 }

cucsEquipmentChassisStatsHistInputPowerMax OBJECT-TYPE
    SYNTAX       INTEGER
    MAX-ACCESS   read-only
    STATUS       current
    DESCRIPTION
        "Cisco UCS equipment:ChassisStatsHist:inputPowerMax
        managed object property"
    ::= { cucsEquipmentChassisStatsHistEntry 7 }

cucsEquipmentChassisStatsHistInputPowerMin OBJECT-TYPE
    SYNTAX       INTEGER
    MAX-ACCESS   read-only
    STATUS       current
    DESCRIPTION
        "Cisco UCS equipment:ChassisStatsHist:inputPowerMin
        managed object property"
    ::= { cucsEquipmentChassisStatsHistEntry 8 }

cucsEquipmentChassisStatsHistMostRecent OBJECT-TYPE
    SYNTAX       TruthValue
    MAX-ACCESS   read-only
    STATUS       current
    DESCRIPTION
        "Cisco UCS equipment:ChassisStatsHist:mostRecent
        managed object property"
    ::= { cucsEquipmentChassisStatsHistEntry 9 }

cucsEquipmentChassisStatsHistOutputPower OBJECT-TYPE
    SYNTAX       INTEGER
    MAX-ACCESS   read-only
    STATUS       current
    DESCRIPTION
        "Cisco UCS equipment:ChassisStatsHist:outputPower
        managed object property"
    ::= { cucsEquipmentChassisStatsHistEntry 10 }

cucsEquipmentChassisStatsHistOutputPowerAvg OBJECT-TYPE
    SYNTAX       INTEGER
    MAX-ACCESS   read-only
    STATUS       current
    DESCRIPTION
        "Cisco UCS equipment:ChassisStatsHist:outputPowerAvg
        managed object property"
    ::= { cucsEquipmentChassisStatsHistEntry 11 }

cucsEquipmentChassisStatsHistOutputPowerMax OBJECT-TYPE
    SYNTAX       INTEGER
    MAX-ACCESS   read-only
    STATUS       current
    DESCRIPTION
        "Cisco UCS equipment:ChassisStatsHist:outputPowerMax
        managed object property"
    ::= { cucsEquipmentChassisStatsHistEntry 12 }

cucsEquipmentChassisStatsHistOutputPowerMin OBJECT-TYPE
    SYNTAX       INTEGER
    MAX-ACCESS   read-only
    STATUS       current
    DESCRIPTION
        "Cisco UCS equipment:ChassisStatsHist:outputPowerMin
        managed object property"
    ::= { cucsEquipmentChassisStatsHistEntry 13 }

cucsEquipmentChassisStatsHistSuspect OBJECT-TYPE
    SYNTAX       TruthValue
    MAX-ACCESS   read-only
    STATUS       current
    DESCRIPTION
        "Cisco UCS equipment:ChassisStatsHist:suspect managed
        object property"
    ::= { cucsEquipmentChassisStatsHistEntry 14 }

cucsEquipmentChassisStatsHistThresholded OBJECT-TYPE
    SYNTAX       CucsEquipmentChassisStatsHistThresholded
    MAX-ACCESS   read-only
    STATUS       current
    DESCRIPTION
        "Cisco UCS equipment:ChassisStatsHist:thresholded
        managed object property"
    ::= { cucsEquipmentChassisStatsHistEntry 15 }

cucsEquipmentChassisStatsHistTimeCollected OBJECT-TYPE
    SYNTAX       DateAndTime
    MAX-ACCESS   read-only
    STATUS       current
    DESCRIPTION
        "Cisco UCS equipment:ChassisStatsHist:timeCollected
        managed object property"
    ::= { cucsEquipmentChassisStatsHistEntry 16 }

cucsEquipmentChassisStatsHistChassisI2CErrors OBJECT-TYPE
    SYNTAX       Unsigned64
    MAX-ACCESS   read-only
    STATUS       current
    DESCRIPTION
        "Cisco UCS equipment:ChassisStatsHist:ChassisI2CErrors
        managed object property"
    ::= { cucsEquipmentChassisStatsHistEntry 17 }

cucsEquipmentChassisStatsHistChassisI2CErrorsAvg OBJECT-TYPE
    SYNTAX       Unsigned64
    MAX-ACCESS   read-only
    STATUS       current
    DESCRIPTION
        "Cisco UCS equipment:ChassisStatsHist:ChassisI2CErrorsAvg
        managed object property"
    ::= { cucsEquipmentChassisStatsHistEntry 22 }

cucsEquipmentChassisStatsHistChassisI2CErrorsMax OBJECT-TYPE
    SYNTAX       Unsigned64
    MAX-ACCESS   read-only
    STATUS       current
    DESCRIPTION
        "Cisco UCS equipment:ChassisStatsHist:ChassisI2CErrorsMax
        managed object property"
    ::= { cucsEquipmentChassisStatsHistEntry 23 }

cucsEquipmentChassisStatsHistChassisI2CErrorsMin OBJECT-TYPE
    SYNTAX       Unsigned64
    MAX-ACCESS   read-only
    STATUS       current
    DESCRIPTION
        "Cisco UCS equipment:ChassisStatsHist:ChassisI2CErrorsMin
        managed object property"
    ::= { cucsEquipmentChassisStatsHistEntry 24 }

cucsEquipmentCimcVmediaTable OBJECT-TYPE
    SYNTAX           SEQUENCE OF CucsEquipmentCimcVmediaEntry
    MAX-ACCESS       not-accessible
    STATUS           current
    DESCRIPTION
        "Cisco UCS equipment:CimcVmedia managed object table"
    ::= { cucsEquipmentObjects 126 }

cucsEquipmentCimcVmediaEntry OBJECT-TYPE
    SYNTAX           CucsEquipmentCimcVmediaEntry
    MAX-ACCESS       not-accessible
    STATUS           current
    DESCRIPTION
        "Entry for the cucsEquipmentCimcVmediaTable table."
    INDEX { cucsEquipmentCimcVmediaInstanceId }
    ::= { cucsEquipmentCimcVmediaTable 1 }

CucsEquipmentCimcVmediaEntry ::= SEQUENCE {
    cucsEquipmentCimcVmediaInstanceId                                CucsManagedObjectId,
    cucsEquipmentCimcVmediaDn                                        CucsManagedObjectDn,
    cucsEquipmentCimcVmediaRn                                        SnmpAdminString,
    cucsEquipmentCimcVmediaDescr                                     SnmpAdminString,
    cucsEquipmentCimcVmediaIntId                                     SnmpAdminString,
    cucsEquipmentCimcVmediaIsSupported                               TruthValue,
    cucsEquipmentCimcVmediaMinBiosVersion                            SnmpAdminString,
    cucsEquipmentCimcVmediaMinCimcVersion                            SnmpAdminString,
    cucsEquipmentCimcVmediaName                                      SnmpAdminString,
    cucsEquipmentCimcVmediaPolicyLevel                               Gauge32,
    cucsEquipmentCimcVmediaPolicyOwner                               CucsPolicyPolicyOwner
}

cucsEquipmentCimcVmediaInstanceId OBJECT-TYPE
    SYNTAX       CucsManagedObjectId
    MAX-ACCESS   not-accessible
    STATUS       current
    DESCRIPTION
        "Instance identifier of the managed object."
    ::= { cucsEquipmentCimcVmediaEntry 1 }

cucsEquipmentCimcVmediaDn OBJECT-TYPE
    SYNTAX       CucsManagedObjectDn
    MAX-ACCESS   read-only
    STATUS       current
    DESCRIPTION
        "Cisco UCS equipment:CimcVmedia:dn managed object property"
    ::= { cucsEquipmentCimcVmediaEntry 2 }

cucsEquipmentCimcVmediaRn OBJECT-TYPE
    SYNTAX       SnmpAdminString
    MAX-ACCESS   read-only
    STATUS       current
    DESCRIPTION
        "Cisco UCS equipment:CimcVmedia:rn managed object property"
    ::= { cucsEquipmentCimcVmediaEntry 3 }

cucsEquipmentCimcVmediaDescr OBJECT-TYPE
    SYNTAX       SnmpAdminString
    MAX-ACCESS   read-only
    STATUS       current
    DESCRIPTION
        "Cisco UCS equipment:CimcVmedia:descr managed object property"
    ::= { cucsEquipmentCimcVmediaEntry 4 }

cucsEquipmentCimcVmediaIntId OBJECT-TYPE
    SYNTAX       SnmpAdminString
    MAX-ACCESS   read-only
    STATUS       current
    DESCRIPTION
        "Cisco UCS equipment:CimcVmedia:intId managed object property"
    ::= { cucsEquipmentCimcVmediaEntry 5 }

cucsEquipmentCimcVmediaIsSupported OBJECT-TYPE
    SYNTAX       TruthValue
    MAX-ACCESS   read-only
    STATUS       current
    DESCRIPTION
        "Cisco UCS equipment:CimcVmedia:isSupported managed
        object property"
    ::= { cucsEquipmentCimcVmediaEntry 6 }

cucsEquipmentCimcVmediaMinBiosVersion OBJECT-TYPE
    SYNTAX       SnmpAdminString
    MAX-ACCESS   read-only
    STATUS       current
    DESCRIPTION
        "Cisco UCS equipment:CimcVmedia:minBiosVersion
        managed object property"
    ::= { cucsEquipmentCimcVmediaEntry 7 }

cucsEquipmentCimcVmediaMinCimcVersion OBJECT-TYPE
    SYNTAX       SnmpAdminString
    MAX-ACCESS   read-only
    STATUS       current
    DESCRIPTION
        "Cisco UCS equipment:CimcVmedia:minCimcVersion
        managed object property"
    ::= { cucsEquipmentCimcVmediaEntry 8 }

cucsEquipmentCimcVmediaName OBJECT-TYPE
    SYNTAX       SnmpAdminString
    MAX-ACCESS   read-only
    STATUS       current
    DESCRIPTION
        "Cisco UCS equipment:CimcVmedia:name managed object property"
    ::= { cucsEquipmentCimcVmediaEntry 9 }

cucsEquipmentCimcVmediaPolicyLevel OBJECT-TYPE
    SYNTAX       Gauge32
    MAX-ACCESS   read-only
    STATUS       current
    DESCRIPTION
        "Cisco UCS equipment:CimcVmedia:policyLevel managed
        object property"
    ::= { cucsEquipmentCimcVmediaEntry 10 }

cucsEquipmentCimcVmediaPolicyOwner OBJECT-TYPE
    SYNTAX       CucsPolicyPolicyOwner
    MAX-ACCESS   read-only
    STATUS       current
    DESCRIPTION
        "Cisco UCS equipment:CimcVmedia:policyOwner managed
        object property"
    ::= { cucsEquipmentCimcVmediaEntry 11 }

cucsEquipmentCiscoOsOpenGateTable OBJECT-TYPE
    SYNTAX           SEQUENCE OF CucsEquipmentCiscoOsOpenGateEntry
    MAX-ACCESS       not-accessible
    STATUS           current
    DESCRIPTION
        "Cisco UCS equipment:CiscoOsOpenGate managed object table"
    ::= { cucsEquipmentObjects 206 }

cucsEquipmentCiscoOsOpenGateEntry OBJECT-TYPE
    SYNTAX           CucsEquipmentCiscoOsOpenGateEntry
    MAX-ACCESS       not-accessible
    STATUS           current
    DESCRIPTION
        "Entry for the cucsEquipmentCiscoOsOpenGateTable table."
    INDEX { cucsEquipmentCiscoOsOpenGateInstanceId }
    ::= { cucsEquipmentCiscoOsOpenGateTable 1 }

CucsEquipmentCiscoOsOpenGateEntry ::= SEQUENCE {
    cucsEquipmentCiscoOsOpenGateInstanceId                           CucsManagedObjectId,
    cucsEquipmentCiscoOsOpenGateDn                                   CucsManagedObjectDn,
    cucsEquipmentCiscoOsOpenGateRn                                   SnmpAdminString,
    cucsEquipmentCiscoOsOpenGateDescr                                SnmpAdminString,
    cucsEquipmentCiscoOsOpenGateIntId                                SnmpAdminString,
    cucsEquipmentCiscoOsOpenGateIsSupported                          TruthValue,
    cucsEquipmentCiscoOsOpenGateMinCimcVersion                       SnmpAdminString,
    cucsEquipmentCiscoOsOpenGateName                                 SnmpAdminString,
    cucsEquipmentCiscoOsOpenGatePolicyLevel                          Gauge32,
    cucsEquipmentCiscoOsOpenGatePolicyOwner                          CucsPolicyPolicyOwner
}

cucsEquipmentCiscoOsOpenGateInstanceId OBJECT-TYPE
    SYNTAX       CucsManagedObjectId
    MAX-ACCESS   not-accessible
    STATUS       current
    DESCRIPTION
        "Instance identifier of the managed object."
    ::= { cucsEquipmentCiscoOsOpenGateEntry 1 }

cucsEquipmentCiscoOsOpenGateDn OBJECT-TYPE
    SYNTAX       CucsManagedObjectDn
    MAX-ACCESS   read-only
    STATUS       current
    DESCRIPTION
        "Cisco UCS equipment:CiscoOsOpenGate:dn managed object property"
    ::= { cucsEquipmentCiscoOsOpenGateEntry 2 }

cucsEquipmentCiscoOsOpenGateRn OBJECT-TYPE
    SYNTAX       SnmpAdminString
    MAX-ACCESS   read-only
    STATUS       current
    DESCRIPTION
        "Cisco UCS equipment:CiscoOsOpenGate:rn managed object property"
    ::= { cucsEquipmentCiscoOsOpenGateEntry 3 }

cucsEquipmentCiscoOsOpenGateDescr OBJECT-TYPE
    SYNTAX       SnmpAdminString
    MAX-ACCESS   read-only
    STATUS       current
    DESCRIPTION
        "Cisco UCS equipment:CiscoOsOpenGate:descr managed
        object property"
    ::= { cucsEquipmentCiscoOsOpenGateEntry 4 }

cucsEquipmentCiscoOsOpenGateIntId OBJECT-TYPE
    SYNTAX       SnmpAdminString
    MAX-ACCESS   read-only
    STATUS       current
    DESCRIPTION
        "Cisco UCS equipment:CiscoOsOpenGate:intId managed
        object property"
    ::= { cucsEquipmentCiscoOsOpenGateEntry 5 }

cucsEquipmentCiscoOsOpenGateIsSupported OBJECT-TYPE
    SYNTAX       TruthValue
    MAX-ACCESS   read-only
    STATUS       current
    DESCRIPTION
        "Cisco UCS equipment:CiscoOsOpenGate:isSupported
        managed object property"
    ::= { cucsEquipmentCiscoOsOpenGateEntry 6 }

cucsEquipmentCiscoOsOpenGateMinCimcVersion OBJECT-TYPE
    SYNTAX       SnmpAdminString
    MAX-ACCESS   read-only
    STATUS       current
    DESCRIPTION
        "Cisco UCS equipment:CiscoOsOpenGate:minCimcVersion
        managed object property"
    ::= { cucsEquipmentCiscoOsOpenGateEntry 7 }

cucsEquipmentCiscoOsOpenGateName OBJECT-TYPE
    SYNTAX       SnmpAdminString
    MAX-ACCESS   read-only
    STATUS       current
    DESCRIPTION
        "Cisco UCS equipment:CiscoOsOpenGate:name managed object property"
    ::= { cucsEquipmentCiscoOsOpenGateEntry 8 }

cucsEquipmentCiscoOsOpenGatePolicyLevel OBJECT-TYPE
    SYNTAX       Gauge32
    MAX-ACCESS   read-only
    STATUS       current
    DESCRIPTION
        "Cisco UCS equipment:CiscoOsOpenGate:policyLevel
        managed object property"
    ::= { cucsEquipmentCiscoOsOpenGateEntry 9 }

cucsEquipmentCiscoOsOpenGatePolicyOwner OBJECT-TYPE
    SYNTAX       CucsPolicyPolicyOwner
    MAX-ACCESS   read-only
    STATUS       current
    DESCRIPTION
        "Cisco UCS equipment:CiscoOsOpenGate:policyOwner
        managed object property"
    ::= { cucsEquipmentCiscoOsOpenGateEntry 10 }

cucsEquipmentComputeConnTable OBJECT-TYPE
    SYNTAX           SEQUENCE OF CucsEquipmentComputeConnEntry
    MAX-ACCESS       not-accessible
    STATUS           current
    DESCRIPTION
        "Cisco UCS equipment:ComputeConn managed object table"
    ::= { cucsEquipmentObjects 223 }

cucsEquipmentComputeConnEntry OBJECT-TYPE
    SYNTAX           CucsEquipmentComputeConnEntry
    MAX-ACCESS       not-accessible
    STATUS           current
    DESCRIPTION
        "Entry for the cucsEquipmentComputeConnTable table."
    INDEX { cucsEquipmentComputeConnInstanceId }
    ::= { cucsEquipmentComputeConnTable 1 }

CucsEquipmentComputeConnEntry ::= SEQUENCE {
    cucsEquipmentComputeConnInstanceId                               CucsManagedObjectId,
    cucsEquipmentComputeConnDn                                       CucsManagedObjectDn,
    cucsEquipmentComputeConnRn                                       SnmpAdminString,
    cucsEquipmentComputeConnServerSiocConnectivity                   CucsEquipmentServerSiocConnState
}

cucsEquipmentComputeConnInstanceId OBJECT-TYPE
    SYNTAX       CucsManagedObjectId
    MAX-ACCESS   not-accessible
    STATUS       current
    DESCRIPTION
        "Instance identifier of the managed object."
    ::= { cucsEquipmentComputeConnEntry 1 }

cucsEquipmentComputeConnDn OBJECT-TYPE
    SYNTAX       CucsManagedObjectDn
    MAX-ACCESS   read-only
    STATUS       current
    DESCRIPTION
        "Cisco UCS equipment:ComputeConn:dn managed object property"
    ::= { cucsEquipmentComputeConnEntry 2 }

cucsEquipmentComputeConnRn OBJECT-TYPE
    SYNTAX       SnmpAdminString
    MAX-ACCESS   read-only
    STATUS       current
    DESCRIPTION
        "Cisco UCS equipment:ComputeConn:rn managed object property"
    ::= { cucsEquipmentComputeConnEntry 3 }

cucsEquipmentComputeConnServerSiocConnectivity OBJECT-TYPE
    SYNTAX       CucsEquipmentServerSiocConnState
    MAX-ACCESS   read-only
    STATUS       current
    DESCRIPTION
        "Cisco UCS equipment:ComputeConn:serverSiocConnectivity
        managed object property"
    ::= { cucsEquipmentComputeConnEntry 4 }

cucsEquipmentComputeConnPolicyTable OBJECT-TYPE
    SYNTAX           SEQUENCE OF CucsEquipmentComputeConnPolicyEntry
    MAX-ACCESS       not-accessible
    STATUS           current
    DESCRIPTION
        "Cisco UCS equipment:ComputeConnPolicy managed object table"
    ::= { cucsEquipmentObjects 224 }

cucsEquipmentComputeConnPolicyEntry OBJECT-TYPE
    SYNTAX           CucsEquipmentComputeConnPolicyEntry
    MAX-ACCESS       not-accessible
    STATUS           current
    DESCRIPTION
        "Entry for the cucsEquipmentComputeConnPolicyTable table."
    INDEX { cucsEquipmentComputeConnPolicyInstanceId }
    ::= { cucsEquipmentComputeConnPolicyTable 1 }

CucsEquipmentComputeConnPolicyEntry ::= SEQUENCE {
    cucsEquipmentComputeConnPolicyInstanceId                         CucsManagedObjectId,
    cucsEquipmentComputeConnPolicyDn                                 CucsManagedObjectDn,
    cucsEquipmentComputeConnPolicyRn                                 SnmpAdminString,
    cucsEquipmentComputeConnPolicyDescr                              SnmpAdminString,
    cucsEquipmentComputeConnPolicyIntId                              SnmpAdminString,
    cucsEquipmentComputeConnPolicyName                               SnmpAdminString,
    cucsEquipmentComputeConnPolicyPolicyLevel                        Gauge32,
    cucsEquipmentComputeConnPolicyPolicyOwner                        CucsPolicyPolicyOwner,
    cucsEquipmentComputeConnPolicyServerSiocConnectivity             CucsEquipmentServerSiocConnState
}

cucsEquipmentComputeConnPolicyInstanceId OBJECT-TYPE
    SYNTAX       CucsManagedObjectId
    MAX-ACCESS   not-accessible
    STATUS       current
    DESCRIPTION
        "Instance identifier of the managed object."
    ::= { cucsEquipmentComputeConnPolicyEntry 1 }

cucsEquipmentComputeConnPolicyDn OBJECT-TYPE
    SYNTAX       CucsManagedObjectDn
    MAX-ACCESS   read-only
    STATUS       current
    DESCRIPTION
        "Cisco UCS equipment:ComputeConnPolicy:dn managed object property"
    ::= { cucsEquipmentComputeConnPolicyEntry 2 }

cucsEquipmentComputeConnPolicyRn OBJECT-TYPE
    SYNTAX       SnmpAdminString
    MAX-ACCESS   read-only
    STATUS       current
    DESCRIPTION
        "Cisco UCS equipment:ComputeConnPolicy:rn managed object property"
    ::= { cucsEquipmentComputeConnPolicyEntry 3 }

cucsEquipmentComputeConnPolicyDescr OBJECT-TYPE
    SYNTAX       SnmpAdminString
    MAX-ACCESS   read-only
    STATUS       current
    DESCRIPTION
        "Cisco UCS equipment:ComputeConnPolicy:descr managed
        object property"
    ::= { cucsEquipmentComputeConnPolicyEntry 4 }

cucsEquipmentComputeConnPolicyIntId OBJECT-TYPE
    SYNTAX       SnmpAdminString
    MAX-ACCESS   read-only
    STATUS       current
    DESCRIPTION
        "Cisco UCS equipment:ComputeConnPolicy:intId managed
        object property"
    ::= { cucsEquipmentComputeConnPolicyEntry 5 }

cucsEquipmentComputeConnPolicyName OBJECT-TYPE
    SYNTAX       SnmpAdminString
    MAX-ACCESS   read-only
    STATUS       current
    DESCRIPTION
        "Cisco UCS equipment:ComputeConnPolicy:name managed
        object property"
    ::= { cucsEquipmentComputeConnPolicyEntry 6 }

cucsEquipmentComputeConnPolicyPolicyLevel OBJECT-TYPE
    SYNTAX       Gauge32
    MAX-ACCESS   read-only
    STATUS       current
    DESCRIPTION
        "Cisco UCS equipment:ComputeConnPolicy:policyLevel
        managed object property"
    ::= { cucsEquipmentComputeConnPolicyEntry 7 }

cucsEquipmentComputeConnPolicyPolicyOwner OBJECT-TYPE
    SYNTAX       CucsPolicyPolicyOwner
    MAX-ACCESS   read-only
    STATUS       current
    DESCRIPTION
        "Cisco UCS equipment:ComputeConnPolicy:policyOwner
        managed object property"
    ::= { cucsEquipmentComputeConnPolicyEntry 8 }

cucsEquipmentComputeConnPolicyServerSiocConnectivity OBJECT-TYPE
    SYNTAX       CucsEquipmentServerSiocConnState
    MAX-ACCESS   read-only
    STATUS       current
    DESCRIPTION
        "Cisco UCS equipment:ComputeConnPolicy:serverSiocConnectivity
        managed object property"
    ::= { cucsEquipmentComputeConnPolicyEntry 9 }

cucsEquipmentDbgPluginCapProviderTable OBJECT-TYPE
    SYNTAX           SEQUENCE OF CucsEquipmentDbgPluginCapProviderEntry
    MAX-ACCESS       not-accessible
    STATUS           current
    DESCRIPTION
        "Cisco UCS equipment:DbgPluginCapProvider managed object table"
    ::= { cucsEquipmentObjects 77 }

cucsEquipmentDbgPluginCapProviderEntry OBJECT-TYPE
    SYNTAX           CucsEquipmentDbgPluginCapProviderEntry
    MAX-ACCESS       not-accessible
    STATUS           current
    DESCRIPTION
        "Entry for the cucsEquipmentDbgPluginCapProviderTable table."
    INDEX { cucsEquipmentDbgPluginCapProviderInstanceId }
    ::= { cucsEquipmentDbgPluginCapProviderTable 1 }

CucsEquipmentDbgPluginCapProviderEntry ::= SEQUENCE {
    cucsEquipmentDbgPluginCapProviderInstanceId                      CucsManagedObjectId,
    cucsEquipmentDbgPluginCapProviderDn                              CucsManagedObjectDn,
    cucsEquipmentDbgPluginCapProviderRn                              SnmpAdminString,
    cucsEquipmentDbgPluginCapProviderDeleted                         TruthValue,
    cucsEquipmentDbgPluginCapProviderDeprecated                      TruthValue,
    cucsEquipmentDbgPluginCapProviderGencount                        Gauge32,
    cucsEquipmentDbgPluginCapProviderMgmtPlaneVer                    SnmpAdminString,
    cucsEquipmentDbgPluginCapProviderModel                           SnmpAdminString,
    cucsEquipmentDbgPluginCapProviderPromCardType                    Gauge32,
    cucsEquipmentDbgPluginCapProviderRevision                        SnmpAdminString,
    cucsEquipmentDbgPluginCapProviderVendor                          SnmpAdminString,
    cucsEquipmentDbgPluginCapProviderElementLoadFailures             Gauge32,
    cucsEquipmentDbgPluginCapProviderElementsLoaded                  Gauge32,
    cucsEquipmentDbgPluginCapProviderLoadErrors                      Gauge32,
    cucsEquipmentDbgPluginCapProviderLoadWarnings                    Gauge32
}

cucsEquipmentDbgPluginCapProviderInstanceId OBJECT-TYPE
    SYNTAX       CucsManagedObjectId
    MAX-ACCESS   not-accessible
    STATUS       current
    DESCRIPTION
        "Instance identifier of the managed object."
    ::= { cucsEquipmentDbgPluginCapProviderEntry 1 }

cucsEquipmentDbgPluginCapProviderDn OBJECT-TYPE
    SYNTAX       CucsManagedObjectDn
    MAX-ACCESS   read-only
    STATUS       current
    DESCRIPTION
        "Cisco UCS equipment:DbgPluginCapProvider:dn managed
        object property"
    ::= { cucsEquipmentDbgPluginCapProviderEntry 2 }

cucsEquipmentDbgPluginCapProviderRn OBJECT-TYPE
    SYNTAX       SnmpAdminString
    MAX-ACCESS   read-only
    STATUS       current
    DESCRIPTION
        "Cisco UCS equipment:DbgPluginCapProvider:rn managed
        object property"
    ::= { cucsEquipmentDbgPluginCapProviderEntry 3 }

cucsEquipmentDbgPluginCapProviderDeleted OBJECT-TYPE
    SYNTAX       TruthValue
    MAX-ACCESS   read-only
    STATUS       current
    DESCRIPTION
        "Cisco UCS equipment:DbgPluginCapProvider:deleted
        managed object property"
    ::= { cucsEquipmentDbgPluginCapProviderEntry 4 }

cucsEquipmentDbgPluginCapProviderDeprecated OBJECT-TYPE
    SYNTAX       TruthValue
    MAX-ACCESS   read-only
    STATUS       current
    DESCRIPTION
        "Cisco UCS equipment:DbgPluginCapProvider:deprecated
        managed object property"
    ::= { cucsEquipmentDbgPluginCapProviderEntry 5 }

cucsEquipmentDbgPluginCapProviderGencount OBJECT-TYPE
    SYNTAX       Gauge32
    MAX-ACCESS   read-only
    STATUS       current
    DESCRIPTION
        "Cisco UCS equipment:DbgPluginCapProvider:gencount
        managed object property"
    ::= { cucsEquipmentDbgPluginCapProviderEntry 6 }

cucsEquipmentDbgPluginCapProviderMgmtPlaneVer OBJECT-TYPE
    SYNTAX       SnmpAdminString
    MAX-ACCESS   read-only
    STATUS       current
    DESCRIPTION
        "Cisco UCS equipment:DbgPluginCapProvider:mgmtPlaneVer
        managed object property"
    ::= { cucsEquipmentDbgPluginCapProviderEntry 7 }

cucsEquipmentDbgPluginCapProviderModel OBJECT-TYPE
    SYNTAX       SnmpAdminString
    MAX-ACCESS   read-only
    STATUS       current
    DESCRIPTION
        "Cisco UCS equipment:DbgPluginCapProvider:model
        managed object property"
    ::= { cucsEquipmentDbgPluginCapProviderEntry 8 }

cucsEquipmentDbgPluginCapProviderPromCardType OBJECT-TYPE
    SYNTAX       Gauge32
    MAX-ACCESS   read-only
    STATUS       current
    DESCRIPTION
        "Cisco UCS equipment:DbgPluginCapProvider:promCardType
        managed object property"
    ::= { cucsEquipmentDbgPluginCapProviderEntry 9 }

cucsEquipmentDbgPluginCapProviderRevision OBJECT-TYPE
    SYNTAX       SnmpAdminString
    MAX-ACCESS   read-only
    STATUS       current
    DESCRIPTION
        "Cisco UCS equipment:DbgPluginCapProvider:revision
        managed object property"
    ::= { cucsEquipmentDbgPluginCapProviderEntry 10 }

cucsEquipmentDbgPluginCapProviderVendor OBJECT-TYPE
    SYNTAX       SnmpAdminString
    MAX-ACCESS   read-only
    STATUS       current
    DESCRIPTION
        "Cisco UCS equipment:DbgPluginCapProvider:vendor
        managed object property"
    ::= { cucsEquipmentDbgPluginCapProviderEntry 11 }

cucsEquipmentDbgPluginCapProviderElementLoadFailures OBJECT-TYPE
    SYNTAX       Gauge32
    MAX-ACCESS   read-only
    STATUS       current
    DESCRIPTION
        "Cisco UCS equipment:DbgPluginCapProvider:elementLoadFailures
        managed object property"
    ::= { cucsEquipmentDbgPluginCapProviderEntry 12 }

cucsEquipmentDbgPluginCapProviderElementsLoaded OBJECT-TYPE
    SYNTAX       Gauge32
    MAX-ACCESS   read-only
    STATUS       current
    DESCRIPTION
        "Cisco UCS equipment:DbgPluginCapProvider:elementsLoaded
        managed object property"
    ::= { cucsEquipmentDbgPluginCapProviderEntry 13 }

cucsEquipmentDbgPluginCapProviderLoadErrors OBJECT-TYPE
    SYNTAX       Gauge32
    MAX-ACCESS   read-only
    STATUS       current
    DESCRIPTION
        "Cisco UCS equipment:DbgPluginCapProvider:loadErrors
        managed object property"
    ::= { cucsEquipmentDbgPluginCapProviderEntry 14 }

cucsEquipmentDbgPluginCapProviderLoadWarnings OBJECT-TYPE
    SYNTAX       Gauge32
    MAX-ACCESS   read-only
    STATUS       current
    DESCRIPTION
        "Cisco UCS equipment:DbgPluginCapProvider:loadWarnings
        managed object property"
    ::= { cucsEquipmentDbgPluginCapProviderEntry 15 }

cucsEquipmentDimmEntryTable OBJECT-TYPE
    SYNTAX           SEQUENCE OF CucsEquipmentDimmEntryEntry
    MAX-ACCESS       not-accessible
    STATUS           current
    DESCRIPTION
        "Cisco UCS equipment:DimmEntry managed object table"
    ::= { cucsEquipmentObjects 99 }

cucsEquipmentDimmEntryEntry OBJECT-TYPE
    SYNTAX           CucsEquipmentDimmEntryEntry
    MAX-ACCESS       not-accessible
    STATUS           current
    DESCRIPTION
        "Entry for the cucsEquipmentDimmEntryTable table."
    INDEX { cucsEquipmentDimmEntryInstanceId }
    ::= { cucsEquipmentDimmEntryTable 1 }

CucsEquipmentDimmEntryEntry ::= SEQUENCE {
    cucsEquipmentDimmEntryInstanceId                                 CucsManagedObjectId,
    cucsEquipmentDimmEntryDn                                         CucsManagedObjectDn,
    cucsEquipmentDimmEntryRn                                         SnmpAdminString,
    cucsEquipmentDimmEntryId                                         Gauge32,
    cucsEquipmentDimmEntrySmbiosname                                 SnmpAdminString
}

cucsEquipmentDimmEntryInstanceId OBJECT-TYPE
    SYNTAX       CucsManagedObjectId
    MAX-ACCESS   not-accessible
    STATUS       current
    DESCRIPTION
        "Instance identifier of the managed object."
    ::= { cucsEquipmentDimmEntryEntry 1 }

cucsEquipmentDimmEntryDn OBJECT-TYPE
    SYNTAX       CucsManagedObjectDn
    MAX-ACCESS   read-only
    STATUS       current
    DESCRIPTION
        "Cisco UCS equipment:DimmEntry:dn managed object property"
    ::= { cucsEquipmentDimmEntryEntry 2 }

cucsEquipmentDimmEntryRn OBJECT-TYPE
    SYNTAX       SnmpAdminString
    MAX-ACCESS   read-only
    STATUS       current
    DESCRIPTION
        "Cisco UCS equipment:DimmEntry:rn managed object property"
    ::= { cucsEquipmentDimmEntryEntry 3 }

cucsEquipmentDimmEntryId OBJECT-TYPE
    SYNTAX       Gauge32
    MAX-ACCESS   read-only
    STATUS       current
    DESCRIPTION
        "Cisco UCS equipment:DimmEntry:id managed object property"
    ::= { cucsEquipmentDimmEntryEntry 4 }

cucsEquipmentDimmEntrySmbiosname OBJECT-TYPE
    SYNTAX       SnmpAdminString
    MAX-ACCESS   read-only
    STATUS       current
    DESCRIPTION
        "Cisco UCS equipment:DimmEntry:smbiosname managed object property"
    ::= { cucsEquipmentDimmEntryEntry 5 }

cucsEquipmentDimmMappingTable OBJECT-TYPE
    SYNTAX           SEQUENCE OF CucsEquipmentDimmMappingEntry
    MAX-ACCESS       not-accessible
    STATUS           current
    DESCRIPTION
        "Cisco UCS equipment:DimmMapping managed object table"
    ::= { cucsEquipmentObjects 100 }

cucsEquipmentDimmMappingEntry OBJECT-TYPE
    SYNTAX           CucsEquipmentDimmMappingEntry
    MAX-ACCESS       not-accessible
    STATUS           current
    DESCRIPTION
        "Entry for the cucsEquipmentDimmMappingTable table."
    INDEX { cucsEquipmentDimmMappingInstanceId }
    ::= { cucsEquipmentDimmMappingTable 1 }

CucsEquipmentDimmMappingEntry ::= SEQUENCE {
    cucsEquipmentDimmMappingInstanceId                               CucsManagedObjectId,
    cucsEquipmentDimmMappingDn                                       CucsManagedObjectDn,
    cucsEquipmentDimmMappingRn                                       SnmpAdminString,
    cucsEquipmentDimmMappingDescr                                    SnmpAdminString,
    cucsEquipmentDimmMappingIntId                                    SnmpAdminString,
    cucsEquipmentDimmMappingName                                     SnmpAdminString,
    cucsEquipmentDimmMappingPolicyLevel                              Gauge32,
    cucsEquipmentDimmMappingPolicyOwner                              CucsPolicyPolicyOwner
}

cucsEquipmentDimmMappingInstanceId OBJECT-TYPE
    SYNTAX       CucsManagedObjectId
    MAX-ACCESS   not-accessible
    STATUS       current
    DESCRIPTION
        "Instance identifier of the managed object."
    ::= { cucsEquipmentDimmMappingEntry 1 }

cucsEquipmentDimmMappingDn OBJECT-TYPE
    SYNTAX       CucsManagedObjectDn
    MAX-ACCESS   read-only
    STATUS       current
    DESCRIPTION
        "Cisco UCS equipment:DimmMapping:dn managed object property"
    ::= { cucsEquipmentDimmMappingEntry 2 }

cucsEquipmentDimmMappingRn OBJECT-TYPE
    SYNTAX       SnmpAdminString
    MAX-ACCESS   read-only
    STATUS       current
    DESCRIPTION
        "Cisco UCS equipment:DimmMapping:rn managed object property"
    ::= { cucsEquipmentDimmMappingEntry 3 }

cucsEquipmentDimmMappingDescr OBJECT-TYPE
    SYNTAX       SnmpAdminString
    MAX-ACCESS   read-only
    STATUS       current
    DESCRIPTION
        "Cisco UCS equipment:DimmMapping:descr managed object property"
    ::= { cucsEquipmentDimmMappingEntry 4 }

cucsEquipmentDimmMappingIntId OBJECT-TYPE
    SYNTAX       SnmpAdminString
    MAX-ACCESS   read-only
    STATUS       current
    DESCRIPTION
        "Cisco UCS equipment:DimmMapping:intId managed object property"
    ::= { cucsEquipmentDimmMappingEntry 5 }

cucsEquipmentDimmMappingName OBJECT-TYPE
    SYNTAX       SnmpAdminString
    MAX-ACCESS   read-only
    STATUS       current
    DESCRIPTION
        "Cisco UCS equipment:DimmMapping:name managed object property"
    ::= { cucsEquipmentDimmMappingEntry 6 }

cucsEquipmentDimmMappingPolicyLevel OBJECT-TYPE
    SYNTAX       Gauge32
    MAX-ACCESS   read-only
    STATUS       current
    DESCRIPTION
        "Cisco UCS equipment:DimmMapping:policyLevel managed
        object property"
    ::= { cucsEquipmentDimmMappingEntry 7 }

cucsEquipmentDimmMappingPolicyOwner OBJECT-TYPE
    SYNTAX       CucsPolicyPolicyOwner
    MAX-ACCESS   read-only
    STATUS       current
    DESCRIPTION
        "Cisco UCS equipment:DimmMapping:policyOwner managed
        object property"
    ::= { cucsEquipmentDimmMappingEntry 8 }

cucsEquipmentDiscoveryCapTable OBJECT-TYPE
    SYNTAX           SEQUENCE OF CucsEquipmentDiscoveryCapEntry
    MAX-ACCESS       not-accessible
    STATUS           current
    DESCRIPTION
        "Cisco UCS equipment:DiscoveryCap managed object table"
    ::= { cucsEquipmentObjects 79 }

cucsEquipmentDiscoveryCapEntry OBJECT-TYPE
    SYNTAX           CucsEquipmentDiscoveryCapEntry
    MAX-ACCESS       not-accessible
    STATUS           current
    DESCRIPTION
        "Entry for the cucsEquipmentDiscoveryCapTable table."
    INDEX { cucsEquipmentDiscoveryCapInstanceId }
    ::= { cucsEquipmentDiscoveryCapTable 1 }

CucsEquipmentDiscoveryCapEntry ::= SEQUENCE {
    cucsEquipmentDiscoveryCapInstanceId                              CucsManagedObjectId,
    cucsEquipmentDiscoveryCapDn                                      CucsManagedObjectDn,
    cucsEquipmentDiscoveryCapRn                                      SnmpAdminString,
    cucsEquipmentDiscoveryCapOperPowerRequirement                    CucsEquipmentDiscoveryCapOperPowerRequirement
}

cucsEquipmentDiscoveryCapInstanceId OBJECT-TYPE
    SYNTAX       CucsManagedObjectId
    MAX-ACCESS   not-accessible
    STATUS       current
    DESCRIPTION
        "Instance identifier of the managed object."
    ::= { cucsEquipmentDiscoveryCapEntry 1 }

cucsEquipmentDiscoveryCapDn OBJECT-TYPE
    SYNTAX       CucsManagedObjectDn
    MAX-ACCESS   read-only
    STATUS       current
    DESCRIPTION
        "Cisco UCS equipment:DiscoveryCap:dn managed object property"
    ::= { cucsEquipmentDiscoveryCapEntry 2 }

cucsEquipmentDiscoveryCapRn OBJECT-TYPE
    SYNTAX       SnmpAdminString
    MAX-ACCESS   read-only
    STATUS       current
    DESCRIPTION
        "Cisco UCS equipment:DiscoveryCap:rn managed object property"
    ::= { cucsEquipmentDiscoveryCapEntry 3 }

cucsEquipmentDiscoveryCapOperPowerRequirement OBJECT-TYPE
    SYNTAX       CucsEquipmentDiscoveryCapOperPowerRequirement
    MAX-ACCESS   read-only
    STATUS       current
    DESCRIPTION
        "Cisco UCS equipment:DiscoveryCap:operPowerRequirement
        managed object property"
    ::= { cucsEquipmentDiscoveryCapEntry 4 }

cucsEquipmentDowngradeConstraintTable OBJECT-TYPE
    SYNTAX           SEQUENCE OF CucsEquipmentDowngradeConstraintEntry
    MAX-ACCESS       not-accessible
    STATUS           current
    DESCRIPTION
        "Cisco UCS equipment:DowngradeConstraint managed object table"
    ::= { cucsEquipmentObjects 117 }

cucsEquipmentDowngradeConstraintEntry OBJECT-TYPE
    SYNTAX           CucsEquipmentDowngradeConstraintEntry
    MAX-ACCESS       not-accessible
    STATUS           current
    DESCRIPTION
        "Entry for the cucsEquipmentDowngradeConstraintTable table."
    INDEX { cucsEquipmentDowngradeConstraintInstanceId }
    ::= { cucsEquipmentDowngradeConstraintTable 1 }

CucsEquipmentDowngradeConstraintEntry ::= SEQUENCE {
    cucsEquipmentDowngradeConstraintInstanceId                       CucsManagedObjectId,
    cucsEquipmentDowngradeConstraintDn                               CucsManagedObjectDn,
    cucsEquipmentDowngradeConstraintRn                               SnmpAdminString,
    cucsEquipmentDowngradeConstraintMinVer                           SnmpAdminString
}

cucsEquipmentDowngradeConstraintInstanceId OBJECT-TYPE
    SYNTAX       CucsManagedObjectId
    MAX-ACCESS   not-accessible
    STATUS       current
    DESCRIPTION
        "Instance identifier of the managed object."
    ::= { cucsEquipmentDowngradeConstraintEntry 1 }

cucsEquipmentDowngradeConstraintDn OBJECT-TYPE
    SYNTAX       CucsManagedObjectDn
    MAX-ACCESS   read-only
    STATUS       current
    DESCRIPTION
        "Cisco UCS equipment:DowngradeConstraint:dn managed
        object property"
    ::= { cucsEquipmentDowngradeConstraintEntry 2 }

cucsEquipmentDowngradeConstraintRn OBJECT-TYPE
    SYNTAX       SnmpAdminString
    MAX-ACCESS   read-only
    STATUS       current
    DESCRIPTION
        "Cisco UCS equipment:DowngradeConstraint:rn managed
        object property"
    ::= { cucsEquipmentDowngradeConstraintEntry 3 }

cucsEquipmentDowngradeConstraintMinVer OBJECT-TYPE
    SYNTAX       SnmpAdminString
    MAX-ACCESS   read-only
    STATUS       current
    DESCRIPTION
        "Cisco UCS equipment:DowngradeConstraint:minVer
        managed object property"
    ::= { cucsEquipmentDowngradeConstraintEntry 4 }

cucsEquipmentDriveSecCapTable OBJECT-TYPE
    SYNTAX           SEQUENCE OF CucsEquipmentDriveSecCapEntry
    MAX-ACCESS       not-accessible
    STATUS           current
    DESCRIPTION
        "Cisco UCS equipment:DriveSecCap managed object table"
    ::= { cucsEquipmentObjects 225 }

cucsEquipmentDriveSecCapEntry OBJECT-TYPE
    SYNTAX           CucsEquipmentDriveSecCapEntry
    MAX-ACCESS       not-accessible
    STATUS           current
    DESCRIPTION
        "Entry for the cucsEquipmentDriveSecCapTable table."
    INDEX { cucsEquipmentDriveSecCapInstanceId }
    ::= { cucsEquipmentDriveSecCapTable 1 }

CucsEquipmentDriveSecCapEntry ::= SEQUENCE {
    cucsEquipmentDriveSecCapInstanceId                               CucsManagedObjectId,
    cucsEquipmentDriveSecCapDn                                       CucsManagedObjectDn,
    cucsEquipmentDriveSecCapRn                                       SnmpAdminString,
    cucsEquipmentDriveSecCapIsSupported                              CucsEquipmentDriveSecCapIsSupported,
    cucsEquipmentDriveSecCapMinVersion                               SnmpAdminString
}

cucsEquipmentDriveSecCapInstanceId OBJECT-TYPE
    SYNTAX       CucsManagedObjectId
    MAX-ACCESS   not-accessible
    STATUS       current
    DESCRIPTION
        "Instance identifier of the managed object."
    ::= { cucsEquipmentDriveSecCapEntry 1 }

cucsEquipmentDriveSecCapDn OBJECT-TYPE
    SYNTAX       CucsManagedObjectDn
    MAX-ACCESS   read-only
    STATUS       current
    DESCRIPTION
        "Cisco UCS equipment:DriveSecCap:dn managed object property"
    ::= { cucsEquipmentDriveSecCapEntry 2 }

cucsEquipmentDriveSecCapRn OBJECT-TYPE
    SYNTAX       SnmpAdminString
    MAX-ACCESS   read-only
    STATUS       current
    DESCRIPTION
        "Cisco UCS equipment:DriveSecCap:rn managed object property"
    ::= { cucsEquipmentDriveSecCapEntry 3 }

cucsEquipmentDriveSecCapIsSupported OBJECT-TYPE
    SYNTAX       CucsEquipmentDriveSecCapIsSupported
    MAX-ACCESS   read-only
    STATUS       current
    DESCRIPTION
        "Cisco UCS equipment:DriveSecCap:isSupported managed
        object property"
    ::= { cucsEquipmentDriveSecCapEntry 4 }

cucsEquipmentDriveSecCapMinVersion OBJECT-TYPE
    SYNTAX       SnmpAdminString
    MAX-ACCESS   read-only
    STATUS       current
    DESCRIPTION
        "Cisco UCS equipment:DriveSecCap:minVersion managed
        object property"
    ::= { cucsEquipmentDriveSecCapEntry 5 }

cucsEquipmentEmbeddedStorageDefTable OBJECT-TYPE
    SYNTAX           SEQUENCE OF CucsEquipmentEmbeddedStorageDefEntry
    MAX-ACCESS       not-accessible
    STATUS           current
    DESCRIPTION
        "Cisco UCS equipment:EmbeddedStorageDef managed object table"
    ::= { cucsEquipmentObjects 207 }

cucsEquipmentEmbeddedStorageDefEntry OBJECT-TYPE
    SYNTAX           CucsEquipmentEmbeddedStorageDefEntry
    MAX-ACCESS       not-accessible
    STATUS           current
    DESCRIPTION
        "Entry for the cucsEquipmentEmbeddedStorageDefTable table."
    INDEX { cucsEquipmentEmbeddedStorageDefInstanceId }
    ::= { cucsEquipmentEmbeddedStorageDefTable 1 }

CucsEquipmentEmbeddedStorageDefEntry ::= SEQUENCE {
    cucsEquipmentEmbeddedStorageDefInstanceId                        CucsManagedObjectId,
    cucsEquipmentEmbeddedStorageDefDn                                CucsManagedObjectDn,
    cucsEquipmentEmbeddedStorageDefRn                                SnmpAdminString,
    cucsEquipmentEmbeddedStorageDefBlockSize                         Gauge32,
    cucsEquipmentEmbeddedStorageDefConnectionProtocol                CucsStorageConnectionProtocol,
    cucsEquipmentEmbeddedStorageDefDescr                             SnmpAdminString,
    cucsEquipmentEmbeddedStorageDefDeviceType                        CucsStorageTechnology,
    cucsEquipmentEmbeddedStorageDefIntId                             SnmpAdminString,
    cucsEquipmentEmbeddedStorageDefName                              SnmpAdminString,
    cucsEquipmentEmbeddedStorageDefNumberOfBlocks                    Unsigned64,
    cucsEquipmentEmbeddedStorageDefPolicyLevel                       Gauge32,
    cucsEquipmentEmbeddedStorageDefPolicyOwner                       CucsPolicyPolicyOwner,
    cucsEquipmentEmbeddedStorageDefSize                              Unsigned64
}

cucsEquipmentEmbeddedStorageDefInstanceId OBJECT-TYPE
    SYNTAX       CucsManagedObjectId
    MAX-ACCESS   not-accessible
    STATUS       current
    DESCRIPTION
        "Instance identifier of the managed object."
    ::= { cucsEquipmentEmbeddedStorageDefEntry 1 }

cucsEquipmentEmbeddedStorageDefDn OBJECT-TYPE
    SYNTAX       CucsManagedObjectDn
    MAX-ACCESS   read-only
    STATUS       current
    DESCRIPTION
        "Cisco UCS equipment:EmbeddedStorageDef:dn managed
        object property"
    ::= { cucsEquipmentEmbeddedStorageDefEntry 2 }

cucsEquipmentEmbeddedStorageDefRn OBJECT-TYPE
    SYNTAX       SnmpAdminString
    MAX-ACCESS   read-only
    STATUS       current
    DESCRIPTION
        "Cisco UCS equipment:EmbeddedStorageDef:rn managed
        object property"
    ::= { cucsEquipmentEmbeddedStorageDefEntry 3 }

cucsEquipmentEmbeddedStorageDefBlockSize OBJECT-TYPE
    SYNTAX       Gauge32
    MAX-ACCESS   read-only
    STATUS       current
    DESCRIPTION
        "Cisco UCS equipment:EmbeddedStorageDef:blockSize
        managed object property"
    ::= { cucsEquipmentEmbeddedStorageDefEntry 4 }

cucsEquipmentEmbeddedStorageDefConnectionProtocol OBJECT-TYPE
    SYNTAX       CucsStorageConnectionProtocol
    MAX-ACCESS   read-only
    STATUS       current
    DESCRIPTION
        "Cisco UCS equipment:EmbeddedStorageDef:connectionProtocol
        managed object property"
    ::= { cucsEquipmentEmbeddedStorageDefEntry 5 }

cucsEquipmentEmbeddedStorageDefDescr OBJECT-TYPE
    SYNTAX       SnmpAdminString
    MAX-ACCESS   read-only
    STATUS       current
    DESCRIPTION
        "Cisco UCS equipment:EmbeddedStorageDef:descr managed
        object property"
    ::= { cucsEquipmentEmbeddedStorageDefEntry 6 }

cucsEquipmentEmbeddedStorageDefDeviceType OBJECT-TYPE
    SYNTAX       CucsStorageTechnology
    MAX-ACCESS   read-only
    STATUS       current
    DESCRIPTION
        "Cisco UCS equipment:EmbeddedStorageDef:deviceType
        managed object property"
    ::= { cucsEquipmentEmbeddedStorageDefEntry 7 }

cucsEquipmentEmbeddedStorageDefIntId OBJECT-TYPE
    SYNTAX       SnmpAdminString
    MAX-ACCESS   read-only
    STATUS       current
    DESCRIPTION
        "Cisco UCS equipment:EmbeddedStorageDef:intId managed
        object property"
    ::= { cucsEquipmentEmbeddedStorageDefEntry 8 }

cucsEquipmentEmbeddedStorageDefName OBJECT-TYPE
    SYNTAX       SnmpAdminString
    MAX-ACCESS   read-only
    STATUS       current
    DESCRIPTION
        "Cisco UCS equipment:EmbeddedStorageDef:name managed
        object property"
    ::= { cucsEquipmentEmbeddedStorageDefEntry 9 }

cucsEquipmentEmbeddedStorageDefNumberOfBlocks OBJECT-TYPE
    SYNTAX       Unsigned64
    MAX-ACCESS   read-only
    STATUS       current
    DESCRIPTION
        "Cisco UCS equipment:EmbeddedStorageDef:numberOfBlocks
        managed object property"
    ::= { cucsEquipmentEmbeddedStorageDefEntry 10 }

cucsEquipmentEmbeddedStorageDefPolicyLevel OBJECT-TYPE
    SYNTAX       Gauge32
    MAX-ACCESS   read-only
    STATUS       current
    DESCRIPTION
        "Cisco UCS equipment:EmbeddedStorageDef:policyLevel
        managed object property"
    ::= { cucsEquipmentEmbeddedStorageDefEntry 11 }

cucsEquipmentEmbeddedStorageDefPolicyOwner OBJECT-TYPE
    SYNTAX       CucsPolicyPolicyOwner
    MAX-ACCESS   read-only
    STATUS       current
    DESCRIPTION
        "Cisco UCS equipment:EmbeddedStorageDef:policyOwner
        managed object property"
    ::= { cucsEquipmentEmbeddedStorageDefEntry 12 }

cucsEquipmentEmbeddedStorageDefSize OBJECT-TYPE
    SYNTAX       Unsigned64
    MAX-ACCESS   read-only
    STATUS       current
    DESCRIPTION
        "Cisco UCS equipment:EmbeddedStorageDef:size managed
        object property"
    ::= { cucsEquipmentEmbeddedStorageDefEntry 13 }

cucsEquipmentFanTable OBJECT-TYPE
    SYNTAX           SEQUENCE OF CucsEquipmentFanEntry
    MAX-ACCESS       not-accessible
    STATUS           current
    DESCRIPTION
        "Cisco UCS equipment:Fan managed object table"
    ::= { cucsEquipmentObjects 12 }

cucsEquipmentFanEntry OBJECT-TYPE
    SYNTAX           CucsEquipmentFanEntry
    MAX-ACCESS       not-accessible
    STATUS           current
    DESCRIPTION
        "Entry for the cucsEquipmentFanTable table."
    INDEX { cucsEquipmentFanInstanceId }
    ::= { cucsEquipmentFanTable 1 }

CucsEquipmentFanEntry ::= SEQUENCE {
    cucsEquipmentFanInstanceId                                       CucsManagedObjectId,
    cucsEquipmentFanDn                                               CucsManagedObjectDn,
    cucsEquipmentFanRn                                               SnmpAdminString,
    cucsEquipmentFanFltAggr                                          Unsigned64,
    cucsEquipmentFanId                                               CucsEquipmentFanId,
    cucsEquipmentFanIntType                                          CucsEquipmentInternalFanType,
    cucsEquipmentFanModel                                            SnmpAdminString,
    cucsEquipmentFanModule                                           CucsEquipmentFanModule,
    cucsEquipmentFanOperState                                        CucsEquipmentOperability,
    cucsEquipmentFanOperability                                      CucsEquipmentOperability,
    cucsEquipmentFanPerf                                             CucsEquipmentSensorThresholdStatus,
    cucsEquipmentFanPower                                            CucsEquipmentPowerState,
    cucsEquipmentFanPresence                                         CucsEquipmentPresence,
    cucsEquipmentFanRevision                                         SnmpAdminString,
    cucsEquipmentFanSerial                                           SnmpAdminString,
    cucsEquipmentFanThermal                                          CucsEquipmentSensorThresholdStatus,
    cucsEquipmentFanTray                                             CucsEquipmentFanTray,
    cucsEquipmentFanVendor                                           SnmpAdminString,
    cucsEquipmentFanVoltage                                          CucsEquipmentSensorThresholdStatus,
    cucsEquipmentFanOperQualifierReason                              SnmpAdminString,
    cucsEquipmentFanFanSpeedPolicyAdminState                         CucsPowerFanSpeed,
    cucsEquipmentFanFanSpeedPolicyOperState                          CucsPowerFanSpeed
}

cucsEquipmentFanInstanceId OBJECT-TYPE
    SYNTAX       CucsManagedObjectId
    MAX-ACCESS   not-accessible
    STATUS       current
    DESCRIPTION
        "Instance identifier of the managed object."
    ::= { cucsEquipmentFanEntry 1 }

cucsEquipmentFanDn OBJECT-TYPE
    SYNTAX       CucsManagedObjectDn
    MAX-ACCESS   read-only
    STATUS       current
    DESCRIPTION
        "Cisco UCS equipment:Fan:dn managed object property"
    ::= { cucsEquipmentFanEntry 2 }

cucsEquipmentFanRn OBJECT-TYPE
    SYNTAX       SnmpAdminString
    MAX-ACCESS   read-only
    STATUS       current
    DESCRIPTION
        "Cisco UCS equipment:Fan:rn managed object property"
    ::= { cucsEquipmentFanEntry 3 }

cucsEquipmentFanFltAggr OBJECT-TYPE
    SYNTAX       Unsigned64
    MAX-ACCESS   read-only
    STATUS       current
    DESCRIPTION
        "Cisco UCS equipment:Fan:fltAggr managed object property"
    ::= { cucsEquipmentFanEntry 4 }

cucsEquipmentFanId OBJECT-TYPE
    SYNTAX       CucsEquipmentFanId
    MAX-ACCESS   read-only
    STATUS       current
    DESCRIPTION
        "Cisco UCS equipment:Fan:id managed object property"
    ::= { cucsEquipmentFanEntry 5 }

cucsEquipmentFanIntType OBJECT-TYPE
    SYNTAX       CucsEquipmentInternalFanType
    MAX-ACCESS   read-only
    STATUS       current
    DESCRIPTION
        "Cisco UCS equipment:Fan:intType managed object property"
    ::= { cucsEquipmentFanEntry 6 }

cucsEquipmentFanModel OBJECT-TYPE
    SYNTAX       SnmpAdminString
    MAX-ACCESS   read-only
    STATUS       current
    DESCRIPTION
        "Cisco UCS equipment:Fan:model managed object property"
    ::= { cucsEquipmentFanEntry 7 }

cucsEquipmentFanModule OBJECT-TYPE
    SYNTAX       CucsEquipmentFanModule
    MAX-ACCESS   read-only
    STATUS       current
    DESCRIPTION
        "Cisco UCS equipment:Fan:module managed object property"
    ::= { cucsEquipmentFanEntry 8 }

cucsEquipmentFanOperState OBJECT-TYPE
    SYNTAX       CucsEquipmentOperability
    MAX-ACCESS   read-only
    STATUS       current
    DESCRIPTION
        "Cisco UCS equipment:Fan:operState managed object property"
    ::= { cucsEquipmentFanEntry 9 }

cucsEquipmentFanOperability OBJECT-TYPE
    SYNTAX       CucsEquipmentOperability
    MAX-ACCESS   read-only
    STATUS       current
    DESCRIPTION
        "Cisco UCS equipment:Fan:operability managed object property"
    ::= { cucsEquipmentFanEntry 10 }

cucsEquipmentFanPerf OBJECT-TYPE
    SYNTAX       CucsEquipmentSensorThresholdStatus
    MAX-ACCESS   read-only
    STATUS       current
    DESCRIPTION
        "Cisco UCS equipment:Fan:perf managed object property"
    ::= { cucsEquipmentFanEntry 11 }

cucsEquipmentFanPower OBJECT-TYPE
    SYNTAX       CucsEquipmentPowerState
    MAX-ACCESS   read-only
    STATUS       current
    DESCRIPTION
        "Cisco UCS equipment:Fan:power managed object property"
    ::= { cucsEquipmentFanEntry 12 }

cucsEquipmentFanPresence OBJECT-TYPE
    SYNTAX       CucsEquipmentPresence
    MAX-ACCESS   read-only
    STATUS       current
    DESCRIPTION
        "Cisco UCS equipment:Fan:presence managed object property"
    ::= { cucsEquipmentFanEntry 13 }

cucsEquipmentFanRevision OBJECT-TYPE
    SYNTAX       SnmpAdminString
    MAX-ACCESS   read-only
    STATUS       current
    DESCRIPTION
        "Cisco UCS equipment:Fan:revision managed object property"
    ::= { cucsEquipmentFanEntry 14 }

cucsEquipmentFanSerial OBJECT-TYPE
    SYNTAX       SnmpAdminString
    MAX-ACCESS   read-only
    STATUS       current
    DESCRIPTION
        "Cisco UCS equipment:Fan:serial managed object property"
    ::= { cucsEquipmentFanEntry 15 }

cucsEquipmentFanThermal OBJECT-TYPE
    SYNTAX       CucsEquipmentSensorThresholdStatus
    MAX-ACCESS   read-only
    STATUS       current
    DESCRIPTION
        "Cisco UCS equipment:Fan:thermal managed object property"
    ::= { cucsEquipmentFanEntry 16 }

cucsEquipmentFanTray OBJECT-TYPE
    SYNTAX       CucsEquipmentFanTray
    MAX-ACCESS   read-only
    STATUS       current
    DESCRIPTION
        "Cisco UCS equipment:Fan:tray managed object property"
    ::= { cucsEquipmentFanEntry 17 }

cucsEquipmentFanVendor OBJECT-TYPE
    SYNTAX       SnmpAdminString
    MAX-ACCESS   read-only
    STATUS       current
    DESCRIPTION
        "Cisco UCS equipment:Fan:vendor managed object property"
    ::= { cucsEquipmentFanEntry 18 }

cucsEquipmentFanVoltage OBJECT-TYPE
    SYNTAX       CucsEquipmentSensorThresholdStatus
    MAX-ACCESS   read-only
    STATUS       current
    DESCRIPTION
        "Cisco UCS equipment:Fan:voltage managed object property"
    ::= { cucsEquipmentFanEntry 19 }

cucsEquipmentFanOperQualifierReason OBJECT-TYPE
    SYNTAX       SnmpAdminString
    MAX-ACCESS   read-only
    STATUS       current
    DESCRIPTION
        "Cisco UCS equipment:Fan:operQualifierReason managed
        object property"
    ::= { cucsEquipmentFanEntry 20 }

cucsEquipmentFanFanSpeedPolicyAdminState OBJECT-TYPE
    SYNTAX       CucsPowerFanSpeed
    MAX-ACCESS   read-only
    STATUS       current
    DESCRIPTION
        "Cisco UCS equipment:Fan:fanSpeedPolicyAdminState
        managed object property"
    ::= { cucsEquipmentFanEntry 21 }

cucsEquipmentFanFanSpeedPolicyOperState OBJECT-TYPE
    SYNTAX       CucsPowerFanSpeed
    MAX-ACCESS   read-only
    STATUS       current
    DESCRIPTION
        "Cisco UCS equipment:Fan:fanSpeedPolicyOperState
        managed object property"
    ::= { cucsEquipmentFanEntry 22 }

cucsEquipmentFanModuleTable OBJECT-TYPE
    SYNTAX           SEQUENCE OF CucsEquipmentFanModuleEntry
    MAX-ACCESS       not-accessible
    STATUS           current
    DESCRIPTION
        "Cisco UCS equipment:FanModule managed object table"
    ::= { cucsEquipmentObjects 13 }

cucsEquipmentFanModuleEntry OBJECT-TYPE
    SYNTAX           CucsEquipmentFanModuleEntry
    MAX-ACCESS       not-accessible
    STATUS           current
    DESCRIPTION
        "Entry for the cucsEquipmentFanModuleTable table."
    INDEX { cucsEquipmentFanModuleInstanceId }
    ::= { cucsEquipmentFanModuleTable 1 }

CucsEquipmentFanModuleEntry ::= SEQUENCE {
    cucsEquipmentFanModuleInstanceId                                 CucsManagedObjectId,
    cucsEquipmentFanModuleDn                                         CucsManagedObjectDn,
    cucsEquipmentFanModuleRn                                         SnmpAdminString,
    cucsEquipmentFanModuleFltAggr                                    Unsigned64,
    cucsEquipmentFanModuleId                                         CucsEquipmentFanModuleId,
    cucsEquipmentFanModuleModel                                      SnmpAdminString,
    cucsEquipmentFanModuleOperState                                  CucsEquipmentOperability,
    cucsEquipmentFanModuleOperability                                CucsEquipmentOperability,
    cucsEquipmentFanModulePerf                                       CucsEquipmentSensorThresholdStatus,
    cucsEquipmentFanModulePower                                      CucsEquipmentPowerState,
    cucsEquipmentFanModulePresence                                   CucsEquipmentPresence,
    cucsEquipmentFanModuleRevision                                   SnmpAdminString,
    cucsEquipmentFanModuleSerial                                     SnmpAdminString,
    cucsEquipmentFanModuleThermal                                    CucsEquipmentSensorThresholdStatus,
    cucsEquipmentFanModuleTray                                       CucsEquipmentFanModuleTray,
    cucsEquipmentFanModuleVendor                                     SnmpAdminString,
    cucsEquipmentFanModuleVoltage                                    CucsEquipmentSensorThresholdStatus,
    cucsEquipmentFanModuleMfgTime                                    DateAndTime,
    cucsEquipmentFanModuleOperQualifierReason                        SnmpAdminString,
    cucsEquipmentFanModulePartNumber                                 SnmpAdminString,
    cucsEquipmentFanModuleVid                                        SnmpAdminString,
    cucsEquipmentFanModuleAssetTag                                   SnmpAdminString
}

cucsEquipmentFanModuleInstanceId OBJECT-TYPE
    SYNTAX       CucsManagedObjectId
    MAX-ACCESS   not-accessible
    STATUS       current
    DESCRIPTION
        "Instance identifier of the managed object."
    ::= { cucsEquipmentFanModuleEntry 1 }

cucsEquipmentFanModuleDn OBJECT-TYPE
    SYNTAX       CucsManagedObjectDn
    MAX-ACCESS   read-only
    STATUS       current
    DESCRIPTION
        "Cisco UCS equipment:FanModule:dn managed object property"
    ::= { cucsEquipmentFanModuleEntry 2 }

cucsEquipmentFanModuleRn OBJECT-TYPE
    SYNTAX       SnmpAdminString
    MAX-ACCESS   read-only
    STATUS       current
    DESCRIPTION
        "Cisco UCS equipment:FanModule:rn managed object property"
    ::= { cucsEquipmentFanModuleEntry 3 }

cucsEquipmentFanModuleFltAggr OBJECT-TYPE
    SYNTAX       Unsigned64
    MAX-ACCESS   read-only
    STATUS       current
    DESCRIPTION
        "Cisco UCS equipment:FanModule:fltAggr managed object property"
    ::= { cucsEquipmentFanModuleEntry 4 }

cucsEquipmentFanModuleId OBJECT-TYPE
    SYNTAX       CucsEquipmentFanModuleId
    MAX-ACCESS   read-only
    STATUS       current
    DESCRIPTION
        "Cisco UCS equipment:FanModule:id managed object property"
    ::= { cucsEquipmentFanModuleEntry 5 }

cucsEquipmentFanModuleModel OBJECT-TYPE
    SYNTAX       SnmpAdminString
    MAX-ACCESS   read-only
    STATUS       current
    DESCRIPTION
        "Cisco UCS equipment:FanModule:model managed object property"
    ::= { cucsEquipmentFanModuleEntry 6 }

cucsEquipmentFanModuleOperState OBJECT-TYPE
    SYNTAX       CucsEquipmentOperability
    MAX-ACCESS   read-only
    STATUS       current
    DESCRIPTION
        "Cisco UCS equipment:FanModule:operState managed object property"
    ::= { cucsEquipmentFanModuleEntry 7 }

cucsEquipmentFanModuleOperability OBJECT-TYPE
    SYNTAX       CucsEquipmentOperability
    MAX-ACCESS   read-only
    STATUS       current
    DESCRIPTION
        "Cisco UCS equipment:FanModule:operability managed
        object property"
    ::= { cucsEquipmentFanModuleEntry 8 }

cucsEquipmentFanModulePerf OBJECT-TYPE
    SYNTAX       CucsEquipmentSensorThresholdStatus
    MAX-ACCESS   read-only
    STATUS       current
    DESCRIPTION
        "Cisco UCS equipment:FanModule:perf managed object property"
    ::= { cucsEquipmentFanModuleEntry 9 }

cucsEquipmentFanModulePower OBJECT-TYPE
    SYNTAX       CucsEquipmentPowerState
    MAX-ACCESS   read-only
    STATUS       current
    DESCRIPTION
        "Cisco UCS equipment:FanModule:power managed object property"
    ::= { cucsEquipmentFanModuleEntry 10 }

cucsEquipmentFanModulePresence OBJECT-TYPE
    SYNTAX       CucsEquipmentPresence
    MAX-ACCESS   read-only
    STATUS       current
    DESCRIPTION
        "Cisco UCS equipment:FanModule:presence managed object property"
    ::= { cucsEquipmentFanModuleEntry 11 }

cucsEquipmentFanModuleRevision OBJECT-TYPE
    SYNTAX       SnmpAdminString
    MAX-ACCESS   read-only
    STATUS       current
    DESCRIPTION
        "Cisco UCS equipment:FanModule:revision managed object property"
    ::= { cucsEquipmentFanModuleEntry 12 }

cucsEquipmentFanModuleSerial OBJECT-TYPE
    SYNTAX       SnmpAdminString
    MAX-ACCESS   read-only
    STATUS       current
    DESCRIPTION
        "Cisco UCS equipment:FanModule:serial managed object property"
    ::= { cucsEquipmentFanModuleEntry 13 }

cucsEquipmentFanModuleThermal OBJECT-TYPE
    SYNTAX       CucsEquipmentSensorThresholdStatus
    MAX-ACCESS   read-only
    STATUS       current
    DESCRIPTION
        "Cisco UCS equipment:FanModule:thermal managed object property"
    ::= { cucsEquipmentFanModuleEntry 14 }

cucsEquipmentFanModuleTray OBJECT-TYPE
    SYNTAX       CucsEquipmentFanModuleTray
    MAX-ACCESS   read-only
    STATUS       current
    DESCRIPTION
        "Cisco UCS equipment:FanModule:tray managed object property"
    ::= { cucsEquipmentFanModuleEntry 15 }

cucsEquipmentFanModuleVendor OBJECT-TYPE
    SYNTAX       SnmpAdminString
    MAX-ACCESS   read-only
    STATUS       current
    DESCRIPTION
        "Cisco UCS equipment:FanModule:vendor managed object property"
    ::= { cucsEquipmentFanModuleEntry 16 }

cucsEquipmentFanModuleVoltage OBJECT-TYPE
    SYNTAX       CucsEquipmentSensorThresholdStatus
    MAX-ACCESS   read-only
    STATUS       current
    DESCRIPTION
        "Cisco UCS equipment:FanModule:voltage managed object property"
    ::= { cucsEquipmentFanModuleEntry 17 }

cucsEquipmentFanModuleMfgTime OBJECT-TYPE
    SYNTAX       DateAndTime
    MAX-ACCESS   read-only
    STATUS       current
    DESCRIPTION
        "Cisco UCS equipment:FanModule:mfgTime managed object property"
    ::= { cucsEquipmentFanModuleEntry 18 }

cucsEquipmentFanModuleOperQualifierReason OBJECT-TYPE
    SYNTAX       SnmpAdminString
    MAX-ACCESS   read-only
    STATUS       current
    DESCRIPTION
        "Cisco UCS equipment:FanModule:operQualifierReason
        managed object property"
    ::= { cucsEquipmentFanModuleEntry 19 }

cucsEquipmentFanModulePartNumber OBJECT-TYPE
    SYNTAX       SnmpAdminString
    MAX-ACCESS   read-only
    STATUS       current
    DESCRIPTION
        "Cisco UCS equipment:FanModule:partNumber managed object property"
    ::= { cucsEquipmentFanModuleEntry 20 }

cucsEquipmentFanModuleVid OBJECT-TYPE
    SYNTAX       SnmpAdminString
    MAX-ACCESS   read-only
    STATUS       current
    DESCRIPTION
        "Cisco UCS equipment:FanModule:vid managed object property"
    ::= { cucsEquipmentFanModuleEntry 21 }

cucsEquipmentFanModuleAssetTag OBJECT-TYPE
    SYNTAX       SnmpAdminString
    MAX-ACCESS   read-only
    STATUS       current
    DESCRIPTION
        "Cisco UCS equipment:FanModule:assetTag managed object property"
    ::= { cucsEquipmentFanModuleEntry 22 }

cucsEquipmentFanModuleCapProviderTable OBJECT-TYPE
    SYNTAX           SEQUENCE OF CucsEquipmentFanModuleCapProviderEntry
    MAX-ACCESS       not-accessible
    STATUS           current
    DESCRIPTION
        "Cisco UCS equipment:FanModuleCapProvider managed object table"
    ::= { cucsEquipmentObjects 14 }

cucsEquipmentFanModuleCapProviderEntry OBJECT-TYPE
    SYNTAX           CucsEquipmentFanModuleCapProviderEntry
    MAX-ACCESS       not-accessible
    STATUS           current
    DESCRIPTION
        "Entry for the cucsEquipmentFanModuleCapProviderTable table."
    INDEX { cucsEquipmentFanModuleCapProviderInstanceId }
    ::= { cucsEquipmentFanModuleCapProviderTable 1 }

CucsEquipmentFanModuleCapProviderEntry ::= SEQUENCE {
    cucsEquipmentFanModuleCapProviderInstanceId                      CucsManagedObjectId,
    cucsEquipmentFanModuleCapProviderDn                              CucsManagedObjectDn,
    cucsEquipmentFanModuleCapProviderRn                              SnmpAdminString,
    cucsEquipmentFanModuleCapProviderDeprecated                      TruthValue,
    cucsEquipmentFanModuleCapProviderGencount                        Gauge32,
    cucsEquipmentFanModuleCapProviderMgmtPlaneVer                    SnmpAdminString,
    cucsEquipmentFanModuleCapProviderModel                           SnmpAdminString,
    cucsEquipmentFanModuleCapProviderRevision                        SnmpAdminString,
    cucsEquipmentFanModuleCapProviderVendor                          SnmpAdminString,
    cucsEquipmentFanModuleCapProviderPromCardType                    Gauge32,
    cucsEquipmentFanModuleCapProviderDeleted                         TruthValue,
    cucsEquipmentFanModuleCapProviderElementLoadFailures             Gauge32,
    cucsEquipmentFanModuleCapProviderElementsLoaded                  Gauge32,
    cucsEquipmentFanModuleCapProviderLoadErrors                      Gauge32,
    cucsEquipmentFanModuleCapProviderLoadWarnings                    Gauge32
}

cucsEquipmentFanModuleCapProviderInstanceId OBJECT-TYPE
    SYNTAX       CucsManagedObjectId
    MAX-ACCESS   not-accessible
    STATUS       current
    DESCRIPTION
        "Instance identifier of the managed object."
    ::= { cucsEquipmentFanModuleCapProviderEntry 1 }

cucsEquipmentFanModuleCapProviderDn OBJECT-TYPE
    SYNTAX       CucsManagedObjectDn
    MAX-ACCESS   read-only
    STATUS       current
    DESCRIPTION
        "Cisco UCS equipment:FanModuleCapProvider:dn managed
        object property"
    ::= { cucsEquipmentFanModuleCapProviderEntry 2 }

cucsEquipmentFanModuleCapProviderRn OBJECT-TYPE
    SYNTAX       SnmpAdminString
    MAX-ACCESS   read-only
    STATUS       current
    DESCRIPTION
        "Cisco UCS equipment:FanModuleCapProvider:rn managed
        object property"
    ::= { cucsEquipmentFanModuleCapProviderEntry 3 }

cucsEquipmentFanModuleCapProviderDeprecated OBJECT-TYPE
    SYNTAX       TruthValue
    MAX-ACCESS   read-only
    STATUS       current
    DESCRIPTION
        "Cisco UCS equipment:FanModuleCapProvider:deprecated
        managed object property"
    ::= { cucsEquipmentFanModuleCapProviderEntry 4 }

cucsEquipmentFanModuleCapProviderGencount OBJECT-TYPE
    SYNTAX       Gauge32
    MAX-ACCESS   read-only
    STATUS       current
    DESCRIPTION
        "Cisco UCS equipment:FanModuleCapProvider:gencount
        managed object property"
    ::= { cucsEquipmentFanModuleCapProviderEntry 5 }

cucsEquipmentFanModuleCapProviderMgmtPlaneVer OBJECT-TYPE
    SYNTAX       SnmpAdminString
    MAX-ACCESS   read-only
    STATUS       current
    DESCRIPTION
        "Cisco UCS equipment:FanModuleCapProvider:mgmtPlaneVer
        managed object property"
    ::= { cucsEquipmentFanModuleCapProviderEntry 6 }

cucsEquipmentFanModuleCapProviderModel OBJECT-TYPE
    SYNTAX       SnmpAdminString
    MAX-ACCESS   read-only
    STATUS       current
    DESCRIPTION
        "Cisco UCS equipment:FanModuleCapProvider:model
        managed object property"
    ::= { cucsEquipmentFanModuleCapProviderEntry 7 }

cucsEquipmentFanModuleCapProviderRevision OBJECT-TYPE
    SYNTAX       SnmpAdminString
    MAX-ACCESS   read-only
    STATUS       current
    DESCRIPTION
        "Cisco UCS equipment:FanModuleCapProvider:revision
        managed object property"
    ::= { cucsEquipmentFanModuleCapProviderEntry 8 }

cucsEquipmentFanModuleCapProviderVendor OBJECT-TYPE
    SYNTAX       SnmpAdminString
    MAX-ACCESS   read-only
    STATUS       current
    DESCRIPTION
        "Cisco UCS equipment:FanModuleCapProvider:vendor
        managed object property"
    ::= { cucsEquipmentFanModuleCapProviderEntry 9 }

cucsEquipmentFanModuleCapProviderPromCardType OBJECT-TYPE
    SYNTAX       Gauge32
    MAX-ACCESS   read-only
    STATUS       current
    DESCRIPTION
        "Cisco UCS equipment:FanModuleCapProvider:promCardType
        managed object property"
    ::= { cucsEquipmentFanModuleCapProviderEntry 10 }

cucsEquipmentFanModuleCapProviderDeleted OBJECT-TYPE
    SYNTAX       TruthValue
    MAX-ACCESS   read-only
    STATUS       current
    DESCRIPTION
        "Cisco UCS equipment:FanModuleCapProvider:deleted
        managed object property"
    ::= { cucsEquipmentFanModuleCapProviderEntry 11 }

cucsEquipmentFanModuleCapProviderElementLoadFailures OBJECT-TYPE
    SYNTAX       Gauge32
    MAX-ACCESS   read-only
    STATUS       current
    DESCRIPTION
        "Cisco UCS equipment:FanModuleCapProvider:elementLoadFailures
        managed object property"
    ::= { cucsEquipmentFanModuleCapProviderEntry 12 }

cucsEquipmentFanModuleCapProviderElementsLoaded OBJECT-TYPE
    SYNTAX       Gauge32
    MAX-ACCESS   read-only
    STATUS       current
    DESCRIPTION
        "Cisco UCS equipment:FanModuleCapProvider:elementsLoaded
        managed object property"
    ::= { cucsEquipmentFanModuleCapProviderEntry 13 }

cucsEquipmentFanModuleCapProviderLoadErrors OBJECT-TYPE
    SYNTAX       Gauge32
    MAX-ACCESS   read-only
    STATUS       current
    DESCRIPTION
        "Cisco UCS equipment:FanModuleCapProvider:loadErrors
        managed object property"
    ::= { cucsEquipmentFanModuleCapProviderEntry 14 }

cucsEquipmentFanModuleCapProviderLoadWarnings OBJECT-TYPE
    SYNTAX       Gauge32
    MAX-ACCESS   read-only
    STATUS       current
    DESCRIPTION
        "Cisco UCS equipment:FanModuleCapProvider:loadWarnings
        managed object property"
    ::= { cucsEquipmentFanModuleCapProviderEntry 15 }

cucsEquipmentFanModuleDefTable OBJECT-TYPE
    SYNTAX           SEQUENCE OF CucsEquipmentFanModuleDefEntry
    MAX-ACCESS       not-accessible
    STATUS           current
    DESCRIPTION
        "Cisco UCS equipment:FanModuleDef managed object table"
    ::= { cucsEquipmentObjects 84 }

cucsEquipmentFanModuleDefEntry OBJECT-TYPE
    SYNTAX           CucsEquipmentFanModuleDefEntry
    MAX-ACCESS       not-accessible
    STATUS           current
    DESCRIPTION
        "Entry for the cucsEquipmentFanModuleDefTable table."
    INDEX { cucsEquipmentFanModuleDefInstanceId }
    ::= { cucsEquipmentFanModuleDefTable 1 }

CucsEquipmentFanModuleDefEntry ::= SEQUENCE {
    cucsEquipmentFanModuleDefInstanceId                              CucsManagedObjectId,
    cucsEquipmentFanModuleDefDn                                      CucsManagedObjectDn,
    cucsEquipmentFanModuleDefRn                                      SnmpAdminString,
    cucsEquipmentFanModuleDefDescr                                   SnmpAdminString,
    cucsEquipmentFanModuleDefFanCapacity                             Gauge32,
    cucsEquipmentFanModuleDefIntId                                   SnmpAdminString,
    cucsEquipmentFanModuleDefName                                    SnmpAdminString,
    cucsEquipmentFanModuleDefPolicyLevel                             Gauge32,
    cucsEquipmentFanModuleDefPolicyOwner                             CucsPolicyPolicyOwner
}

cucsEquipmentFanModuleDefInstanceId OBJECT-TYPE
    SYNTAX       CucsManagedObjectId
    MAX-ACCESS   not-accessible
    STATUS       current
    DESCRIPTION
        "Instance identifier of the managed object."
    ::= { cucsEquipmentFanModuleDefEntry 1 }

cucsEquipmentFanModuleDefDn OBJECT-TYPE
    SYNTAX       CucsManagedObjectDn
    MAX-ACCESS   read-only
    STATUS       current
    DESCRIPTION
        "Cisco UCS equipment:FanModuleDef:dn managed object property"
    ::= { cucsEquipmentFanModuleDefEntry 2 }

cucsEquipmentFanModuleDefRn OBJECT-TYPE
    SYNTAX       SnmpAdminString
    MAX-ACCESS   read-only
    STATUS       current
    DESCRIPTION
        "Cisco UCS equipment:FanModuleDef:rn managed object property"
    ::= { cucsEquipmentFanModuleDefEntry 3 }

cucsEquipmentFanModuleDefDescr OBJECT-TYPE
    SYNTAX       SnmpAdminString
    MAX-ACCESS   read-only
    STATUS       current
    DESCRIPTION
        "Cisco UCS equipment:FanModuleDef:descr managed object property"
    ::= { cucsEquipmentFanModuleDefEntry 4 }

cucsEquipmentFanModuleDefFanCapacity OBJECT-TYPE
    SYNTAX       Gauge32
    MAX-ACCESS   read-only
    STATUS       current
    DESCRIPTION
        "Cisco UCS equipment:FanModuleDef:fanCapacity managed
        object property"
    ::= { cucsEquipmentFanModuleDefEntry 5 }

cucsEquipmentFanModuleDefIntId OBJECT-TYPE
    SYNTAX       SnmpAdminString
    MAX-ACCESS   read-only
    STATUS       current
    DESCRIPTION
        "Cisco UCS equipment:FanModuleDef:intId managed object property"
    ::= { cucsEquipmentFanModuleDefEntry 6 }

cucsEquipmentFanModuleDefName OBJECT-TYPE
    SYNTAX       SnmpAdminString
    MAX-ACCESS   read-only
    STATUS       current
    DESCRIPTION
        "Cisco UCS equipment:FanModuleDef:name managed object property"
    ::= { cucsEquipmentFanModuleDefEntry 7 }

cucsEquipmentFanModuleDefPolicyLevel OBJECT-TYPE
    SYNTAX       Gauge32
    MAX-ACCESS   read-only
    STATUS       current
    DESCRIPTION
        "Cisco UCS equipment:FanModuleDef:policyLevel managed
        object property"
    ::= { cucsEquipmentFanModuleDefEntry 8 }

cucsEquipmentFanModuleDefPolicyOwner OBJECT-TYPE
    SYNTAX       CucsPolicyPolicyOwner
    MAX-ACCESS   read-only
    STATUS       current
    DESCRIPTION
        "Cisco UCS equipment:FanModuleDef:policyOwner managed
        object property"
    ::= { cucsEquipmentFanModuleDefEntry 9 }

cucsEquipmentFanModuleStatsTable OBJECT-TYPE
    SYNTAX           SEQUENCE OF CucsEquipmentFanModuleStatsEntry
    MAX-ACCESS       not-accessible
    STATUS           current
    DESCRIPTION
        "Cisco UCS equipment:FanModuleStats managed object table"
    ::= { cucsEquipmentObjects 15 }

cucsEquipmentFanModuleStatsEntry OBJECT-TYPE
    SYNTAX           CucsEquipmentFanModuleStatsEntry
    MAX-ACCESS       not-accessible
    STATUS           current
    DESCRIPTION
        "Entry for the cucsEquipmentFanModuleStatsTable table."
    INDEX { cucsEquipmentFanModuleStatsInstanceId }
    ::= { cucsEquipmentFanModuleStatsTable 1 }

CucsEquipmentFanModuleStatsEntry ::= SEQUENCE {
    cucsEquipmentFanModuleStatsInstanceId                            CucsManagedObjectId,
    cucsEquipmentFanModuleStatsDn                                    CucsManagedObjectDn,
    cucsEquipmentFanModuleStatsRn                                    SnmpAdminString,
    cucsEquipmentFanModuleStatsAmbientTemp                           INTEGER,
    cucsEquipmentFanModuleStatsAmbientTempAvg                        INTEGER,
    cucsEquipmentFanModuleStatsAmbientTempMax                        INTEGER,
    cucsEquipmentFanModuleStatsAmbientTempMin                        INTEGER,
    cucsEquipmentFanModuleStatsIntervals                             Gauge32,
    cucsEquipmentFanModuleStatsSuspect                               TruthValue,
    cucsEquipmentFanModuleStatsThresholded                           CucsEquipmentFanModuleStatsThresholded,
    cucsEquipmentFanModuleStatsTimeCollected                         DateAndTime,
    cucsEquipmentFanModuleStatsUpdate                                Gauge32,
    cucsEquipmentFanModuleStatsFanModuleI2CErrors                    Unsigned64,
    cucsEquipmentFanModuleStatsFanModuleI2CErrorsAvg                 Unsigned64,
    cucsEquipmentFanModuleStatsFanModuleI2CErrorsMax                 Unsigned64,
    cucsEquipmentFanModuleStatsFanModuleI2CErrorsMin                 Unsigned64
}

cucsEquipmentFanModuleStatsInstanceId OBJECT-TYPE
    SYNTAX       CucsManagedObjectId
    MAX-ACCESS   not-accessible
    STATUS       current
    DESCRIPTION
        "Instance identifier of the managed object."
    ::= { cucsEquipmentFanModuleStatsEntry 1 }

cucsEquipmentFanModuleStatsDn OBJECT-TYPE
    SYNTAX       CucsManagedObjectDn
    MAX-ACCESS   read-only
    STATUS       current
    DESCRIPTION
        "Cisco UCS equipment:FanModuleStats:dn managed object property"
    ::= { cucsEquipmentFanModuleStatsEntry 2 }

cucsEquipmentFanModuleStatsRn OBJECT-TYPE
    SYNTAX       SnmpAdminString
    MAX-ACCESS   read-only
    STATUS       current
    DESCRIPTION
        "Cisco UCS equipment:FanModuleStats:rn managed object property"
    ::= { cucsEquipmentFanModuleStatsEntry 3 }

cucsEquipmentFanModuleStatsAmbientTemp OBJECT-TYPE
    SYNTAX       INTEGER
    MAX-ACCESS   read-only
    STATUS       current
    DESCRIPTION
        "Cisco UCS equipment:FanModuleStats:ambientTemp
        managed object property"
    ::= { cucsEquipmentFanModuleStatsEntry 4 }

cucsEquipmentFanModuleStatsAmbientTempAvg OBJECT-TYPE
    SYNTAX       INTEGER
    MAX-ACCESS   read-only
    STATUS       current
    DESCRIPTION
        "Cisco UCS equipment:FanModuleStats:ambientTempAvg
        managed object property"
    ::= { cucsEquipmentFanModuleStatsEntry 5 }

cucsEquipmentFanModuleStatsAmbientTempMax OBJECT-TYPE
    SYNTAX       INTEGER
    MAX-ACCESS   read-only
    STATUS       current
    DESCRIPTION
        "Cisco UCS equipment:FanModuleStats:ambientTempMax
        managed object property"
    ::= { cucsEquipmentFanModuleStatsEntry 6 }

cucsEquipmentFanModuleStatsAmbientTempMin OBJECT-TYPE
    SYNTAX       INTEGER
    MAX-ACCESS   read-only
    STATUS       current
    DESCRIPTION
        "Cisco UCS equipment:FanModuleStats:ambientTempMin
        managed object property"
    ::= { cucsEquipmentFanModuleStatsEntry 7 }

cucsEquipmentFanModuleStatsIntervals OBJECT-TYPE
    SYNTAX       Gauge32
    MAX-ACCESS   read-only
    STATUS       current
    DESCRIPTION
        "Cisco UCS equipment:FanModuleStats:intervals managed
        object property"
    ::= { cucsEquipmentFanModuleStatsEntry 8 }

cucsEquipmentFanModuleStatsSuspect OBJECT-TYPE
    SYNTAX       TruthValue
    MAX-ACCESS   read-only
    STATUS       current
    DESCRIPTION
        "Cisco UCS equipment:FanModuleStats:suspect managed
        object property"
    ::= { cucsEquipmentFanModuleStatsEntry 9 }

cucsEquipmentFanModuleStatsThresholded OBJECT-TYPE
    SYNTAX       CucsEquipmentFanModuleStatsThresholded
    MAX-ACCESS   read-only
    STATUS       current
    DESCRIPTION
        "Cisco UCS equipment:FanModuleStats:thresholded
        managed object property"
    ::= { cucsEquipmentFanModuleStatsEntry 10 }

cucsEquipmentFanModuleStatsTimeCollected OBJECT-TYPE
    SYNTAX       DateAndTime
    MAX-ACCESS   read-only
    STATUS       current
    DESCRIPTION
        "Cisco UCS equipment:FanModuleStats:timeCollected
        managed object property"
    ::= { cucsEquipmentFanModuleStatsEntry 11 }

cucsEquipmentFanModuleStatsUpdate OBJECT-TYPE
    SYNTAX       Gauge32
    MAX-ACCESS   read-only
    STATUS       current
    DESCRIPTION
        "Cisco UCS equipment:FanModuleStats:update managed
        object property"
    ::= { cucsEquipmentFanModuleStatsEntry 12 }

cucsEquipmentFanModuleStatsFanModuleI2CErrors OBJECT-TYPE
    SYNTAX       Unsigned64
    MAX-ACCESS   read-only
    STATUS       current
    DESCRIPTION
        "Cisco UCS equipment:FanModuleStats:FanModuleI2CErrors
        managed object property"
    ::= { cucsEquipmentFanModuleStatsEntry 15 }

cucsEquipmentFanModuleStatsFanModuleI2CErrorsAvg OBJECT-TYPE
    SYNTAX       Unsigned64
    MAX-ACCESS   read-only
    STATUS       current
    DESCRIPTION
        "Cisco UCS equipment:FanModuleStats:FanModuleI2CErrorsAvg
        managed object property"
    ::= { cucsEquipmentFanModuleStatsEntry 16 }

cucsEquipmentFanModuleStatsFanModuleI2CErrorsMax OBJECT-TYPE
    SYNTAX       Unsigned64
    MAX-ACCESS   read-only
    STATUS       current
    DESCRIPTION
        "Cisco UCS equipment:FanModuleStats:FanModuleI2CErrorsMax
        managed object property"
    ::= { cucsEquipmentFanModuleStatsEntry 17 }

cucsEquipmentFanModuleStatsFanModuleI2CErrorsMin OBJECT-TYPE
    SYNTAX       Unsigned64
    MAX-ACCESS   read-only
    STATUS       current
    DESCRIPTION
        "Cisco UCS equipment:FanModuleStats:FanModuleI2CErrorsMin
        managed object property"
    ::= { cucsEquipmentFanModuleStatsEntry 18 }

cucsEquipmentFanModuleStatsHistTable OBJECT-TYPE
    SYNTAX           SEQUENCE OF CucsEquipmentFanModuleStatsHistEntry
    MAX-ACCESS       not-accessible
    STATUS           current
    DESCRIPTION
        "Cisco UCS equipment:FanModuleStatsHist managed object table"
    ::= { cucsEquipmentObjects 16 }

cucsEquipmentFanModuleStatsHistEntry OBJECT-TYPE
    SYNTAX           CucsEquipmentFanModuleStatsHistEntry
    MAX-ACCESS       not-accessible
    STATUS           current
    DESCRIPTION
        "Entry for the cucsEquipmentFanModuleStatsHistTable table."
    INDEX { cucsEquipmentFanModuleStatsHistInstanceId }
    ::= { cucsEquipmentFanModuleStatsHistTable 1 }

CucsEquipmentFanModuleStatsHistEntry ::= SEQUENCE {
    cucsEquipmentFanModuleStatsHistInstanceId                        CucsManagedObjectId,
    cucsEquipmentFanModuleStatsHistDn                                CucsManagedObjectDn,
    cucsEquipmentFanModuleStatsHistRn                                SnmpAdminString,
    cucsEquipmentFanModuleStatsHistAmbientTemp                       INTEGER,
    cucsEquipmentFanModuleStatsHistAmbientTempAvg                    INTEGER,
    cucsEquipmentFanModuleStatsHistAmbientTempMax                    INTEGER,
    cucsEquipmentFanModuleStatsHistAmbientTempMin                    INTEGER,
    cucsEquipmentFanModuleStatsHistId                                Unsigned64,
    cucsEquipmentFanModuleStatsHistMostRecent                        TruthValue,
    cucsEquipmentFanModuleStatsHistSuspect                           TruthValue,
    cucsEquipmentFanModuleStatsHistThresholded                       CucsEquipmentFanModuleStatsHistThresholded,
    cucsEquipmentFanModuleStatsHistTimeCollected                     DateAndTime,
    cucsEquipmentFanModuleStatsHistFanModuleI2CErrors                Unsigned64,
    cucsEquipmentFanModuleStatsHistFanModuleI2CErrorsAvg             Unsigned64,
    cucsEquipmentFanModuleStatsHistFanModuleI2CErrorsMax             Unsigned64,
    cucsEquipmentFanModuleStatsHistFanModuleI2CErrorsMin             Unsigned64
}

cucsEquipmentFanModuleStatsHistInstanceId OBJECT-TYPE
    SYNTAX       CucsManagedObjectId
    MAX-ACCESS   not-accessible
    STATUS       current
    DESCRIPTION
        "Instance identifier of the managed object."
    ::= { cucsEquipmentFanModuleStatsHistEntry 1 }

cucsEquipmentFanModuleStatsHistDn OBJECT-TYPE
    SYNTAX       CucsManagedObjectDn
    MAX-ACCESS   read-only
    STATUS       current
    DESCRIPTION
        "Cisco UCS equipment:FanModuleStatsHist:dn managed
        object property"
    ::= { cucsEquipmentFanModuleStatsHistEntry 2 }

cucsEquipmentFanModuleStatsHistRn OBJECT-TYPE
    SYNTAX       SnmpAdminString
    MAX-ACCESS   read-only
    STATUS       current
    DESCRIPTION
        "Cisco UCS equipment:FanModuleStatsHist:rn managed
        object property"
    ::= { cucsEquipmentFanModuleStatsHistEntry 3 }

cucsEquipmentFanModuleStatsHistAmbientTemp OBJECT-TYPE
    SYNTAX       INTEGER
    MAX-ACCESS   read-only
    STATUS       current
    DESCRIPTION
        "Cisco UCS equipment:FanModuleStatsHist:ambientTemp
        managed object property"
    ::= { cucsEquipmentFanModuleStatsHistEntry 4 }

cucsEquipmentFanModuleStatsHistAmbientTempAvg OBJECT-TYPE
    SYNTAX       INTEGER
    MAX-ACCESS   read-only
    STATUS       current
    DESCRIPTION
        "Cisco UCS equipment:FanModuleStatsHist:ambientTempAvg
        managed object property"
    ::= { cucsEquipmentFanModuleStatsHistEntry 5 }

cucsEquipmentFanModuleStatsHistAmbientTempMax OBJECT-TYPE
    SYNTAX       INTEGER
    MAX-ACCESS   read-only
    STATUS       current
    DESCRIPTION
        "Cisco UCS equipment:FanModuleStatsHist:ambientTempMax
        managed object property"
    ::= { cucsEquipmentFanModuleStatsHistEntry 6 }

cucsEquipmentFanModuleStatsHistAmbientTempMin OBJECT-TYPE
    SYNTAX       INTEGER
    MAX-ACCESS   read-only
    STATUS       current
    DESCRIPTION
        "Cisco UCS equipment:FanModuleStatsHist:ambientTempMin
        managed object property"
    ::= { cucsEquipmentFanModuleStatsHistEntry 7 }

cucsEquipmentFanModuleStatsHistId OBJECT-TYPE
    SYNTAX       Unsigned64
    MAX-ACCESS   read-only
    STATUS       current
    DESCRIPTION
        "Cisco UCS equipment:FanModuleStatsHist:id managed
        object property"
    ::= { cucsEquipmentFanModuleStatsHistEntry 8 }

cucsEquipmentFanModuleStatsHistMostRecent OBJECT-TYPE
    SYNTAX       TruthValue
    MAX-ACCESS   read-only
    STATUS       current
    DESCRIPTION
        "Cisco UCS equipment:FanModuleStatsHist:mostRecent
        managed object property"
    ::= { cucsEquipmentFanModuleStatsHistEntry 9 }

cucsEquipmentFanModuleStatsHistSuspect OBJECT-TYPE
    SYNTAX       TruthValue
    MAX-ACCESS   read-only
    STATUS       current
    DESCRIPTION
        "Cisco UCS equipment:FanModuleStatsHist:suspect
        managed object property"
    ::= { cucsEquipmentFanModuleStatsHistEntry 10 }

cucsEquipmentFanModuleStatsHistThresholded OBJECT-TYPE
    SYNTAX       CucsEquipmentFanModuleStatsHistThresholded
    MAX-ACCESS   read-only
    STATUS       current
    DESCRIPTION
        "Cisco UCS equipment:FanModuleStatsHist:thresholded
        managed object property"
    ::= { cucsEquipmentFanModuleStatsHistEntry 11 }

cucsEquipmentFanModuleStatsHistTimeCollected OBJECT-TYPE
    SYNTAX       DateAndTime
    MAX-ACCESS   read-only
    STATUS       current
    DESCRIPTION
        "Cisco UCS equipment:FanModuleStatsHist:timeCollected
        managed object property"
    ::= { cucsEquipmentFanModuleStatsHistEntry 12 }

cucsEquipmentFanModuleStatsHistFanModuleI2CErrors OBJECT-TYPE
    SYNTAX       Unsigned64
    MAX-ACCESS   read-only
    STATUS       current
    DESCRIPTION
        "Cisco UCS equipment:FanModuleStatsHist:FanModuleI2CErrors
        managed object property"
    ::= { cucsEquipmentFanModuleStatsHistEntry 13 }

cucsEquipmentFanModuleStatsHistFanModuleI2CErrorsAvg OBJECT-TYPE
    SYNTAX       Unsigned64
    MAX-ACCESS   read-only
    STATUS       current
    DESCRIPTION
        "Cisco UCS equipment:FanModuleStatsHist:FanModuleI2CErrorsAvg
        managed object property"
    ::= { cucsEquipmentFanModuleStatsHistEntry 14 }

cucsEquipmentFanModuleStatsHistFanModuleI2CErrorsMax OBJECT-TYPE
    SYNTAX       Unsigned64
    MAX-ACCESS   read-only
    STATUS       current
    DESCRIPTION
        "Cisco UCS equipment:FanModuleStatsHist:FanModuleI2CErrorsMax
        managed object property"
    ::= { cucsEquipmentFanModuleStatsHistEntry 15 }

cucsEquipmentFanModuleStatsHistFanModuleI2CErrorsMin OBJECT-TYPE
    SYNTAX       Unsigned64
    MAX-ACCESS   read-only
    STATUS       current
    DESCRIPTION
        "Cisco UCS equipment:FanModuleStatsHist:FanModuleI2CErrorsMin
        managed object property"
    ::= { cucsEquipmentFanModuleStatsHistEntry 16 }

cucsEquipmentFanStatsTable OBJECT-TYPE
    SYNTAX           SEQUENCE OF CucsEquipmentFanStatsEntry
    MAX-ACCESS       not-accessible
    STATUS           current
    DESCRIPTION
        "Cisco UCS equipment:FanStats managed object table"
    ::= { cucsEquipmentObjects 17 }

cucsEquipmentFanStatsEntry OBJECT-TYPE
    SYNTAX           CucsEquipmentFanStatsEntry
    MAX-ACCESS       not-accessible
    STATUS           current
    DESCRIPTION
        "Entry for the cucsEquipmentFanStatsTable table."
    INDEX { cucsEquipmentFanStatsInstanceId }
    ::= { cucsEquipmentFanStatsTable 1 }

CucsEquipmentFanStatsEntry ::= SEQUENCE {
    cucsEquipmentFanStatsInstanceId                                  CucsManagedObjectId,
    cucsEquipmentFanStatsDn                                          CucsManagedObjectDn,
    cucsEquipmentFanStatsRn                                          SnmpAdminString,
    cucsEquipmentFanStatsIntervals                                   Gauge32,
    cucsEquipmentFanStatsSpeed                                       Gauge32,
    cucsEquipmentFanStatsSpeedAvg                                    Gauge32,
    cucsEquipmentFanStatsSpeedMax                                    Gauge32,
    cucsEquipmentFanStatsSpeedMin                                    Gauge32,
    cucsEquipmentFanStatsSuspect                                     TruthValue,
    cucsEquipmentFanStatsThresholded                                 CucsEquipmentFanStatsThresholded,
    cucsEquipmentFanStatsTimeCollected                               DateAndTime,
    cucsEquipmentFanStatsUpdate                                      Gauge32
}

cucsEquipmentFanStatsInstanceId OBJECT-TYPE
    SYNTAX       CucsManagedObjectId
    MAX-ACCESS   not-accessible
    STATUS       current
    DESCRIPTION
        "Instance identifier of the managed object."
    ::= { cucsEquipmentFanStatsEntry 1 }

cucsEquipmentFanStatsDn OBJECT-TYPE
    SYNTAX       CucsManagedObjectDn
    MAX-ACCESS   read-only
    STATUS       current
    DESCRIPTION
        "Cisco UCS equipment:FanStats:dn managed object property"
    ::= { cucsEquipmentFanStatsEntry 2 }

cucsEquipmentFanStatsRn OBJECT-TYPE
    SYNTAX       SnmpAdminString
    MAX-ACCESS   read-only
    STATUS       current
    DESCRIPTION
        "Cisco UCS equipment:FanStats:rn managed object property"
    ::= { cucsEquipmentFanStatsEntry 3 }

cucsEquipmentFanStatsIntervals OBJECT-TYPE
    SYNTAX       Gauge32
    MAX-ACCESS   read-only
    STATUS       current
    DESCRIPTION
        "Cisco UCS equipment:FanStats:intervals managed object property"
    ::= { cucsEquipmentFanStatsEntry 4 }

cucsEquipmentFanStatsSpeed OBJECT-TYPE
    SYNTAX       Gauge32
    MAX-ACCESS   read-only
    STATUS       current
    DESCRIPTION
        "Cisco UCS equipment:FanStats:speed managed object property"
    ::= { cucsEquipmentFanStatsEntry 5 }

cucsEquipmentFanStatsSpeedAvg OBJECT-TYPE
    SYNTAX       Gauge32
    MAX-ACCESS   read-only
    STATUS       current
    DESCRIPTION
        "Cisco UCS equipment:FanStats:speedAvg managed object property"
    ::= { cucsEquipmentFanStatsEntry 6 }

cucsEquipmentFanStatsSpeedMax OBJECT-TYPE
    SYNTAX       Gauge32
    MAX-ACCESS   read-only
    STATUS       current
    DESCRIPTION
        "Cisco UCS equipment:FanStats:speedMax managed object property"
    ::= { cucsEquipmentFanStatsEntry 7 }

cucsEquipmentFanStatsSpeedMin OBJECT-TYPE
    SYNTAX       Gauge32
    MAX-ACCESS   read-only
    STATUS       current
    DESCRIPTION
        "Cisco UCS equipment:FanStats:speedMin managed object property"
    ::= { cucsEquipmentFanStatsEntry 8 }

cucsEquipmentFanStatsSuspect OBJECT-TYPE
    SYNTAX       TruthValue
    MAX-ACCESS   read-only
    STATUS       current
    DESCRIPTION
        "Cisco UCS equipment:FanStats:suspect managed object property"
    ::= { cucsEquipmentFanStatsEntry 9 }

cucsEquipmentFanStatsThresholded OBJECT-TYPE
    SYNTAX       CucsEquipmentFanStatsThresholded
    MAX-ACCESS   read-only
    STATUS       current
    DESCRIPTION
        "Cisco UCS equipment:FanStats:thresholded managed object property"
    ::= { cucsEquipmentFanStatsEntry 10 }

cucsEquipmentFanStatsTimeCollected OBJECT-TYPE
    SYNTAX       DateAndTime
    MAX-ACCESS   read-only
    STATUS       current
    DESCRIPTION
        "Cisco UCS equipment:FanStats:timeCollected managed
        object property"
    ::= { cucsEquipmentFanStatsEntry 11 }

cucsEquipmentFanStatsUpdate OBJECT-TYPE
    SYNTAX       Gauge32
    MAX-ACCESS   read-only
    STATUS       current
    DESCRIPTION
        "Cisco UCS equipment:FanStats:update managed object property"
    ::= { cucsEquipmentFanStatsEntry 12 }

cucsEquipmentFanStatsHistTable OBJECT-TYPE
    SYNTAX           SEQUENCE OF CucsEquipmentFanStatsHistEntry
    MAX-ACCESS       not-accessible
    STATUS           current
    DESCRIPTION
        "Cisco UCS equipment:FanStatsHist managed object table"
    ::= { cucsEquipmentObjects 18 }

cucsEquipmentFanStatsHistEntry OBJECT-TYPE
    SYNTAX           CucsEquipmentFanStatsHistEntry
    MAX-ACCESS       not-accessible
    STATUS           current
    DESCRIPTION
        "Entry for the cucsEquipmentFanStatsHistTable table."
    INDEX { cucsEquipmentFanStatsHistInstanceId }
    ::= { cucsEquipmentFanStatsHistTable 1 }

CucsEquipmentFanStatsHistEntry ::= SEQUENCE {
    cucsEquipmentFanStatsHistInstanceId                              CucsManagedObjectId,
    cucsEquipmentFanStatsHistDn                                      CucsManagedObjectDn,
    cucsEquipmentFanStatsHistRn                                      SnmpAdminString,
    cucsEquipmentFanStatsHistId                                      Unsigned64,
    cucsEquipmentFanStatsHistMostRecent                              TruthValue,
    cucsEquipmentFanStatsHistSpeed                                   Gauge32,
    cucsEquipmentFanStatsHistSpeedAvg                                Gauge32,
    cucsEquipmentFanStatsHistSpeedMax                                Gauge32,
    cucsEquipmentFanStatsHistSpeedMin                                Gauge32,
    cucsEquipmentFanStatsHistSuspect                                 TruthValue,
    cucsEquipmentFanStatsHistThresholded                             CucsEquipmentFanStatsHistThresholded,
    cucsEquipmentFanStatsHistTimeCollected                           DateAndTime
}

cucsEquipmentFanStatsHistInstanceId OBJECT-TYPE
    SYNTAX       CucsManagedObjectId
    MAX-ACCESS   not-accessible
    STATUS       current
    DESCRIPTION
        "Instance identifier of the managed object."
    ::= { cucsEquipmentFanStatsHistEntry 1 }

cucsEquipmentFanStatsHistDn OBJECT-TYPE
    SYNTAX       CucsManagedObjectDn
    MAX-ACCESS   read-only
    STATUS       current
    DESCRIPTION
        "Cisco UCS equipment:FanStatsHist:dn managed object property"
    ::= { cucsEquipmentFanStatsHistEntry 2 }

cucsEquipmentFanStatsHistRn OBJECT-TYPE
    SYNTAX       SnmpAdminString
    MAX-ACCESS   read-only
    STATUS       current
    DESCRIPTION
        "Cisco UCS equipment:FanStatsHist:rn managed object property"
    ::= { cucsEquipmentFanStatsHistEntry 3 }

cucsEquipmentFanStatsHistId OBJECT-TYPE
    SYNTAX       Unsigned64
    MAX-ACCESS   read-only
    STATUS       current
    DESCRIPTION
        "Cisco UCS equipment:FanStatsHist:id managed object property"
    ::= { cucsEquipmentFanStatsHistEntry 4 }

cucsEquipmentFanStatsHistMostRecent OBJECT-TYPE
    SYNTAX       TruthValue
    MAX-ACCESS   read-only
    STATUS       current
    DESCRIPTION
        "Cisco UCS equipment:FanStatsHist:mostRecent managed
        object property"
    ::= { cucsEquipmentFanStatsHistEntry 5 }

cucsEquipmentFanStatsHistSpeed OBJECT-TYPE
    SYNTAX       Gauge32
    MAX-ACCESS   read-only
    STATUS       current
    DESCRIPTION
        "Cisco UCS equipment:FanStatsHist:speed managed object property"
    ::= { cucsEquipmentFanStatsHistEntry 6 }

cucsEquipmentFanStatsHistSpeedAvg OBJECT-TYPE
    SYNTAX       Gauge32
    MAX-ACCESS   read-only
    STATUS       current
    DESCRIPTION
        "Cisco UCS equipment:FanStatsHist:speedAvg managed
        object property"
    ::= { cucsEquipmentFanStatsHistEntry 7 }

cucsEquipmentFanStatsHistSpeedMax OBJECT-TYPE
    SYNTAX       Gauge32
    MAX-ACCESS   read-only
    STATUS       current
    DESCRIPTION
        "Cisco UCS equipment:FanStatsHist:speedMax managed
        object property"
    ::= { cucsEquipmentFanStatsHistEntry 8 }

cucsEquipmentFanStatsHistSpeedMin OBJECT-TYPE
    SYNTAX       Gauge32
    MAX-ACCESS   read-only
    STATUS       current
    DESCRIPTION
        "Cisco UCS equipment:FanStatsHist:speedMin managed
        object property"
    ::= { cucsEquipmentFanStatsHistEntry 9 }

cucsEquipmentFanStatsHistSuspect OBJECT-TYPE
    SYNTAX       TruthValue
    MAX-ACCESS   read-only
    STATUS       current
    DESCRIPTION
        "Cisco UCS equipment:FanStatsHist:suspect managed object property"
    ::= { cucsEquipmentFanStatsHistEntry 10 }

cucsEquipmentFanStatsHistThresholded OBJECT-TYPE
    SYNTAX       CucsEquipmentFanStatsHistThresholded
    MAX-ACCESS   read-only
    STATUS       current
    DESCRIPTION
        "Cisco UCS equipment:FanStatsHist:thresholded managed
        object property"
    ::= { cucsEquipmentFanStatsHistEntry 11 }

cucsEquipmentFanStatsHistTimeCollected OBJECT-TYPE
    SYNTAX       DateAndTime
    MAX-ACCESS   read-only
    STATUS       current
    DESCRIPTION
        "Cisco UCS equipment:FanStatsHist:timeCollected
        managed object property"
    ::= { cucsEquipmentFanStatsHistEntry 12 }

cucsEquipmentFexTable OBJECT-TYPE
    SYNTAX           SEQUENCE OF CucsEquipmentFexEntry
    MAX-ACCESS       not-accessible
    STATUS           current
    DESCRIPTION
        "Cisco UCS equipment:Fex managed object table"
    ::= { cucsEquipmentObjects 19 }

cucsEquipmentFexEntry OBJECT-TYPE
    SYNTAX           CucsEquipmentFexEntry
    MAX-ACCESS       not-accessible
    STATUS           current
    DESCRIPTION
        "Entry for the cucsEquipmentFexTable table."
    INDEX { cucsEquipmentFexInstanceId }
    ::= { cucsEquipmentFexTable 1 }

CucsEquipmentFexEntry ::= SEQUENCE {
    cucsEquipmentFexInstanceId                                       CucsManagedObjectId,
    cucsEquipmentFexDn                                               CucsManagedObjectDn,
    cucsEquipmentFexRn                                               SnmpAdminString,
    cucsEquipmentFexAdminPowerState                                  CucsEquipmentAdminPowerState,
    cucsEquipmentFexAdminState                                       CucsEquipmentChassisAdminState,
    cucsEquipmentFexConfigState                                      CucsEquipmentChassisConfigState,
    cucsEquipmentFexFltAggr                                          Unsigned64,
    cucsEquipmentFexFsmDescr                                         SnmpAdminString,
    cucsEquipmentFexFsmPrev                                          SnmpAdminString,
    cucsEquipmentFexFsmProgr                                         Gauge32,
    cucsEquipmentFexFsmRmtInvErrCode                                 Gauge32,
    cucsEquipmentFexFsmRmtInvErrDescr                                SnmpAdminString,
    cucsEquipmentFexFsmRmtInvRslt                                    CucsConditionRemoteInvRslt,
    cucsEquipmentFexFsmStageDescr                                    SnmpAdminString,
    cucsEquipmentFexFsmStamp                                         DateAndTime,
    cucsEquipmentFexFsmStatus                                        SnmpAdminString,
    cucsEquipmentFexFsmTry                                           Gauge32,
    cucsEquipmentFexId                                               CucsEquipmentFexId,
    cucsEquipmentFexModel                                            SnmpAdminString,
    cucsEquipmentFexOperQualifier                                    CucsEquipmentChassisIssues,
    cucsEquipmentFexOperState                                        CucsEquipmentOperability,
    cucsEquipmentFexOperability                                      CucsEquipmentOperability,
    cucsEquipmentFexPower                                            CucsEquipmentPowerState,
    cucsEquipmentFexPresence                                         CucsEquipmentPresence,
    cucsEquipmentFexRevision                                         SnmpAdminString,
    cucsEquipmentFexSerial                                           SnmpAdminString,
    cucsEquipmentFexThermal                                          CucsEquipmentSensorThresholdStatus,
    cucsEquipmentFexUsrLbl                                           SnmpAdminString,
    cucsEquipmentFexVendor                                           SnmpAdminString,
    cucsEquipmentFexVoltage                                          CucsEquipmentSensorThresholdStatus,
    cucsEquipmentFexSwitchId                                         CucsNetworkSwitchId,
    cucsEquipmentFexLicGP                                            Unsigned64,
    cucsEquipmentFexLicState                                         CucsLicenseState,
    cucsEquipmentFexOperQualifierReason                              SnmpAdminString
}

cucsEquipmentFexInstanceId OBJECT-TYPE
    SYNTAX       CucsManagedObjectId
    MAX-ACCESS   not-accessible
    STATUS       current
    DESCRIPTION
        "Instance identifier of the managed object."
    ::= { cucsEquipmentFexEntry 1 }

cucsEquipmentFexDn OBJECT-TYPE
    SYNTAX       CucsManagedObjectDn
    MAX-ACCESS   read-only
    STATUS       current
    DESCRIPTION
        "Cisco UCS equipment:Fex:dn managed object property"
    ::= { cucsEquipmentFexEntry 2 }

cucsEquipmentFexRn OBJECT-TYPE
    SYNTAX       SnmpAdminString
    MAX-ACCESS   read-only
    STATUS       current
    DESCRIPTION
        "Cisco UCS equipment:Fex:rn managed object property"
    ::= { cucsEquipmentFexEntry 3 }

cucsEquipmentFexAdminPowerState OBJECT-TYPE
    SYNTAX       CucsEquipmentAdminPowerState
    MAX-ACCESS   read-only
    STATUS       current
    DESCRIPTION
        "Cisco UCS equipment:Fex:adminPowerState managed object property"
    ::= { cucsEquipmentFexEntry 4 }

cucsEquipmentFexAdminState OBJECT-TYPE
    SYNTAX       CucsEquipmentChassisAdminState
    MAX-ACCESS   read-only
    STATUS       current
    DESCRIPTION
        "Cisco UCS equipment:Fex:adminState managed object property"
    ::= { cucsEquipmentFexEntry 5 }

cucsEquipmentFexConfigState OBJECT-TYPE
    SYNTAX       CucsEquipmentChassisConfigState
    MAX-ACCESS   read-only
    STATUS       current
    DESCRIPTION
        "Cisco UCS equipment:Fex:configState managed object property"
    ::= { cucsEquipmentFexEntry 6 }

cucsEquipmentFexFltAggr OBJECT-TYPE
    SYNTAX       Unsigned64
    MAX-ACCESS   read-only
    STATUS       current
    DESCRIPTION
        "Cisco UCS equipment:Fex:fltAggr managed object property"
    ::= { cucsEquipmentFexEntry 7 }

cucsEquipmentFexFsmDescr OBJECT-TYPE
    SYNTAX       SnmpAdminString
    MAX-ACCESS   read-only
    STATUS       current
    DESCRIPTION
        "Cisco UCS equipment:Fex:fsmDescr managed object property"
    ::= { cucsEquipmentFexEntry 8 }

cucsEquipmentFexFsmPrev OBJECT-TYPE
    SYNTAX       SnmpAdminString
    MAX-ACCESS   read-only
    STATUS       current
    DESCRIPTION
        "Cisco UCS equipment:Fex:fsmPrev managed object property"
    ::= { cucsEquipmentFexEntry 9 }

cucsEquipmentFexFsmProgr OBJECT-TYPE
    SYNTAX       Gauge32
    MAX-ACCESS   read-only
    STATUS       current
    DESCRIPTION
        "Cisco UCS equipment:Fex:fsmProgr managed object property"
    ::= { cucsEquipmentFexEntry 10 }

cucsEquipmentFexFsmRmtInvErrCode OBJECT-TYPE
    SYNTAX       Gauge32
    MAX-ACCESS   read-only
    STATUS       current
    DESCRIPTION
        "Cisco UCS equipment:Fex:fsmRmtInvErrCode managed object property"
    ::= { cucsEquipmentFexEntry 11 }

cucsEquipmentFexFsmRmtInvErrDescr OBJECT-TYPE
    SYNTAX       SnmpAdminString
    MAX-ACCESS   read-only
    STATUS       current
    DESCRIPTION
        "Cisco UCS equipment:Fex:fsmRmtInvErrDescr managed
        object property"
    ::= { cucsEquipmentFexEntry 12 }

cucsEquipmentFexFsmRmtInvRslt OBJECT-TYPE
    SYNTAX       CucsConditionRemoteInvRslt
    MAX-ACCESS   read-only
    STATUS       current
    DESCRIPTION
        "Cisco UCS equipment:Fex:fsmRmtInvRslt managed object property"
    ::= { cucsEquipmentFexEntry 13 }

cucsEquipmentFexFsmStageDescr OBJECT-TYPE
    SYNTAX       SnmpAdminString
    MAX-ACCESS   read-only
    STATUS       current
    DESCRIPTION
        "Cisco UCS equipment:Fex:fsmStageDescr managed object property"
    ::= { cucsEquipmentFexEntry 14 }

cucsEquipmentFexFsmStamp OBJECT-TYPE
    SYNTAX       DateAndTime
    MAX-ACCESS   read-only
    STATUS       current
    DESCRIPTION
        "Cisco UCS equipment:Fex:fsmStamp managed object property"
    ::= { cucsEquipmentFexEntry 15 }

cucsEquipmentFexFsmStatus OBJECT-TYPE
    SYNTAX       SnmpAdminString
    MAX-ACCESS   read-only
    STATUS       current
    DESCRIPTION
        "Cisco UCS equipment:Fex:fsmStatus managed object property"
    ::= { cucsEquipmentFexEntry 16 }

cucsEquipmentFexFsmTry OBJECT-TYPE
    SYNTAX       Gauge32
    MAX-ACCESS   read-only
    STATUS       current
    DESCRIPTION
        "Cisco UCS equipment:Fex:fsmTry managed object property"
    ::= { cucsEquipmentFexEntry 17 }

cucsEquipmentFexId OBJECT-TYPE
    SYNTAX       CucsEquipmentFexId
    MAX-ACCESS   read-only
    STATUS       current
    DESCRIPTION
        "Cisco UCS equipment:Fex:id managed object property"
    ::= { cucsEquipmentFexEntry 18 }

cucsEquipmentFexModel OBJECT-TYPE
    SYNTAX       SnmpAdminString
    MAX-ACCESS   read-only
    STATUS       current
    DESCRIPTION
        "Cisco UCS equipment:Fex:model managed object property"
    ::= { cucsEquipmentFexEntry 19 }

cucsEquipmentFexOperQualifier OBJECT-TYPE
    SYNTAX       CucsEquipmentChassisIssues
    MAX-ACCESS   read-only
    STATUS       current
    DESCRIPTION
        "Cisco UCS equipment:Fex:operQualifier managed object property"
    ::= { cucsEquipmentFexEntry 20 }

cucsEquipmentFexOperState OBJECT-TYPE
    SYNTAX       CucsEquipmentOperability
    MAX-ACCESS   read-only
    STATUS       current
    DESCRIPTION
        "Cisco UCS equipment:Fex:operState managed object property"
    ::= { cucsEquipmentFexEntry 21 }

cucsEquipmentFexOperability OBJECT-TYPE
    SYNTAX       CucsEquipmentOperability
    MAX-ACCESS   read-only
    STATUS       current
    DESCRIPTION
        "Cisco UCS equipment:Fex:operability managed object property"
    ::= { cucsEquipmentFexEntry 22 }

cucsEquipmentFexPower OBJECT-TYPE
    SYNTAX       CucsEquipmentPowerState
    MAX-ACCESS   read-only
    STATUS       current
    DESCRIPTION
        "Cisco UCS equipment:Fex:power managed object property"
    ::= { cucsEquipmentFexEntry 23 }

cucsEquipmentFexPresence OBJECT-TYPE
    SYNTAX       CucsEquipmentPresence
    MAX-ACCESS   read-only
    STATUS       current
    DESCRIPTION
        "Cisco UCS equipment:Fex:presence managed object property"
    ::= { cucsEquipmentFexEntry 24 }

cucsEquipmentFexRevision OBJECT-TYPE
    SYNTAX       SnmpAdminString
    MAX-ACCESS   read-only
    STATUS       current
    DESCRIPTION
        "Cisco UCS equipment:Fex:revision managed object property"
    ::= { cucsEquipmentFexEntry 25 }

cucsEquipmentFexSerial OBJECT-TYPE
    SYNTAX       SnmpAdminString
    MAX-ACCESS   read-only
    STATUS       current
    DESCRIPTION
        "Cisco UCS equipment:Fex:serial managed object property"
    ::= { cucsEquipmentFexEntry 26 }

cucsEquipmentFexThermal OBJECT-TYPE
    SYNTAX       CucsEquipmentSensorThresholdStatus
    MAX-ACCESS   read-only
    STATUS       current
    DESCRIPTION
        "Cisco UCS equipment:Fex:thermal managed object property"
    ::= { cucsEquipmentFexEntry 27 }

cucsEquipmentFexUsrLbl OBJECT-TYPE
    SYNTAX       SnmpAdminString
    MAX-ACCESS   read-only
    STATUS       current
    DESCRIPTION
        "Cisco UCS equipment:Fex:usrLbl managed object property"
    ::= { cucsEquipmentFexEntry 28 }

cucsEquipmentFexVendor OBJECT-TYPE
    SYNTAX       SnmpAdminString
    MAX-ACCESS   read-only
    STATUS       current
    DESCRIPTION
        "Cisco UCS equipment:Fex:vendor managed object property"
    ::= { cucsEquipmentFexEntry 29 }

cucsEquipmentFexVoltage OBJECT-TYPE
    SYNTAX       CucsEquipmentSensorThresholdStatus
    MAX-ACCESS   read-only
    STATUS       current
    DESCRIPTION
        "Cisco UCS equipment:Fex:voltage managed object property"
    ::= { cucsEquipmentFexEntry 30 }

cucsEquipmentFexSwitchId OBJECT-TYPE
    SYNTAX       CucsNetworkSwitchId
    MAX-ACCESS   read-only
    STATUS       current
    DESCRIPTION
        "Cisco UCS equipment:Fex:switchId managed object property"
    ::= { cucsEquipmentFexEntry 31 }

cucsEquipmentFexLicGP OBJECT-TYPE
    SYNTAX       Unsigned64
    MAX-ACCESS   read-only
    STATUS       current
    DESCRIPTION
        "Cisco UCS equipment:Fex:licGP managed object property"
    ::= { cucsEquipmentFexEntry 32 }

cucsEquipmentFexLicState OBJECT-TYPE
    SYNTAX       CucsLicenseState
    MAX-ACCESS   read-only
    STATUS       current
    DESCRIPTION
        "Cisco UCS equipment:Fex:licState managed object property"
    ::= { cucsEquipmentFexEntry 33 }

cucsEquipmentFexOperQualifierReason OBJECT-TYPE
    SYNTAX       SnmpAdminString
    MAX-ACCESS   read-only
    STATUS       current
    DESCRIPTION
        "Cisco UCS equipment:Fex:operQualifierReason managed
        object property"
    ::= { cucsEquipmentFexEntry 34 }

cucsEquipmentFexCapProviderTable OBJECT-TYPE
    SYNTAX           SEQUENCE OF CucsEquipmentFexCapProviderEntry
    MAX-ACCESS       not-accessible
    STATUS           current
    DESCRIPTION
        "Cisco UCS equipment:FexCapProvider managed object table"
    ::= { cucsEquipmentObjects 20 }

cucsEquipmentFexCapProviderEntry OBJECT-TYPE
    SYNTAX           CucsEquipmentFexCapProviderEntry
    MAX-ACCESS       not-accessible
    STATUS           current
    DESCRIPTION
        "Entry for the cucsEquipmentFexCapProviderTable table."
    INDEX { cucsEquipmentFexCapProviderInstanceId }
    ::= { cucsEquipmentFexCapProviderTable 1 }

CucsEquipmentFexCapProviderEntry ::= SEQUENCE {
    cucsEquipmentFexCapProviderInstanceId                            CucsManagedObjectId,
    cucsEquipmentFexCapProviderDn                                    CucsManagedObjectDn,
    cucsEquipmentFexCapProviderRn                                    SnmpAdminString,
    cucsEquipmentFexCapProviderDeprecated                            TruthValue,
    cucsEquipmentFexCapProviderGencount                              Gauge32,
    cucsEquipmentFexCapProviderMgmtPlaneVer                          SnmpAdminString,
    cucsEquipmentFexCapProviderModel                                 SnmpAdminString,
    cucsEquipmentFexCapProviderRevision                              SnmpAdminString,
    cucsEquipmentFexCapProviderVendor                                SnmpAdminString,
    cucsEquipmentFexCapProviderPromCardType                          Gauge32,
    cucsEquipmentFexCapProviderDeleted                               TruthValue,
    cucsEquipmentFexCapProviderRole                                  CucsEquipmentFexCapProviderRole,
    cucsEquipmentFexCapProviderElementLoadFailures                   Gauge32,
    cucsEquipmentFexCapProviderElementsLoaded                        Gauge32,
    cucsEquipmentFexCapProviderLoadErrors                            Gauge32,
    cucsEquipmentFexCapProviderLoadWarnings                          Gauge32
}

cucsEquipmentFexCapProviderInstanceId OBJECT-TYPE
    SYNTAX       CucsManagedObjectId
    MAX-ACCESS   not-accessible
    STATUS       current
    DESCRIPTION
        "Instance identifier of the managed object."
    ::= { cucsEquipmentFexCapProviderEntry 1 }

cucsEquipmentFexCapProviderDn OBJECT-TYPE
    SYNTAX       CucsManagedObjectDn
    MAX-ACCESS   read-only
    STATUS       current
    DESCRIPTION
        "Cisco UCS equipment:FexCapProvider:dn managed object property"
    ::= { cucsEquipmentFexCapProviderEntry 2 }

cucsEquipmentFexCapProviderRn OBJECT-TYPE
    SYNTAX       SnmpAdminString
    MAX-ACCESS   read-only
    STATUS       current
    DESCRIPTION
        "Cisco UCS equipment:FexCapProvider:rn managed object property"
    ::= { cucsEquipmentFexCapProviderEntry 3 }

cucsEquipmentFexCapProviderDeprecated OBJECT-TYPE
    SYNTAX       TruthValue
    MAX-ACCESS   read-only
    STATUS       current
    DESCRIPTION
        "Cisco UCS equipment:FexCapProvider:deprecated
        managed object property"
    ::= { cucsEquipmentFexCapProviderEntry 4 }

cucsEquipmentFexCapProviderGencount OBJECT-TYPE
    SYNTAX       Gauge32
    MAX-ACCESS   read-only
    STATUS       current
    DESCRIPTION
        "Cisco UCS equipment:FexCapProvider:gencount managed
        object property"
    ::= { cucsEquipmentFexCapProviderEntry 5 }

cucsEquipmentFexCapProviderMgmtPlaneVer OBJECT-TYPE
    SYNTAX       SnmpAdminString
    MAX-ACCESS   read-only
    STATUS       current
    DESCRIPTION
        "Cisco UCS equipment:FexCapProvider:mgmtPlaneVer
        managed object property"
    ::= { cucsEquipmentFexCapProviderEntry 6 }

cucsEquipmentFexCapProviderModel OBJECT-TYPE
    SYNTAX       SnmpAdminString
    MAX-ACCESS   read-only
    STATUS       current
    DESCRIPTION
        "Cisco UCS equipment:FexCapProvider:model managed object property"
    ::= { cucsEquipmentFexCapProviderEntry 7 }

cucsEquipmentFexCapProviderRevision OBJECT-TYPE
    SYNTAX       SnmpAdminString
    MAX-ACCESS   read-only
    STATUS       current
    DESCRIPTION
        "Cisco UCS equipment:FexCapProvider:revision managed
        object property"
    ::= { cucsEquipmentFexCapProviderEntry 8 }

cucsEquipmentFexCapProviderVendor OBJECT-TYPE
    SYNTAX       SnmpAdminString
    MAX-ACCESS   read-only
    STATUS       current
    DESCRIPTION
        "Cisco UCS equipment:FexCapProvider:vendor managed
        object property"
    ::= { cucsEquipmentFexCapProviderEntry 9 }

cucsEquipmentFexCapProviderPromCardType OBJECT-TYPE
    SYNTAX       Gauge32
    MAX-ACCESS   read-only
    STATUS       current
    DESCRIPTION
        "Cisco UCS equipment:FexCapProvider:promCardType
        managed object property"
    ::= { cucsEquipmentFexCapProviderEntry 10 }

cucsEquipmentFexCapProviderDeleted OBJECT-TYPE
    SYNTAX       TruthValue
    MAX-ACCESS   read-only
    STATUS       current
    DESCRIPTION
        "Cisco UCS equipment:FexCapProvider:deleted managed
        object property"
    ::= { cucsEquipmentFexCapProviderEntry 11 }

cucsEquipmentFexCapProviderRole OBJECT-TYPE
    SYNTAX       CucsEquipmentFexCapProviderRole
    MAX-ACCESS   read-only
    STATUS       current
    DESCRIPTION
        "Cisco UCS equipment:FexCapProvider:role managed object property"
    ::= { cucsEquipmentFexCapProviderEntry 12 }

cucsEquipmentFexCapProviderElementLoadFailures OBJECT-TYPE
    SYNTAX       Gauge32
    MAX-ACCESS   read-only
    STATUS       current
    DESCRIPTION
        "Cisco UCS equipment:FexCapProvider:elementLoadFailures
        managed object property"
    ::= { cucsEquipmentFexCapProviderEntry 13 }

cucsEquipmentFexCapProviderElementsLoaded OBJECT-TYPE
    SYNTAX       Gauge32
    MAX-ACCESS   read-only
    STATUS       current
    DESCRIPTION
        "Cisco UCS equipment:FexCapProvider:elementsLoaded
        managed object property"
    ::= { cucsEquipmentFexCapProviderEntry 14 }

cucsEquipmentFexCapProviderLoadErrors OBJECT-TYPE
    SYNTAX       Gauge32
    MAX-ACCESS   read-only
    STATUS       current
    DESCRIPTION
        "Cisco UCS equipment:FexCapProvider:loadErrors
        managed object property"
    ::= { cucsEquipmentFexCapProviderEntry 15 }

cucsEquipmentFexCapProviderLoadWarnings OBJECT-TYPE
    SYNTAX       Gauge32
    MAX-ACCESS   read-only
    STATUS       current
    DESCRIPTION
        "Cisco UCS equipment:FexCapProvider:loadWarnings
        managed object property"
    ::= { cucsEquipmentFexCapProviderEntry 16 }

cucsEquipmentFexEnvStatsTable OBJECT-TYPE
    SYNTAX           SEQUENCE OF CucsEquipmentFexEnvStatsEntry
    MAX-ACCESS       not-accessible
    STATUS           current
    DESCRIPTION
        "Cisco UCS equipment:FexEnvStats managed object table"
    ::= { cucsEquipmentObjects 21 }

cucsEquipmentFexEnvStatsEntry OBJECT-TYPE
    SYNTAX           CucsEquipmentFexEnvStatsEntry
    MAX-ACCESS       not-accessible
    STATUS           current
    DESCRIPTION
        "Entry for the cucsEquipmentFexEnvStatsTable table."
    INDEX { cucsEquipmentFexEnvStatsInstanceId }
    ::= { cucsEquipmentFexEnvStatsTable 1 }

CucsEquipmentFexEnvStatsEntry ::= SEQUENCE {
    cucsEquipmentFexEnvStatsInstanceId                               CucsManagedObjectId,
    cucsEquipmentFexEnvStatsDn                                       CucsManagedObjectDn,
    cucsEquipmentFexEnvStatsRn                                       SnmpAdminString,
    cucsEquipmentFexEnvStatsDie1                                     INTEGER,
    cucsEquipmentFexEnvStatsDie1Avg                                  INTEGER,
    cucsEquipmentFexEnvStatsDie1Max                                  INTEGER,
    cucsEquipmentFexEnvStatsDie1Min                                  INTEGER,
    cucsEquipmentFexEnvStatsInlet                                    INTEGER,
    cucsEquipmentFexEnvStatsInlet1                                   INTEGER,
    cucsEquipmentFexEnvStatsInlet1Avg                                INTEGER,
    cucsEquipmentFexEnvStatsInlet1Max                                INTEGER,
    cucsEquipmentFexEnvStatsInlet1Min                                INTEGER,
    cucsEquipmentFexEnvStatsInletAvg                                 INTEGER,
    cucsEquipmentFexEnvStatsInletMax                                 INTEGER,
    cucsEquipmentFexEnvStatsInletMin                                 INTEGER,
    cucsEquipmentFexEnvStatsInputStatus                              SnmpAdminString,
    cucsEquipmentFexEnvStatsIntervals                                Gauge32,
    cucsEquipmentFexEnvStatsOutlet1                                  INTEGER,
    cucsEquipmentFexEnvStatsOutlet1Avg                               INTEGER,
    cucsEquipmentFexEnvStatsOutlet1Max                               INTEGER,
    cucsEquipmentFexEnvStatsOutlet1Min                               INTEGER,
    cucsEquipmentFexEnvStatsOutlet2                                  INTEGER,
    cucsEquipmentFexEnvStatsOutlet2Avg                               INTEGER,
    cucsEquipmentFexEnvStatsOutlet2Max                               INTEGER,
    cucsEquipmentFexEnvStatsOutlet2Min                               INTEGER,
    cucsEquipmentFexEnvStatsSuspect                                  TruthValue,
    cucsEquipmentFexEnvStatsThresholded                              CucsEquipmentFexEnvStatsThresholded,
    cucsEquipmentFexEnvStatsTimeCollected                            DateAndTime,
    cucsEquipmentFexEnvStatsUpdate                                   Gauge32
}

cucsEquipmentFexEnvStatsInstanceId OBJECT-TYPE
    SYNTAX       CucsManagedObjectId
    MAX-ACCESS   not-accessible
    STATUS       current
    DESCRIPTION
        "Instance identifier of the managed object."
    ::= { cucsEquipmentFexEnvStatsEntry 1 }

cucsEquipmentFexEnvStatsDn OBJECT-TYPE
    SYNTAX       CucsManagedObjectDn
    MAX-ACCESS   read-only
    STATUS       current
    DESCRIPTION
        "Cisco UCS equipment:FexEnvStats:dn managed object property"
    ::= { cucsEquipmentFexEnvStatsEntry 2 }

cucsEquipmentFexEnvStatsRn OBJECT-TYPE
    SYNTAX       SnmpAdminString
    MAX-ACCESS   read-only
    STATUS       current
    DESCRIPTION
        "Cisco UCS equipment:FexEnvStats:rn managed object property"
    ::= { cucsEquipmentFexEnvStatsEntry 3 }

cucsEquipmentFexEnvStatsDie1 OBJECT-TYPE
    SYNTAX       INTEGER
    MAX-ACCESS   read-only
    STATUS       current
    DESCRIPTION
        "Cisco UCS equipment:FexEnvStats:die1 managed object property"
    ::= { cucsEquipmentFexEnvStatsEntry 4 }

cucsEquipmentFexEnvStatsDie1Avg OBJECT-TYPE
    SYNTAX       INTEGER
    MAX-ACCESS   read-only
    STATUS       current
    DESCRIPTION
        "Cisco UCS equipment:FexEnvStats:die1Avg managed object property"
    ::= { cucsEquipmentFexEnvStatsEntry 5 }

cucsEquipmentFexEnvStatsDie1Max OBJECT-TYPE
    SYNTAX       INTEGER
    MAX-ACCESS   read-only
    STATUS       current
    DESCRIPTION
        "Cisco UCS equipment:FexEnvStats:die1Max managed object property"
    ::= { cucsEquipmentFexEnvStatsEntry 6 }

cucsEquipmentFexEnvStatsDie1Min OBJECT-TYPE
    SYNTAX       INTEGER
    MAX-ACCESS   read-only
    STATUS       current
    DESCRIPTION
        "Cisco UCS equipment:FexEnvStats:die1Min managed object property"
    ::= { cucsEquipmentFexEnvStatsEntry 7 }

cucsEquipmentFexEnvStatsInlet OBJECT-TYPE
    SYNTAX       INTEGER
    MAX-ACCESS   read-only
    STATUS       current
    DESCRIPTION
        "Cisco UCS equipment:FexEnvStats:inlet managed object property"
    ::= { cucsEquipmentFexEnvStatsEntry 8 }

cucsEquipmentFexEnvStatsInlet1 OBJECT-TYPE
    SYNTAX       INTEGER
    MAX-ACCESS   read-only
    STATUS       current
    DESCRIPTION
        "Cisco UCS equipment:FexEnvStats:inlet1 managed object property"
    ::= { cucsEquipmentFexEnvStatsEntry 9 }

cucsEquipmentFexEnvStatsInlet1Avg OBJECT-TYPE
    SYNTAX       INTEGER
    MAX-ACCESS   read-only
    STATUS       current
    DESCRIPTION
        "Cisco UCS equipment:FexEnvStats:inlet1Avg managed
        object property"
    ::= { cucsEquipmentFexEnvStatsEntry 10 }

cucsEquipmentFexEnvStatsInlet1Max OBJECT-TYPE
    SYNTAX       INTEGER
    MAX-ACCESS   read-only
    STATUS       current
    DESCRIPTION
        "Cisco UCS equipment:FexEnvStats:inlet1Max managed
        object property"
    ::= { cucsEquipmentFexEnvStatsEntry 11 }

cucsEquipmentFexEnvStatsInlet1Min OBJECT-TYPE
    SYNTAX       INTEGER
    MAX-ACCESS   read-only
    STATUS       current
    DESCRIPTION
        "Cisco UCS equipment:FexEnvStats:inlet1Min managed
        object property"
    ::= { cucsEquipmentFexEnvStatsEntry 12 }

cucsEquipmentFexEnvStatsInletAvg OBJECT-TYPE
    SYNTAX       INTEGER
    MAX-ACCESS   read-only
    STATUS       current
    DESCRIPTION
        "Cisco UCS equipment:FexEnvStats:inletAvg managed object property"
    ::= { cucsEquipmentFexEnvStatsEntry 13 }

cucsEquipmentFexEnvStatsInletMax OBJECT-TYPE
    SYNTAX       INTEGER
    MAX-ACCESS   read-only
    STATUS       current
    DESCRIPTION
        "Cisco UCS equipment:FexEnvStats:inletMax managed object property"
    ::= { cucsEquipmentFexEnvStatsEntry 14 }

cucsEquipmentFexEnvStatsInletMin OBJECT-TYPE
    SYNTAX       INTEGER
    MAX-ACCESS   read-only
    STATUS       current
    DESCRIPTION
        "Cisco UCS equipment:FexEnvStats:inletMin managed object property"
    ::= { cucsEquipmentFexEnvStatsEntry 15 }

cucsEquipmentFexEnvStatsInputStatus OBJECT-TYPE
    SYNTAX       SnmpAdminString
    MAX-ACCESS   read-only
    STATUS       current
    DESCRIPTION
        "Cisco UCS equipment:FexEnvStats:inputStatus managed
        object property"
    ::= { cucsEquipmentFexEnvStatsEntry 16 }

cucsEquipmentFexEnvStatsIntervals OBJECT-TYPE
    SYNTAX       Gauge32
    MAX-ACCESS   read-only
    STATUS       current
    DESCRIPTION
        "Cisco UCS equipment:FexEnvStats:intervals managed
        object property"
    ::= { cucsEquipmentFexEnvStatsEntry 17 }

cucsEquipmentFexEnvStatsOutlet1 OBJECT-TYPE
    SYNTAX       INTEGER
    MAX-ACCESS   read-only
    STATUS       current
    DESCRIPTION
        "Cisco UCS equipment:FexEnvStats:outlet1 managed object property"
    ::= { cucsEquipmentFexEnvStatsEntry 18 }

cucsEquipmentFexEnvStatsOutlet1Avg OBJECT-TYPE
    SYNTAX       INTEGER
    MAX-ACCESS   read-only
    STATUS       current
    DESCRIPTION
        "Cisco UCS equipment:FexEnvStats:outlet1Avg managed
        object property"
    ::= { cucsEquipmentFexEnvStatsEntry 19 }

cucsEquipmentFexEnvStatsOutlet1Max OBJECT-TYPE
    SYNTAX       INTEGER
    MAX-ACCESS   read-only
    STATUS       current
    DESCRIPTION
        "Cisco UCS equipment:FexEnvStats:outlet1Max managed
        object property"
    ::= { cucsEquipmentFexEnvStatsEntry 20 }

cucsEquipmentFexEnvStatsOutlet1Min OBJECT-TYPE
    SYNTAX       INTEGER
    MAX-ACCESS   read-only
    STATUS       current
    DESCRIPTION
        "Cisco UCS equipment:FexEnvStats:outlet1Min managed
        object property"
    ::= { cucsEquipmentFexEnvStatsEntry 21 }

cucsEquipmentFexEnvStatsOutlet2 OBJECT-TYPE
    SYNTAX       INTEGER
    MAX-ACCESS   read-only
    STATUS       current
    DESCRIPTION
        "Cisco UCS equipment:FexEnvStats:outlet2 managed object property"
    ::= { cucsEquipmentFexEnvStatsEntry 22 }

cucsEquipmentFexEnvStatsOutlet2Avg OBJECT-TYPE
    SYNTAX       INTEGER
    MAX-ACCESS   read-only
    STATUS       current
    DESCRIPTION
        "Cisco UCS equipment:FexEnvStats:outlet2Avg managed
        object property"
    ::= { cucsEquipmentFexEnvStatsEntry 23 }

cucsEquipmentFexEnvStatsOutlet2Max OBJECT-TYPE
    SYNTAX       INTEGER
    MAX-ACCESS   read-only
    STATUS       current
    DESCRIPTION
        "Cisco UCS equipment:FexEnvStats:outlet2Max managed
        object property"
    ::= { cucsEquipmentFexEnvStatsEntry 24 }

cucsEquipmentFexEnvStatsOutlet2Min OBJECT-TYPE
    SYNTAX       INTEGER
    MAX-ACCESS   read-only
    STATUS       current
    DESCRIPTION
        "Cisco UCS equipment:FexEnvStats:outlet2Min managed
        object property"
    ::= { cucsEquipmentFexEnvStatsEntry 25 }

cucsEquipmentFexEnvStatsSuspect OBJECT-TYPE
    SYNTAX       TruthValue
    MAX-ACCESS   read-only
    STATUS       current
    DESCRIPTION
        "Cisco UCS equipment:FexEnvStats:suspect managed object property"
    ::= { cucsEquipmentFexEnvStatsEntry 26 }

cucsEquipmentFexEnvStatsThresholded OBJECT-TYPE
    SYNTAX       CucsEquipmentFexEnvStatsThresholded
    MAX-ACCESS   read-only
    STATUS       current
    DESCRIPTION
        "Cisco UCS equipment:FexEnvStats:thresholded managed
        object property"
    ::= { cucsEquipmentFexEnvStatsEntry 27 }

cucsEquipmentFexEnvStatsTimeCollected OBJECT-TYPE
    SYNTAX       DateAndTime
    MAX-ACCESS   read-only
    STATUS       current
    DESCRIPTION
        "Cisco UCS equipment:FexEnvStats:timeCollected
        managed object property"
    ::= { cucsEquipmentFexEnvStatsEntry 28 }

cucsEquipmentFexEnvStatsUpdate OBJECT-TYPE
    SYNTAX       Gauge32
    MAX-ACCESS   read-only
    STATUS       current
    DESCRIPTION
        "Cisco UCS equipment:FexEnvStats:update managed object property"
    ::= { cucsEquipmentFexEnvStatsEntry 29 }

cucsEquipmentFexEnvStatsHistTable OBJECT-TYPE
    SYNTAX           SEQUENCE OF CucsEquipmentFexEnvStatsHistEntry
    MAX-ACCESS       not-accessible
    STATUS           current
    DESCRIPTION
        "Cisco UCS equipment:FexEnvStatsHist managed object table"
    ::= { cucsEquipmentObjects 22 }

cucsEquipmentFexEnvStatsHistEntry OBJECT-TYPE
    SYNTAX           CucsEquipmentFexEnvStatsHistEntry
    MAX-ACCESS       not-accessible
    STATUS           current
    DESCRIPTION
        "Entry for the cucsEquipmentFexEnvStatsHistTable table."
    INDEX { cucsEquipmentFexEnvStatsHistInstanceId }
    ::= { cucsEquipmentFexEnvStatsHistTable 1 }

CucsEquipmentFexEnvStatsHistEntry ::= SEQUENCE {
    cucsEquipmentFexEnvStatsHistInstanceId                           CucsManagedObjectId,
    cucsEquipmentFexEnvStatsHistDn                                   CucsManagedObjectDn,
    cucsEquipmentFexEnvStatsHistRn                                   SnmpAdminString,
    cucsEquipmentFexEnvStatsHistDie1                                 INTEGER,
    cucsEquipmentFexEnvStatsHistDie1Avg                              INTEGER,
    cucsEquipmentFexEnvStatsHistDie1Max                              INTEGER,
    cucsEquipmentFexEnvStatsHistDie1Min                              INTEGER,
    cucsEquipmentFexEnvStatsHistId                                   Unsigned64,
    cucsEquipmentFexEnvStatsHistInlet                                INTEGER,
    cucsEquipmentFexEnvStatsHistInlet1                               INTEGER,
    cucsEquipmentFexEnvStatsHistInlet1Avg                            INTEGER,
    cucsEquipmentFexEnvStatsHistInlet1Max                            INTEGER,
    cucsEquipmentFexEnvStatsHistInlet1Min                            INTEGER,
    cucsEquipmentFexEnvStatsHistInletAvg                             INTEGER,
    cucsEquipmentFexEnvStatsHistInletMax                             INTEGER,
    cucsEquipmentFexEnvStatsHistInletMin                             INTEGER,
    cucsEquipmentFexEnvStatsHistMostRecent                           TruthValue,
    cucsEquipmentFexEnvStatsHistOutlet1                              INTEGER,
    cucsEquipmentFexEnvStatsHistOutlet1Avg                           INTEGER,
    cucsEquipmentFexEnvStatsHistOutlet1Max                           INTEGER,
    cucsEquipmentFexEnvStatsHistOutlet1Min                           INTEGER,
    cucsEquipmentFexEnvStatsHistOutlet2                              INTEGER,
    cucsEquipmentFexEnvStatsHistOutlet2Avg                           INTEGER,
    cucsEquipmentFexEnvStatsHistOutlet2Max                           INTEGER,
    cucsEquipmentFexEnvStatsHistOutlet2Min                           INTEGER,
    cucsEquipmentFexEnvStatsHistSuspect                              TruthValue,
    cucsEquipmentFexEnvStatsHistThresholded                          CucsEquipmentFexEnvStatsHistThresholded,
    cucsEquipmentFexEnvStatsHistTimeCollected                        DateAndTime
}

cucsEquipmentFexEnvStatsHistInstanceId OBJECT-TYPE
    SYNTAX       CucsManagedObjectId
    MAX-ACCESS   not-accessible
    STATUS       current
    DESCRIPTION
        "Instance identifier of the managed object."
    ::= { cucsEquipmentFexEnvStatsHistEntry 1 }

cucsEquipmentFexEnvStatsHistDn OBJECT-TYPE
    SYNTAX       CucsManagedObjectDn
    MAX-ACCESS   read-only
    STATUS       current
    DESCRIPTION
        "Cisco UCS equipment:FexEnvStatsHist:dn managed object property"
    ::= { cucsEquipmentFexEnvStatsHistEntry 2 }

cucsEquipmentFexEnvStatsHistRn OBJECT-TYPE
    SYNTAX       SnmpAdminString
    MAX-ACCESS   read-only
    STATUS       current
    DESCRIPTION
        "Cisco UCS equipment:FexEnvStatsHist:rn managed object property"
    ::= { cucsEquipmentFexEnvStatsHistEntry 3 }

cucsEquipmentFexEnvStatsHistDie1 OBJECT-TYPE
    SYNTAX       INTEGER
    MAX-ACCESS   read-only
    STATUS       current
    DESCRIPTION
        "Cisco UCS equipment:FexEnvStatsHist:die1 managed object property"
    ::= { cucsEquipmentFexEnvStatsHistEntry 4 }

cucsEquipmentFexEnvStatsHistDie1Avg OBJECT-TYPE
    SYNTAX       INTEGER
    MAX-ACCESS   read-only
    STATUS       current
    DESCRIPTION
        "Cisco UCS equipment:FexEnvStatsHist:die1Avg managed
        object property"
    ::= { cucsEquipmentFexEnvStatsHistEntry 5 }

cucsEquipmentFexEnvStatsHistDie1Max OBJECT-TYPE
    SYNTAX       INTEGER
    MAX-ACCESS   read-only
    STATUS       current
    DESCRIPTION
        "Cisco UCS equipment:FexEnvStatsHist:die1Max managed
        object property"
    ::= { cucsEquipmentFexEnvStatsHistEntry 6 }

cucsEquipmentFexEnvStatsHistDie1Min OBJECT-TYPE
    SYNTAX       INTEGER
    MAX-ACCESS   read-only
    STATUS       current
    DESCRIPTION
        "Cisco UCS equipment:FexEnvStatsHist:die1Min managed
        object property"
    ::= { cucsEquipmentFexEnvStatsHistEntry 7 }

cucsEquipmentFexEnvStatsHistId OBJECT-TYPE
    SYNTAX       Unsigned64
    MAX-ACCESS   read-only
    STATUS       current
    DESCRIPTION
        "Cisco UCS equipment:FexEnvStatsHist:id managed object property"
    ::= { cucsEquipmentFexEnvStatsHistEntry 8 }

cucsEquipmentFexEnvStatsHistInlet OBJECT-TYPE
    SYNTAX       INTEGER
    MAX-ACCESS   read-only
    STATUS       current
    DESCRIPTION
        "Cisco UCS equipment:FexEnvStatsHist:inlet managed
        object property"
    ::= { cucsEquipmentFexEnvStatsHistEntry 9 }

cucsEquipmentFexEnvStatsHistInlet1 OBJECT-TYPE
    SYNTAX       INTEGER
    MAX-ACCESS   read-only
    STATUS       current
    DESCRIPTION
        "Cisco UCS equipment:FexEnvStatsHist:inlet1 managed
        object property"
    ::= { cucsEquipmentFexEnvStatsHistEntry 10 }

cucsEquipmentFexEnvStatsHistInlet1Avg OBJECT-TYPE
    SYNTAX       INTEGER
    MAX-ACCESS   read-only
    STATUS       current
    DESCRIPTION
        "Cisco UCS equipment:FexEnvStatsHist:inlet1Avg
        managed object property"
    ::= { cucsEquipmentFexEnvStatsHistEntry 11 }

cucsEquipmentFexEnvStatsHistInlet1Max OBJECT-TYPE
    SYNTAX       INTEGER
    MAX-ACCESS   read-only
    STATUS       current
    DESCRIPTION
        "Cisco UCS equipment:FexEnvStatsHist:inlet1Max
        managed object property"
    ::= { cucsEquipmentFexEnvStatsHistEntry 12 }

cucsEquipmentFexEnvStatsHistInlet1Min OBJECT-TYPE
    SYNTAX       INTEGER
    MAX-ACCESS   read-only
    STATUS       current
    DESCRIPTION
        "Cisco UCS equipment:FexEnvStatsHist:inlet1Min
        managed object property"
    ::= { cucsEquipmentFexEnvStatsHistEntry 13 }

cucsEquipmentFexEnvStatsHistInletAvg OBJECT-TYPE
    SYNTAX       INTEGER
    MAX-ACCESS   read-only
    STATUS       current
    DESCRIPTION
        "Cisco UCS equipment:FexEnvStatsHist:inletAvg managed
        object property"
    ::= { cucsEquipmentFexEnvStatsHistEntry 14 }

cucsEquipmentFexEnvStatsHistInletMax OBJECT-TYPE
    SYNTAX       INTEGER
    MAX-ACCESS   read-only
    STATUS       current
    DESCRIPTION
        "Cisco UCS equipment:FexEnvStatsHist:inletMax managed
        object property"
    ::= { cucsEquipmentFexEnvStatsHistEntry 15 }

cucsEquipmentFexEnvStatsHistInletMin OBJECT-TYPE
    SYNTAX       INTEGER
    MAX-ACCESS   read-only
    STATUS       current
    DESCRIPTION
        "Cisco UCS equipment:FexEnvStatsHist:inletMin managed
        object property"
    ::= { cucsEquipmentFexEnvStatsHistEntry 16 }

cucsEquipmentFexEnvStatsHistMostRecent OBJECT-TYPE
    SYNTAX       TruthValue
    MAX-ACCESS   read-only
    STATUS       current
    DESCRIPTION
        "Cisco UCS equipment:FexEnvStatsHist:mostRecent
        managed object property"
    ::= { cucsEquipmentFexEnvStatsHistEntry 17 }

cucsEquipmentFexEnvStatsHistOutlet1 OBJECT-TYPE
    SYNTAX       INTEGER
    MAX-ACCESS   read-only
    STATUS       current
    DESCRIPTION
        "Cisco UCS equipment:FexEnvStatsHist:outlet1 managed
        object property"
    ::= { cucsEquipmentFexEnvStatsHistEntry 18 }

cucsEquipmentFexEnvStatsHistOutlet1Avg OBJECT-TYPE
    SYNTAX       INTEGER
    MAX-ACCESS   read-only
    STATUS       current
    DESCRIPTION
        "Cisco UCS equipment:FexEnvStatsHist:outlet1Avg
        managed object property"
    ::= { cucsEquipmentFexEnvStatsHistEntry 19 }

cucsEquipmentFexEnvStatsHistOutlet1Max OBJECT-TYPE
    SYNTAX       INTEGER
    MAX-ACCESS   read-only
    STATUS       current
    DESCRIPTION
        "Cisco UCS equipment:FexEnvStatsHist:outlet1Max
        managed object property"
    ::= { cucsEquipmentFexEnvStatsHistEntry 20 }

cucsEquipmentFexEnvStatsHistOutlet1Min OBJECT-TYPE
    SYNTAX       INTEGER
    MAX-ACCESS   read-only
    STATUS       current
    DESCRIPTION
        "Cisco UCS equipment:FexEnvStatsHist:outlet1Min
        managed object property"
    ::= { cucsEquipmentFexEnvStatsHistEntry 21 }

cucsEquipmentFexEnvStatsHistOutlet2 OBJECT-TYPE
    SYNTAX       INTEGER
    MAX-ACCESS   read-only
    STATUS       current
    DESCRIPTION
        "Cisco UCS equipment:FexEnvStatsHist:outlet2 managed
        object property"
    ::= { cucsEquipmentFexEnvStatsHistEntry 22 }

cucsEquipmentFexEnvStatsHistOutlet2Avg OBJECT-TYPE
    SYNTAX       INTEGER
    MAX-ACCESS   read-only
    STATUS       current
    DESCRIPTION
        "Cisco UCS equipment:FexEnvStatsHist:outlet2Avg
        managed object property"
    ::= { cucsEquipmentFexEnvStatsHistEntry 23 }

cucsEquipmentFexEnvStatsHistOutlet2Max OBJECT-TYPE
    SYNTAX       INTEGER
    MAX-ACCESS   read-only
    STATUS       current
    DESCRIPTION
        "Cisco UCS equipment:FexEnvStatsHist:outlet2Max
        managed object property"
    ::= { cucsEquipmentFexEnvStatsHistEntry 24 }

cucsEquipmentFexEnvStatsHistOutlet2Min OBJECT-TYPE
    SYNTAX       INTEGER
    MAX-ACCESS   read-only
    STATUS       current
    DESCRIPTION
        "Cisco UCS equipment:FexEnvStatsHist:outlet2Min
        managed object property"
    ::= { cucsEquipmentFexEnvStatsHistEntry 25 }

cucsEquipmentFexEnvStatsHistSuspect OBJECT-TYPE
    SYNTAX       TruthValue
    MAX-ACCESS   read-only
    STATUS       current
    DESCRIPTION
        "Cisco UCS equipment:FexEnvStatsHist:suspect managed
        object property"
    ::= { cucsEquipmentFexEnvStatsHistEntry 26 }

cucsEquipmentFexEnvStatsHistThresholded OBJECT-TYPE
    SYNTAX       CucsEquipmentFexEnvStatsHistThresholded
    MAX-ACCESS   read-only
    STATUS       current
    DESCRIPTION
        "Cisco UCS equipment:FexEnvStatsHist:thresholded
        managed object property"
    ::= { cucsEquipmentFexEnvStatsHistEntry 27 }

cucsEquipmentFexEnvStatsHistTimeCollected OBJECT-TYPE
    SYNTAX       DateAndTime
    MAX-ACCESS   read-only
    STATUS       current
    DESCRIPTION
        "Cisco UCS equipment:FexEnvStatsHist:timeCollected
        managed object property"
    ::= { cucsEquipmentFexEnvStatsHistEntry 28 }

cucsEquipmentFexFsmTable OBJECT-TYPE
    SYNTAX           SEQUENCE OF CucsEquipmentFexFsmEntry
    MAX-ACCESS       not-accessible
    STATUS           current
    DESCRIPTION
        "Cisco UCS equipment:FexFsm managed object table"
    ::= { cucsEquipmentObjects 107 }

cucsEquipmentFexFsmEntry OBJECT-TYPE
    SYNTAX           CucsEquipmentFexFsmEntry
    MAX-ACCESS       not-accessible
    STATUS           current
    DESCRIPTION
        "Entry for the cucsEquipmentFexFsmTable table."
    INDEX { cucsEquipmentFexFsmInstanceId }
    ::= { cucsEquipmentFexFsmTable 1 }

CucsEquipmentFexFsmEntry ::= SEQUENCE {
    cucsEquipmentFexFsmInstanceId                                    CucsManagedObjectId,
    cucsEquipmentFexFsmDn                                            CucsManagedObjectDn,
    cucsEquipmentFexFsmRn                                            SnmpAdminString,
    cucsEquipmentFexFsmCompletionTime                                DateAndTime,
    cucsEquipmentFexFsmCurrentFsm                                    CucsEquipmentFexFsmCurrentFsm,
    cucsEquipmentFexFsmDescrData                                     SnmpAdminString,
    cucsEquipmentFexFsmFsmStatus                                     CucsFsmFsmStageStatus,
    cucsEquipmentFexFsmProgress                                      Gauge32,
    cucsEquipmentFexFsmRmtErrCode                                    Gauge32,
    cucsEquipmentFexFsmRmtErrDescr                                   SnmpAdminString,
    cucsEquipmentFexFsmRmtRslt                                       CucsConditionRemoteInvRslt
}

cucsEquipmentFexFsmInstanceId OBJECT-TYPE
    SYNTAX       CucsManagedObjectId
    MAX-ACCESS   not-accessible
    STATUS       current
    DESCRIPTION
        "Instance identifier of the managed object."
    ::= { cucsEquipmentFexFsmEntry 1 }

cucsEquipmentFexFsmDn OBJECT-TYPE
    SYNTAX       CucsManagedObjectDn
    MAX-ACCESS   read-only
    STATUS       current
    DESCRIPTION
        "Cisco UCS equipment:FexFsm:dn managed object property"
    ::= { cucsEquipmentFexFsmEntry 2 }

cucsEquipmentFexFsmRn OBJECT-TYPE
    SYNTAX       SnmpAdminString
    MAX-ACCESS   read-only
    STATUS       current
    DESCRIPTION
        "Cisco UCS equipment:FexFsm:rn managed object property"
    ::= { cucsEquipmentFexFsmEntry 3 }

cucsEquipmentFexFsmCompletionTime OBJECT-TYPE
    SYNTAX       DateAndTime
    MAX-ACCESS   read-only
    STATUS       current
    DESCRIPTION
        "Cisco UCS equipment:FexFsm:completionTime managed
        object property"
    ::= { cucsEquipmentFexFsmEntry 4 }

cucsEquipmentFexFsmCurrentFsm OBJECT-TYPE
    SYNTAX       CucsEquipmentFexFsmCurrentFsm
    MAX-ACCESS   read-only
    STATUS       current
    DESCRIPTION
        "Cisco UCS equipment:FexFsm:currentFsm managed object property"
    ::= { cucsEquipmentFexFsmEntry 5 }

cucsEquipmentFexFsmDescrData OBJECT-TYPE
    SYNTAX       SnmpAdminString
    MAX-ACCESS   read-only
    STATUS       current
    DESCRIPTION
        "Cisco UCS equipment:FexFsm:descr managed object property"
    ::= { cucsEquipmentFexFsmEntry 6 }

cucsEquipmentFexFsmFsmStatus OBJECT-TYPE
    SYNTAX       CucsFsmFsmStageStatus
    MAX-ACCESS   read-only
    STATUS       current
    DESCRIPTION
        "Cisco UCS equipment:FexFsm:fsmStatus managed object property"
    ::= { cucsEquipmentFexFsmEntry 7 }

cucsEquipmentFexFsmProgress OBJECT-TYPE
    SYNTAX       Gauge32
    MAX-ACCESS   read-only
    STATUS       current
    DESCRIPTION
        "Cisco UCS equipment:FexFsm:progress managed object property"
    ::= { cucsEquipmentFexFsmEntry 8 }

cucsEquipmentFexFsmRmtErrCode OBJECT-TYPE
    SYNTAX       Gauge32
    MAX-ACCESS   read-only
    STATUS       current
    DESCRIPTION
        "Cisco UCS equipment:FexFsm:rmtErrCode managed object property"
    ::= { cucsEquipmentFexFsmEntry 9 }

cucsEquipmentFexFsmRmtErrDescr OBJECT-TYPE
    SYNTAX       SnmpAdminString
    MAX-ACCESS   read-only
    STATUS       current
    DESCRIPTION
        "Cisco UCS equipment:FexFsm:rmtErrDescr managed object property"
    ::= { cucsEquipmentFexFsmEntry 10 }

cucsEquipmentFexFsmRmtRslt OBJECT-TYPE
    SYNTAX       CucsConditionRemoteInvRslt
    MAX-ACCESS   read-only
    STATUS       current
    DESCRIPTION
        "Cisco UCS equipment:FexFsm:rmtRslt managed object property"
    ::= { cucsEquipmentFexFsmEntry 11 }

cucsEquipmentFexFsmStageTable OBJECT-TYPE
    SYNTAX           SEQUENCE OF CucsEquipmentFexFsmStageEntry
    MAX-ACCESS       not-accessible
    STATUS           current
    DESCRIPTION
        "Cisco UCS equipment:FexFsmStage managed object table"
    ::= { cucsEquipmentObjects 108 }

cucsEquipmentFexFsmStageEntry OBJECT-TYPE
    SYNTAX           CucsEquipmentFexFsmStageEntry
    MAX-ACCESS       not-accessible
    STATUS           current
    DESCRIPTION
        "Entry for the cucsEquipmentFexFsmStageTable table."
    INDEX { cucsEquipmentFexFsmStageInstanceId }
    ::= { cucsEquipmentFexFsmStageTable 1 }

CucsEquipmentFexFsmStageEntry ::= SEQUENCE {
    cucsEquipmentFexFsmStageInstanceId                               CucsManagedObjectId,
    cucsEquipmentFexFsmStageDn                                       CucsManagedObjectDn,
    cucsEquipmentFexFsmStageRn                                       SnmpAdminString,
    cucsEquipmentFexFsmStageDescrData                                SnmpAdminString,
    cucsEquipmentFexFsmStageLastUpdateTime                           DateAndTime,
    cucsEquipmentFexFsmStageName                                     CucsEquipmentFexFsmStageName,
    cucsEquipmentFexFsmStageOrder                                    Gauge32,
    cucsEquipmentFexFsmStageRetry                                    Gauge32,
    cucsEquipmentFexFsmStageStageStatus                              CucsFsmFsmStageStatus
}

cucsEquipmentFexFsmStageInstanceId OBJECT-TYPE
    SYNTAX       CucsManagedObjectId
    MAX-ACCESS   not-accessible
    STATUS       current
    DESCRIPTION
        "Instance identifier of the managed object."
    ::= { cucsEquipmentFexFsmStageEntry 1 }

cucsEquipmentFexFsmStageDn OBJECT-TYPE
    SYNTAX       CucsManagedObjectDn
    MAX-ACCESS   read-only
    STATUS       current
    DESCRIPTION
        "Cisco UCS equipment:FexFsmStage:dn managed object property"
    ::= { cucsEquipmentFexFsmStageEntry 2 }

cucsEquipmentFexFsmStageRn OBJECT-TYPE
    SYNTAX       SnmpAdminString
    MAX-ACCESS   read-only
    STATUS       current
    DESCRIPTION
        "Cisco UCS equipment:FexFsmStage:rn managed object property"
    ::= { cucsEquipmentFexFsmStageEntry 3 }

cucsEquipmentFexFsmStageDescrData OBJECT-TYPE
    SYNTAX       SnmpAdminString
    MAX-ACCESS   read-only
    STATUS       current
    DESCRIPTION
        "Cisco UCS equipment:FexFsmStage:descr managed object property"
    ::= { cucsEquipmentFexFsmStageEntry 4 }

cucsEquipmentFexFsmStageLastUpdateTime OBJECT-TYPE
    SYNTAX       DateAndTime
    MAX-ACCESS   read-only
    STATUS       current
    DESCRIPTION
        "Cisco UCS equipment:FexFsmStage:lastUpdateTime
        managed object property"
    ::= { cucsEquipmentFexFsmStageEntry 5 }

cucsEquipmentFexFsmStageName OBJECT-TYPE
    SYNTAX       CucsEquipmentFexFsmStageName
    MAX-ACCESS   read-only
    STATUS       current
    DESCRIPTION
        "Cisco UCS equipment:FexFsmStage:name managed object property"
    ::= { cucsEquipmentFexFsmStageEntry 6 }

cucsEquipmentFexFsmStageOrder OBJECT-TYPE
    SYNTAX       Gauge32
    MAX-ACCESS   read-only
    STATUS       current
    DESCRIPTION
        "Cisco UCS equipment:FexFsmStage:order managed object property"
    ::= { cucsEquipmentFexFsmStageEntry 7 }

cucsEquipmentFexFsmStageRetry OBJECT-TYPE
    SYNTAX       Gauge32
    MAX-ACCESS   read-only
    STATUS       current
    DESCRIPTION
        "Cisco UCS equipment:FexFsmStage:retry managed object property"
    ::= { cucsEquipmentFexFsmStageEntry 8 }

cucsEquipmentFexFsmStageStageStatus OBJECT-TYPE
    SYNTAX       CucsFsmFsmStageStatus
    MAX-ACCESS   read-only
    STATUS       current
    DESCRIPTION
        "Cisco UCS equipment:FexFsmStage:stageStatus managed
        object property"
    ::= { cucsEquipmentFexFsmStageEntry 9 }

cucsEquipmentFexFsmTaskTable OBJECT-TYPE
    SYNTAX           SEQUENCE OF CucsEquipmentFexFsmTaskEntry
    MAX-ACCESS       not-accessible
    STATUS           current
    DESCRIPTION
        "Cisco UCS equipment:FexFsmTask managed object table"
    ::= { cucsEquipmentObjects 23 }

cucsEquipmentFexFsmTaskEntry OBJECT-TYPE
    SYNTAX           CucsEquipmentFexFsmTaskEntry
    MAX-ACCESS       not-accessible
    STATUS           current
    DESCRIPTION
        "Entry for the cucsEquipmentFexFsmTaskTable table."
    INDEX { cucsEquipmentFexFsmTaskInstanceId }
    ::= { cucsEquipmentFexFsmTaskTable 1 }

CucsEquipmentFexFsmTaskEntry ::= SEQUENCE {
    cucsEquipmentFexFsmTaskInstanceId                                CucsManagedObjectId,
    cucsEquipmentFexFsmTaskDn                                        CucsManagedObjectDn,
    cucsEquipmentFexFsmTaskRn                                        SnmpAdminString,
    cucsEquipmentFexFsmTaskCompletion                                CucsFsmCompletion,
    cucsEquipmentFexFsmTaskFlags                                     CucsFsmFlags,
    cucsEquipmentFexFsmTaskItem                                      CucsEquipmentFexFsmTaskItem,
    cucsEquipmentFexFsmTaskSeqId                                     Gauge32
}

cucsEquipmentFexFsmTaskInstanceId OBJECT-TYPE
    SYNTAX       CucsManagedObjectId
    MAX-ACCESS   not-accessible
    STATUS       current
    DESCRIPTION
        "Instance identifier of the managed object."
    ::= { cucsEquipmentFexFsmTaskEntry 1 }

cucsEquipmentFexFsmTaskDn OBJECT-TYPE
    SYNTAX       CucsManagedObjectDn
    MAX-ACCESS   read-only
    STATUS       current
    DESCRIPTION
        "Cisco UCS equipment:FexFsmTask:dn managed object property"
    ::= { cucsEquipmentFexFsmTaskEntry 2 }

cucsEquipmentFexFsmTaskRn OBJECT-TYPE
    SYNTAX       SnmpAdminString
    MAX-ACCESS   read-only
    STATUS       current
    DESCRIPTION
        "Cisco UCS equipment:FexFsmTask:rn managed object property"
    ::= { cucsEquipmentFexFsmTaskEntry 3 }

cucsEquipmentFexFsmTaskCompletion OBJECT-TYPE
    SYNTAX       CucsFsmCompletion
    MAX-ACCESS   read-only
    STATUS       current
    DESCRIPTION
        "Cisco UCS equipment:FexFsmTask:completion managed
        object property"
    ::= { cucsEquipmentFexFsmTaskEntry 4 }

cucsEquipmentFexFsmTaskFlags OBJECT-TYPE
    SYNTAX       CucsFsmFlags
    MAX-ACCESS   read-only
    STATUS       current
    DESCRIPTION
        "Cisco UCS equipment:FexFsmTask:flags managed object property"
    ::= { cucsEquipmentFexFsmTaskEntry 5 }

cucsEquipmentFexFsmTaskItem OBJECT-TYPE
    SYNTAX       CucsEquipmentFexFsmTaskItem
    MAX-ACCESS   read-only
    STATUS       current
    DESCRIPTION
        "Cisco UCS equipment:FexFsmTask:item managed object property"
    ::= { cucsEquipmentFexFsmTaskEntry 6 }

cucsEquipmentFexFsmTaskSeqId OBJECT-TYPE
    SYNTAX       Gauge32
    MAX-ACCESS   read-only
    STATUS       current
    DESCRIPTION
        "Cisco UCS equipment:FexFsmTask:seqId managed object property"
    ::= { cucsEquipmentFexFsmTaskEntry 7 }

cucsEquipmentFexPowerSummaryTable OBJECT-TYPE
    SYNTAX           SEQUENCE OF CucsEquipmentFexPowerSummaryEntry
    MAX-ACCESS       not-accessible
    STATUS           current
    DESCRIPTION
        "Cisco UCS equipment:FexPowerSummary managed object table"
    ::= { cucsEquipmentObjects 24 }

cucsEquipmentFexPowerSummaryEntry OBJECT-TYPE
    SYNTAX           CucsEquipmentFexPowerSummaryEntry
    MAX-ACCESS       not-accessible
    STATUS           current
    DESCRIPTION
        "Entry for the cucsEquipmentFexPowerSummaryTable table."
    INDEX { cucsEquipmentFexPowerSummaryInstanceId }
    ::= { cucsEquipmentFexPowerSummaryTable 1 }

CucsEquipmentFexPowerSummaryEntry ::= SEQUENCE {
    cucsEquipmentFexPowerSummaryInstanceId                           CucsManagedObjectId,
    cucsEquipmentFexPowerSummaryDn                                   CucsManagedObjectDn,
    cucsEquipmentFexPowerSummaryRn                                   SnmpAdminString,
    cucsEquipmentFexPowerSummaryModulePower                          INTEGER,
    cucsEquipmentFexPowerSummaryModulePowerAvg                       INTEGER,
    cucsEquipmentFexPowerSummaryModulePowerMax                       INTEGER,
    cucsEquipmentFexPowerSummaryModulePowerMin                       INTEGER,
    cucsEquipmentFexPowerSummaryAvailablePower                       INTEGER,
    cucsEquipmentFexPowerSummaryAvailablePowerAvg                    INTEGER,
    cucsEquipmentFexPowerSummaryAvailablePowerMax                    INTEGER,
    cucsEquipmentFexPowerSummaryAvailablePowerMin                    INTEGER,
    cucsEquipmentFexPowerSummaryIntervals                            Gauge32,
    cucsEquipmentFexPowerSummaryReservedPower                        INTEGER,
    cucsEquipmentFexPowerSummaryReservedPowerAvg                     INTEGER,
    cucsEquipmentFexPowerSummaryReservedPowerMax                     INTEGER,
    cucsEquipmentFexPowerSummaryReservedPowerMin                     INTEGER,
    cucsEquipmentFexPowerSummarySuspect                              TruthValue,
    cucsEquipmentFexPowerSummaryThresholded                          CucsEquipmentFexPowerSummaryThresholded,
    cucsEquipmentFexPowerSummaryTimeCollected                        DateAndTime,
    cucsEquipmentFexPowerSummaryTotalPower                           INTEGER,
    cucsEquipmentFexPowerSummaryTotalPowerAvg                        INTEGER,
    cucsEquipmentFexPowerSummaryTotalPowerMax                        INTEGER,
    cucsEquipmentFexPowerSummaryTotalPowerMin                        INTEGER,
    cucsEquipmentFexPowerSummaryUpdate                               Gauge32
}

cucsEquipmentFexPowerSummaryInstanceId OBJECT-TYPE
    SYNTAX       CucsManagedObjectId
    MAX-ACCESS   not-accessible
    STATUS       current
    DESCRIPTION
        "Instance identifier of the managed object."
    ::= { cucsEquipmentFexPowerSummaryEntry 1 }

cucsEquipmentFexPowerSummaryDn OBJECT-TYPE
    SYNTAX       CucsManagedObjectDn
    MAX-ACCESS   read-only
    STATUS       current
    DESCRIPTION
        "Cisco UCS equipment:FexPowerSummary:dn managed object property"
    ::= { cucsEquipmentFexPowerSummaryEntry 2 }

cucsEquipmentFexPowerSummaryRn OBJECT-TYPE
    SYNTAX       SnmpAdminString
    MAX-ACCESS   read-only
    STATUS       current
    DESCRIPTION
        "Cisco UCS equipment:FexPowerSummary:rn managed object property"
    ::= { cucsEquipmentFexPowerSummaryEntry 3 }

cucsEquipmentFexPowerSummaryModulePower OBJECT-TYPE
    SYNTAX       INTEGER
    MAX-ACCESS   read-only
    STATUS       current
    DESCRIPTION
        "Cisco UCS equipment:FexPowerSummary:ModulePower
        managed object property"
    ::= { cucsEquipmentFexPowerSummaryEntry 4 }

cucsEquipmentFexPowerSummaryModulePowerAvg OBJECT-TYPE
    SYNTAX       INTEGER
    MAX-ACCESS   read-only
    STATUS       current
    DESCRIPTION
        "Cisco UCS equipment:FexPowerSummary:ModulePowerAvg
        managed object property"
    ::= { cucsEquipmentFexPowerSummaryEntry 5 }

cucsEquipmentFexPowerSummaryModulePowerMax OBJECT-TYPE
    SYNTAX       INTEGER
    MAX-ACCESS   read-only
    STATUS       current
    DESCRIPTION
        "Cisco UCS equipment:FexPowerSummary:ModulePowerMax
        managed object property"
    ::= { cucsEquipmentFexPowerSummaryEntry 6 }

cucsEquipmentFexPowerSummaryModulePowerMin OBJECT-TYPE
    SYNTAX       INTEGER
    MAX-ACCESS   read-only
    STATUS       current
    DESCRIPTION
        "Cisco UCS equipment:FexPowerSummary:ModulePowerMin
        managed object property"
    ::= { cucsEquipmentFexPowerSummaryEntry 7 }

cucsEquipmentFexPowerSummaryAvailablePower OBJECT-TYPE
    SYNTAX       INTEGER
    MAX-ACCESS   read-only
    STATUS       current
    DESCRIPTION
        "Cisco UCS equipment:FexPowerSummary:availablePower
        managed object property"
    ::= { cucsEquipmentFexPowerSummaryEntry 8 }

cucsEquipmentFexPowerSummaryAvailablePowerAvg OBJECT-TYPE
    SYNTAX       INTEGER
    MAX-ACCESS   read-only
    STATUS       current
    DESCRIPTION
        "Cisco UCS equipment:FexPowerSummary:availablePowerAvg
        managed object property"
    ::= { cucsEquipmentFexPowerSummaryEntry 9 }

cucsEquipmentFexPowerSummaryAvailablePowerMax OBJECT-TYPE
    SYNTAX       INTEGER
    MAX-ACCESS   read-only
    STATUS       current
    DESCRIPTION
        "Cisco UCS equipment:FexPowerSummary:availablePowerMax
        managed object property"
    ::= { cucsEquipmentFexPowerSummaryEntry 10 }

cucsEquipmentFexPowerSummaryAvailablePowerMin OBJECT-TYPE
    SYNTAX       INTEGER
    MAX-ACCESS   read-only
    STATUS       current
    DESCRIPTION
        "Cisco UCS equipment:FexPowerSummary:availablePowerMin
        managed object property"
    ::= { cucsEquipmentFexPowerSummaryEntry 11 }

cucsEquipmentFexPowerSummaryIntervals OBJECT-TYPE
    SYNTAX       Gauge32
    MAX-ACCESS   read-only
    STATUS       current
    DESCRIPTION
        "Cisco UCS equipment:FexPowerSummary:intervals
        managed object property"
    ::= { cucsEquipmentFexPowerSummaryEntry 12 }

cucsEquipmentFexPowerSummaryReservedPower OBJECT-TYPE
    SYNTAX       INTEGER
    MAX-ACCESS   read-only
    STATUS       current
    DESCRIPTION
        "Cisco UCS equipment:FexPowerSummary:reservedPower
        managed object property"
    ::= { cucsEquipmentFexPowerSummaryEntry 13 }

cucsEquipmentFexPowerSummaryReservedPowerAvg OBJECT-TYPE
    SYNTAX       INTEGER
    MAX-ACCESS   read-only
    STATUS       current
    DESCRIPTION
        "Cisco UCS equipment:FexPowerSummary:reservedPowerAvg
        managed object property"
    ::= { cucsEquipmentFexPowerSummaryEntry 14 }

cucsEquipmentFexPowerSummaryReservedPowerMax OBJECT-TYPE
    SYNTAX       INTEGER
    MAX-ACCESS   read-only
    STATUS       current
    DESCRIPTION
        "Cisco UCS equipment:FexPowerSummary:reservedPowerMax
        managed object property"
    ::= { cucsEquipmentFexPowerSummaryEntry 15 }

cucsEquipmentFexPowerSummaryReservedPowerMin OBJECT-TYPE
    SYNTAX       INTEGER
    MAX-ACCESS   read-only
    STATUS       current
    DESCRIPTION
        "Cisco UCS equipment:FexPowerSummary:reservedPowerMin
        managed object property"
    ::= { cucsEquipmentFexPowerSummaryEntry 16 }

cucsEquipmentFexPowerSummarySuspect OBJECT-TYPE
    SYNTAX       TruthValue
    MAX-ACCESS   read-only
    STATUS       current
    DESCRIPTION
        "Cisco UCS equipment:FexPowerSummary:suspect managed
        object property"
    ::= { cucsEquipmentFexPowerSummaryEntry 17 }

cucsEquipmentFexPowerSummaryThresholded OBJECT-TYPE
    SYNTAX       CucsEquipmentFexPowerSummaryThresholded
    MAX-ACCESS   read-only
    STATUS       current
    DESCRIPTION
        "Cisco UCS equipment:FexPowerSummary:thresholded
        managed object property"
    ::= { cucsEquipmentFexPowerSummaryEntry 18 }

cucsEquipmentFexPowerSummaryTimeCollected OBJECT-TYPE
    SYNTAX       DateAndTime
    MAX-ACCESS   read-only
    STATUS       current
    DESCRIPTION
        "Cisco UCS equipment:FexPowerSummary:timeCollected
        managed object property"
    ::= { cucsEquipmentFexPowerSummaryEntry 19 }

cucsEquipmentFexPowerSummaryTotalPower OBJECT-TYPE
    SYNTAX       INTEGER
    MAX-ACCESS   read-only
    STATUS       current
    DESCRIPTION
        "Cisco UCS equipment:FexPowerSummary:totalPower
        managed object property"
    ::= { cucsEquipmentFexPowerSummaryEntry 20 }

cucsEquipmentFexPowerSummaryTotalPowerAvg OBJECT-TYPE
    SYNTAX       INTEGER
    MAX-ACCESS   read-only
    STATUS       current
    DESCRIPTION
        "Cisco UCS equipment:FexPowerSummary:totalPowerAvg
        managed object property"
    ::= { cucsEquipmentFexPowerSummaryEntry 21 }

cucsEquipmentFexPowerSummaryTotalPowerMax OBJECT-TYPE
    SYNTAX       INTEGER
    MAX-ACCESS   read-only
    STATUS       current
    DESCRIPTION
        "Cisco UCS equipment:FexPowerSummary:totalPowerMax
        managed object property"
    ::= { cucsEquipmentFexPowerSummaryEntry 22 }

cucsEquipmentFexPowerSummaryTotalPowerMin OBJECT-TYPE
    SYNTAX       INTEGER
    MAX-ACCESS   read-only
    STATUS       current
    DESCRIPTION
        "Cisco UCS equipment:FexPowerSummary:totalPowerMin
        managed object property"
    ::= { cucsEquipmentFexPowerSummaryEntry 23 }

cucsEquipmentFexPowerSummaryUpdate OBJECT-TYPE
    SYNTAX       Gauge32
    MAX-ACCESS   read-only
    STATUS       current
    DESCRIPTION
        "Cisco UCS equipment:FexPowerSummary:update managed
        object property"
    ::= { cucsEquipmentFexPowerSummaryEntry 24 }

cucsEquipmentFexPowerSummaryHistTable OBJECT-TYPE
    SYNTAX           SEQUENCE OF CucsEquipmentFexPowerSummaryHistEntry
    MAX-ACCESS       not-accessible
    STATUS           current
    DESCRIPTION
        "Cisco UCS equipment:FexPowerSummaryHist managed object table"
    ::= { cucsEquipmentObjects 25 }

cucsEquipmentFexPowerSummaryHistEntry OBJECT-TYPE
    SYNTAX           CucsEquipmentFexPowerSummaryHistEntry
    MAX-ACCESS       not-accessible
    STATUS           current
    DESCRIPTION
        "Entry for the cucsEquipmentFexPowerSummaryHistTable table."
    INDEX { cucsEquipmentFexPowerSummaryHistInstanceId }
    ::= { cucsEquipmentFexPowerSummaryHistTable 1 }

CucsEquipmentFexPowerSummaryHistEntry ::= SEQUENCE {
    cucsEquipmentFexPowerSummaryHistInstanceId                       CucsManagedObjectId,
    cucsEquipmentFexPowerSummaryHistDn                               CucsManagedObjectDn,
    cucsEquipmentFexPowerSummaryHistRn                               SnmpAdminString,
    cucsEquipmentFexPowerSummaryHistModulePower                      INTEGER,
    cucsEquipmentFexPowerSummaryHistModulePowerAvg                   INTEGER,
    cucsEquipmentFexPowerSummaryHistModulePowerMax                   INTEGER,
    cucsEquipmentFexPowerSummaryHistModulePowerMin                   INTEGER,
    cucsEquipmentFexPowerSummaryHistAvailablePower                   INTEGER,
    cucsEquipmentFexPowerSummaryHistAvailablePowerAvg                INTEGER,
    cucsEquipmentFexPowerSummaryHistAvailablePowerMax                INTEGER,
    cucsEquipmentFexPowerSummaryHistAvailablePowerMin                INTEGER,
    cucsEquipmentFexPowerSummaryHistId                               Unsigned64,
    cucsEquipmentFexPowerSummaryHistMostRecent                       TruthValue,
    cucsEquipmentFexPowerSummaryHistReservedPower                    INTEGER,
    cucsEquipmentFexPowerSummaryHistReservedPowerAvg                 INTEGER,
    cucsEquipmentFexPowerSummaryHistReservedPowerMax                 INTEGER,
    cucsEquipmentFexPowerSummaryHistReservedPowerMin                 INTEGER,
    cucsEquipmentFexPowerSummaryHistSuspect                          TruthValue,
    cucsEquipmentFexPowerSummaryHistThresholded                      CucsEquipmentFexPowerSummaryHistThresholded,
    cucsEquipmentFexPowerSummaryHistTimeCollected                    DateAndTime,
    cucsEquipmentFexPowerSummaryHistTotalPower                       INTEGER,
    cucsEquipmentFexPowerSummaryHistTotalPowerAvg                    INTEGER,
    cucsEquipmentFexPowerSummaryHistTotalPowerMax                    INTEGER,
    cucsEquipmentFexPowerSummaryHistTotalPowerMin                    INTEGER
}

cucsEquipmentFexPowerSummaryHistInstanceId OBJECT-TYPE
    SYNTAX       CucsManagedObjectId
    MAX-ACCESS   not-accessible
    STATUS       current
    DESCRIPTION
        "Instance identifier of the managed object."
    ::= { cucsEquipmentFexPowerSummaryHistEntry 1 }

cucsEquipmentFexPowerSummaryHistDn OBJECT-TYPE
    SYNTAX       CucsManagedObjectDn
    MAX-ACCESS   read-only
    STATUS       current
    DESCRIPTION
        "Cisco UCS equipment:FexPowerSummaryHist:dn managed
        object property"
    ::= { cucsEquipmentFexPowerSummaryHistEntry 2 }

cucsEquipmentFexPowerSummaryHistRn OBJECT-TYPE
    SYNTAX       SnmpAdminString
    MAX-ACCESS   read-only
    STATUS       current
    DESCRIPTION
        "Cisco UCS equipment:FexPowerSummaryHist:rn managed
        object property"
    ::= { cucsEquipmentFexPowerSummaryHistEntry 3 }

cucsEquipmentFexPowerSummaryHistModulePower OBJECT-TYPE
    SYNTAX       INTEGER
    MAX-ACCESS   read-only
    STATUS       current
    DESCRIPTION
        "Cisco UCS equipment:FexPowerSummaryHist:ModulePower
        managed object property"
    ::= { cucsEquipmentFexPowerSummaryHistEntry 4 }

cucsEquipmentFexPowerSummaryHistModulePowerAvg OBJECT-TYPE
    SYNTAX       INTEGER
    MAX-ACCESS   read-only
    STATUS       current
    DESCRIPTION
        "Cisco UCS equipment:FexPowerSummaryHist:ModulePowerAvg
        managed object property"
    ::= { cucsEquipmentFexPowerSummaryHistEntry 5 }

cucsEquipmentFexPowerSummaryHistModulePowerMax OBJECT-TYPE
    SYNTAX       INTEGER
    MAX-ACCESS   read-only
    STATUS       current
    DESCRIPTION
        "Cisco UCS equipment:FexPowerSummaryHist:ModulePowerMax
        managed object property"
    ::= { cucsEquipmentFexPowerSummaryHistEntry 6 }

cucsEquipmentFexPowerSummaryHistModulePowerMin OBJECT-TYPE
    SYNTAX       INTEGER
    MAX-ACCESS   read-only
    STATUS       current
    DESCRIPTION
        "Cisco UCS equipment:FexPowerSummaryHist:ModulePowerMin
        managed object property"
    ::= { cucsEquipmentFexPowerSummaryHistEntry 7 }

cucsEquipmentFexPowerSummaryHistAvailablePower OBJECT-TYPE
    SYNTAX       INTEGER
    MAX-ACCESS   read-only
    STATUS       current
    DESCRIPTION
        "Cisco UCS equipment:FexPowerSummaryHist:availablePower
        managed object property"
    ::= { cucsEquipmentFexPowerSummaryHistEntry 8 }

cucsEquipmentFexPowerSummaryHistAvailablePowerAvg OBJECT-TYPE
    SYNTAX       INTEGER
    MAX-ACCESS   read-only
    STATUS       current
    DESCRIPTION
        "Cisco UCS equipment:FexPowerSummaryHist:availablePowerAvg
        managed object property"
    ::= { cucsEquipmentFexPowerSummaryHistEntry 9 }

cucsEquipmentFexPowerSummaryHistAvailablePowerMax OBJECT-TYPE
    SYNTAX       INTEGER
    MAX-ACCESS   read-only
    STATUS       current
    DESCRIPTION
        "Cisco UCS equipment:FexPowerSummaryHist:availablePowerMax
        managed object property"
    ::= { cucsEquipmentFexPowerSummaryHistEntry 10 }

cucsEquipmentFexPowerSummaryHistAvailablePowerMin OBJECT-TYPE
    SYNTAX       INTEGER
    MAX-ACCESS   read-only
    STATUS       current
    DESCRIPTION
        "Cisco UCS equipment:FexPowerSummaryHist:availablePowerMin
        managed object property"
    ::= { cucsEquipmentFexPowerSummaryHistEntry 11 }

cucsEquipmentFexPowerSummaryHistId OBJECT-TYPE
    SYNTAX       Unsigned64
    MAX-ACCESS   read-only
    STATUS       current
    DESCRIPTION
        "Cisco UCS equipment:FexPowerSummaryHist:id managed
        object property"
    ::= { cucsEquipmentFexPowerSummaryHistEntry 12 }

cucsEquipmentFexPowerSummaryHistMostRecent OBJECT-TYPE
    SYNTAX       TruthValue
    MAX-ACCESS   read-only
    STATUS       current
    DESCRIPTION
        "Cisco UCS equipment:FexPowerSummaryHist:mostRecent
        managed object property"
    ::= { cucsEquipmentFexPowerSummaryHistEntry 13 }

cucsEquipmentFexPowerSummaryHistReservedPower OBJECT-TYPE
    SYNTAX       INTEGER
    MAX-ACCESS   read-only
    STATUS       current
    DESCRIPTION
        "Cisco UCS equipment:FexPowerSummaryHist:reservedPower
        managed object property"
    ::= { cucsEquipmentFexPowerSummaryHistEntry 14 }

cucsEquipmentFexPowerSummaryHistReservedPowerAvg OBJECT-TYPE
    SYNTAX       INTEGER
    MAX-ACCESS   read-only
    STATUS       current
    DESCRIPTION
        "Cisco UCS equipment:FexPowerSummaryHist:reservedPowerAvg
        managed object property"
    ::= { cucsEquipmentFexPowerSummaryHistEntry 15 }

cucsEquipmentFexPowerSummaryHistReservedPowerMax OBJECT-TYPE
    SYNTAX       INTEGER
    MAX-ACCESS   read-only
    STATUS       current
    DESCRIPTION
        "Cisco UCS equipment:FexPowerSummaryHist:reservedPowerMax
        managed object property"
    ::= { cucsEquipmentFexPowerSummaryHistEntry 16 }

cucsEquipmentFexPowerSummaryHistReservedPowerMin OBJECT-TYPE
    SYNTAX       INTEGER
    MAX-ACCESS   read-only
    STATUS       current
    DESCRIPTION
        "Cisco UCS equipment:FexPowerSummaryHist:reservedPowerMin
        managed object property"
    ::= { cucsEquipmentFexPowerSummaryHistEntry 17 }

cucsEquipmentFexPowerSummaryHistSuspect OBJECT-TYPE
    SYNTAX       TruthValue
    MAX-ACCESS   read-only
    STATUS       current
    DESCRIPTION
        "Cisco UCS equipment:FexPowerSummaryHist:suspect
        managed object property"
    ::= { cucsEquipmentFexPowerSummaryHistEntry 18 }

cucsEquipmentFexPowerSummaryHistThresholded OBJECT-TYPE
    SYNTAX       CucsEquipmentFexPowerSummaryHistThresholded
    MAX-ACCESS   read-only
    STATUS       current
    DESCRIPTION
        "Cisco UCS equipment:FexPowerSummaryHist:thresholded
        managed object property"
    ::= { cucsEquipmentFexPowerSummaryHistEntry 19 }

cucsEquipmentFexPowerSummaryHistTimeCollected OBJECT-TYPE
    SYNTAX       DateAndTime
    MAX-ACCESS   read-only
    STATUS       current
    DESCRIPTION
        "Cisco UCS equipment:FexPowerSummaryHist:timeCollected
        managed object property"
    ::= { cucsEquipmentFexPowerSummaryHistEntry 20 }

cucsEquipmentFexPowerSummaryHistTotalPower OBJECT-TYPE
    SYNTAX       INTEGER
    MAX-ACCESS   read-only
    STATUS       current
    DESCRIPTION
        "Cisco UCS equipment:FexPowerSummaryHist:totalPower
        managed object property"
    ::= { cucsEquipmentFexPowerSummaryHistEntry 21 }

cucsEquipmentFexPowerSummaryHistTotalPowerAvg OBJECT-TYPE
    SYNTAX       INTEGER
    MAX-ACCESS   read-only
    STATUS       current
    DESCRIPTION
        "Cisco UCS equipment:FexPowerSummaryHist:totalPowerAvg
        managed object property"
    ::= { cucsEquipmentFexPowerSummaryHistEntry 22 }

cucsEquipmentFexPowerSummaryHistTotalPowerMax OBJECT-TYPE
    SYNTAX       INTEGER
    MAX-ACCESS   read-only
    STATUS       current
    DESCRIPTION
        "Cisco UCS equipment:FexPowerSummaryHist:totalPowerMax
        managed object property"
    ::= { cucsEquipmentFexPowerSummaryHistEntry 23 }

cucsEquipmentFexPowerSummaryHistTotalPowerMin OBJECT-TYPE
    SYNTAX       INTEGER
    MAX-ACCESS   read-only
    STATUS       current
    DESCRIPTION
        "Cisco UCS equipment:FexPowerSummaryHist:totalPowerMin
        managed object property"
    ::= { cucsEquipmentFexPowerSummaryHistEntry 24 }

cucsEquipmentFexPsuInputStatsTable OBJECT-TYPE
    SYNTAX           SEQUENCE OF CucsEquipmentFexPsuInputStatsEntry
    MAX-ACCESS       not-accessible
    STATUS           current
    DESCRIPTION
        "Cisco UCS equipment:FexPsuInputStats managed object table"
    ::= { cucsEquipmentObjects 26 }

cucsEquipmentFexPsuInputStatsEntry OBJECT-TYPE
    SYNTAX           CucsEquipmentFexPsuInputStatsEntry
    MAX-ACCESS       not-accessible
    STATUS           current
    DESCRIPTION
        "Entry for the cucsEquipmentFexPsuInputStatsTable table."
    INDEX { cucsEquipmentFexPsuInputStatsInstanceId }
    ::= { cucsEquipmentFexPsuInputStatsTable 1 }

CucsEquipmentFexPsuInputStatsEntry ::= SEQUENCE {
    cucsEquipmentFexPsuInputStatsInstanceId                          CucsManagedObjectId,
    cucsEquipmentFexPsuInputStatsDn                                  CucsManagedObjectDn,
    cucsEquipmentFexPsuInputStatsRn                                  SnmpAdminString,
    cucsEquipmentFexPsuInputStatsCurrent                             INTEGER,
    cucsEquipmentFexPsuInputStatsCurrentAvg                          INTEGER,
    cucsEquipmentFexPsuInputStatsCurrentMax                          INTEGER,
    cucsEquipmentFexPsuInputStatsCurrentMin                          INTEGER,
    cucsEquipmentFexPsuInputStatsInputStatus                         SnmpAdminString,
    cucsEquipmentFexPsuInputStatsIntervals                           Gauge32,
    cucsEquipmentFexPsuInputStatsPower                               INTEGER,
    cucsEquipmentFexPsuInputStatsPowerAvg                            INTEGER,
    cucsEquipmentFexPsuInputStatsPowerMax                            INTEGER,
    cucsEquipmentFexPsuInputStatsPowerMin                            INTEGER,
    cucsEquipmentFexPsuInputStatsSuspect                             TruthValue,
    cucsEquipmentFexPsuInputStatsThresholded                         CucsEquipmentFexPsuInputStatsThresholded,
    cucsEquipmentFexPsuInputStatsTimeCollected                       DateAndTime,
    cucsEquipmentFexPsuInputStatsUpdate                              Gauge32,
    cucsEquipmentFexPsuInputStatsVoltage                             INTEGER,
    cucsEquipmentFexPsuInputStatsVoltageAvg                          INTEGER,
    cucsEquipmentFexPsuInputStatsVoltageMax                          INTEGER,
    cucsEquipmentFexPsuInputStatsVoltageMin                          INTEGER
}

cucsEquipmentFexPsuInputStatsInstanceId OBJECT-TYPE
    SYNTAX       CucsManagedObjectId
    MAX-ACCESS   not-accessible
    STATUS       current
    DESCRIPTION
        "Instance identifier of the managed object."
    ::= { cucsEquipmentFexPsuInputStatsEntry 1 }

cucsEquipmentFexPsuInputStatsDn OBJECT-TYPE
    SYNTAX       CucsManagedObjectDn
    MAX-ACCESS   read-only
    STATUS       current
    DESCRIPTION
        "Cisco UCS equipment:FexPsuInputStats:dn managed object property"
    ::= { cucsEquipmentFexPsuInputStatsEntry 2 }

cucsEquipmentFexPsuInputStatsRn OBJECT-TYPE
    SYNTAX       SnmpAdminString
    MAX-ACCESS   read-only
    STATUS       current
    DESCRIPTION
        "Cisco UCS equipment:FexPsuInputStats:rn managed object property"
    ::= { cucsEquipmentFexPsuInputStatsEntry 3 }

cucsEquipmentFexPsuInputStatsCurrent OBJECT-TYPE
    SYNTAX       INTEGER
    MAX-ACCESS   read-only
    STATUS       current
    DESCRIPTION
        "Cisco UCS equipment:FexPsuInputStats:current managed
        object property"
    ::= { cucsEquipmentFexPsuInputStatsEntry 4 }

cucsEquipmentFexPsuInputStatsCurrentAvg OBJECT-TYPE
    SYNTAX       INTEGER
    MAX-ACCESS   read-only
    STATUS       current
    DESCRIPTION
        "Cisco UCS equipment:FexPsuInputStats:currentAvg
        managed object property"
    ::= { cucsEquipmentFexPsuInputStatsEntry 5 }

cucsEquipmentFexPsuInputStatsCurrentMax OBJECT-TYPE
    SYNTAX       INTEGER
    MAX-ACCESS   read-only
    STATUS       current
    DESCRIPTION
        "Cisco UCS equipment:FexPsuInputStats:currentMax
        managed object property"
    ::= { cucsEquipmentFexPsuInputStatsEntry 6 }

cucsEquipmentFexPsuInputStatsCurrentMin OBJECT-TYPE
    SYNTAX       INTEGER
    MAX-ACCESS   read-only
    STATUS       current
    DESCRIPTION
        "Cisco UCS equipment:FexPsuInputStats:currentMin
        managed object property"
    ::= { cucsEquipmentFexPsuInputStatsEntry 7 }

cucsEquipmentFexPsuInputStatsInputStatus OBJECT-TYPE
    SYNTAX       SnmpAdminString
    MAX-ACCESS   read-only
    STATUS       current
    DESCRIPTION
        "Cisco UCS equipment:FexPsuInputStats:inputStatus
        managed object property"
    ::= { cucsEquipmentFexPsuInputStatsEntry 8 }

cucsEquipmentFexPsuInputStatsIntervals OBJECT-TYPE
    SYNTAX       Gauge32
    MAX-ACCESS   read-only
    STATUS       current
    DESCRIPTION
        "Cisco UCS equipment:FexPsuInputStats:intervals
        managed object property"
    ::= { cucsEquipmentFexPsuInputStatsEntry 9 }

cucsEquipmentFexPsuInputStatsPower OBJECT-TYPE
    SYNTAX       INTEGER
    MAX-ACCESS   read-only
    STATUS       current
    DESCRIPTION
        "Cisco UCS equipment:FexPsuInputStats:power managed
        object property"
    ::= { cucsEquipmentFexPsuInputStatsEntry 10 }

cucsEquipmentFexPsuInputStatsPowerAvg OBJECT-TYPE
    SYNTAX       INTEGER
    MAX-ACCESS   read-only
    STATUS       current
    DESCRIPTION
        "Cisco UCS equipment:FexPsuInputStats:powerAvg
        managed object property"
    ::= { cucsEquipmentFexPsuInputStatsEntry 11 }

cucsEquipmentFexPsuInputStatsPowerMax OBJECT-TYPE
    SYNTAX       INTEGER
    MAX-ACCESS   read-only
    STATUS       current
    DESCRIPTION
        "Cisco UCS equipment:FexPsuInputStats:powerMax
        managed object property"
    ::= { cucsEquipmentFexPsuInputStatsEntry 12 }

cucsEquipmentFexPsuInputStatsPowerMin OBJECT-TYPE
    SYNTAX       INTEGER
    MAX-ACCESS   read-only
    STATUS       current
    DESCRIPTION
        "Cisco UCS equipment:FexPsuInputStats:powerMin
        managed object property"
    ::= { cucsEquipmentFexPsuInputStatsEntry 13 }

cucsEquipmentFexPsuInputStatsSuspect OBJECT-TYPE
    SYNTAX       TruthValue
    MAX-ACCESS   read-only
    STATUS       current
    DESCRIPTION
        "Cisco UCS equipment:FexPsuInputStats:suspect managed
        object property"
    ::= { cucsEquipmentFexPsuInputStatsEntry 14 }

cucsEquipmentFexPsuInputStatsThresholded OBJECT-TYPE
    SYNTAX       CucsEquipmentFexPsuInputStatsThresholded
    MAX-ACCESS   read-only
    STATUS       current
    DESCRIPTION
        "Cisco UCS equipment:FexPsuInputStats:thresholded
        managed object property"
    ::= { cucsEquipmentFexPsuInputStatsEntry 15 }

cucsEquipmentFexPsuInputStatsTimeCollected OBJECT-TYPE
    SYNTAX       DateAndTime
    MAX-ACCESS   read-only
    STATUS       current
    DESCRIPTION
        "Cisco UCS equipment:FexPsuInputStats:timeCollected
        managed object property"
    ::= { cucsEquipmentFexPsuInputStatsEntry 16 }

cucsEquipmentFexPsuInputStatsUpdate OBJECT-TYPE
    SYNTAX       Gauge32
    MAX-ACCESS   read-only
    STATUS       current
    DESCRIPTION
        "Cisco UCS equipment:FexPsuInputStats:update managed
        object property"
    ::= { cucsEquipmentFexPsuInputStatsEntry 17 }

cucsEquipmentFexPsuInputStatsVoltage OBJECT-TYPE
    SYNTAX       INTEGER
    MAX-ACCESS   read-only
    STATUS       current
    DESCRIPTION
        "Cisco UCS equipment:FexPsuInputStats:voltage managed
        object property"
    ::= { cucsEquipmentFexPsuInputStatsEntry 18 }

cucsEquipmentFexPsuInputStatsVoltageAvg OBJECT-TYPE
    SYNTAX       INTEGER
    MAX-ACCESS   read-only
    STATUS       current
    DESCRIPTION
        "Cisco UCS equipment:FexPsuInputStats:voltageAvg
        managed object property"
    ::= { cucsEquipmentFexPsuInputStatsEntry 19 }

cucsEquipmentFexPsuInputStatsVoltageMax OBJECT-TYPE
    SYNTAX       INTEGER
    MAX-ACCESS   read-only
    STATUS       current
    DESCRIPTION
        "Cisco UCS equipment:FexPsuInputStats:voltageMax
        managed object property"
    ::= { cucsEquipmentFexPsuInputStatsEntry 20 }

cucsEquipmentFexPsuInputStatsVoltageMin OBJECT-TYPE
    SYNTAX       INTEGER
    MAX-ACCESS   read-only
    STATUS       current
    DESCRIPTION
        "Cisco UCS equipment:FexPsuInputStats:voltageMin
        managed object property"
    ::= { cucsEquipmentFexPsuInputStatsEntry 21 }

cucsEquipmentFexPsuInputStatsHistTable OBJECT-TYPE
    SYNTAX           SEQUENCE OF CucsEquipmentFexPsuInputStatsHistEntry
    MAX-ACCESS       not-accessible
    STATUS           current
    DESCRIPTION
        "Cisco UCS equipment:FexPsuInputStatsHist managed object table"
    ::= { cucsEquipmentObjects 27 }

cucsEquipmentFexPsuInputStatsHistEntry OBJECT-TYPE
    SYNTAX           CucsEquipmentFexPsuInputStatsHistEntry
    MAX-ACCESS       not-accessible
    STATUS           current
    DESCRIPTION
        "Entry for the cucsEquipmentFexPsuInputStatsHistTable table."
    INDEX { cucsEquipmentFexPsuInputStatsHistInstanceId }
    ::= { cucsEquipmentFexPsuInputStatsHistTable 1 }

CucsEquipmentFexPsuInputStatsHistEntry ::= SEQUENCE {
    cucsEquipmentFexPsuInputStatsHistInstanceId                      CucsManagedObjectId,
    cucsEquipmentFexPsuInputStatsHistDn                              CucsManagedObjectDn,
    cucsEquipmentFexPsuInputStatsHistRn                              SnmpAdminString,
    cucsEquipmentFexPsuInputStatsHistCurrent                         INTEGER,
    cucsEquipmentFexPsuInputStatsHistCurrentAvg                      INTEGER,
    cucsEquipmentFexPsuInputStatsHistCurrentMax                      INTEGER,
    cucsEquipmentFexPsuInputStatsHistCurrentMin                      INTEGER,
    cucsEquipmentFexPsuInputStatsHistId                              Unsigned64,
    cucsEquipmentFexPsuInputStatsHistMostRecent                      TruthValue,
    cucsEquipmentFexPsuInputStatsHistPower                           INTEGER,
    cucsEquipmentFexPsuInputStatsHistPowerAvg                        INTEGER,
    cucsEquipmentFexPsuInputStatsHistPowerMax                        INTEGER,
    cucsEquipmentFexPsuInputStatsHistPowerMin                        INTEGER,
    cucsEquipmentFexPsuInputStatsHistSuspect                         TruthValue,
    cucsEquipmentFexPsuInputStatsHistThresholded                     CucsEquipmentFexPsuInputStatsHistThresholded,
    cucsEquipmentFexPsuInputStatsHistTimeCollected                   DateAndTime,
    cucsEquipmentFexPsuInputStatsHistVoltage                         INTEGER,
    cucsEquipmentFexPsuInputStatsHistVoltageAvg                      INTEGER,
    cucsEquipmentFexPsuInputStatsHistVoltageMax                      INTEGER,
    cucsEquipmentFexPsuInputStatsHistVoltageMin                      INTEGER
}

cucsEquipmentFexPsuInputStatsHistInstanceId OBJECT-TYPE
    SYNTAX       CucsManagedObjectId
    MAX-ACCESS   not-accessible
    STATUS       current
    DESCRIPTION
        "Instance identifier of the managed object."
    ::= { cucsEquipmentFexPsuInputStatsHistEntry 1 }

cucsEquipmentFexPsuInputStatsHistDn OBJECT-TYPE
    SYNTAX       CucsManagedObjectDn
    MAX-ACCESS   read-only
    STATUS       current
    DESCRIPTION
        "Cisco UCS equipment:FexPsuInputStatsHist:dn managed
        object property"
    ::= { cucsEquipmentFexPsuInputStatsHistEntry 2 }

cucsEquipmentFexPsuInputStatsHistRn OBJECT-TYPE
    SYNTAX       SnmpAdminString
    MAX-ACCESS   read-only
    STATUS       current
    DESCRIPTION
        "Cisco UCS equipment:FexPsuInputStatsHist:rn managed
        object property"
    ::= { cucsEquipmentFexPsuInputStatsHistEntry 3 }

cucsEquipmentFexPsuInputStatsHistCurrent OBJECT-TYPE
    SYNTAX       INTEGER
    MAX-ACCESS   read-only
    STATUS       current
    DESCRIPTION
        "Cisco UCS equipment:FexPsuInputStatsHist:current
        managed object property"
    ::= { cucsEquipmentFexPsuInputStatsHistEntry 4 }

cucsEquipmentFexPsuInputStatsHistCurrentAvg OBJECT-TYPE
    SYNTAX       INTEGER
    MAX-ACCESS   read-only
    STATUS       current
    DESCRIPTION
        "Cisco UCS equipment:FexPsuInputStatsHist:currentAvg
        managed object property"
    ::= { cucsEquipmentFexPsuInputStatsHistEntry 5 }

cucsEquipmentFexPsuInputStatsHistCurrentMax OBJECT-TYPE
    SYNTAX       INTEGER
    MAX-ACCESS   read-only
    STATUS       current
    DESCRIPTION
        "Cisco UCS equipment:FexPsuInputStatsHist:currentMax
        managed object property"
    ::= { cucsEquipmentFexPsuInputStatsHistEntry 6 }

cucsEquipmentFexPsuInputStatsHistCurrentMin OBJECT-TYPE
    SYNTAX       INTEGER
    MAX-ACCESS   read-only
    STATUS       current
    DESCRIPTION
        "Cisco UCS equipment:FexPsuInputStatsHist:currentMin
        managed object property"
    ::= { cucsEquipmentFexPsuInputStatsHistEntry 7 }

cucsEquipmentFexPsuInputStatsHistId OBJECT-TYPE
    SYNTAX       Unsigned64
    MAX-ACCESS   read-only
    STATUS       current
    DESCRIPTION
        "Cisco UCS equipment:FexPsuInputStatsHist:id managed
        object property"
    ::= { cucsEquipmentFexPsuInputStatsHistEntry 8 }

cucsEquipmentFexPsuInputStatsHistMostRecent OBJECT-TYPE
    SYNTAX       TruthValue
    MAX-ACCESS   read-only
    STATUS       current
    DESCRIPTION
        "Cisco UCS equipment:FexPsuInputStatsHist:mostRecent
        managed object property"
    ::= { cucsEquipmentFexPsuInputStatsHistEntry 9 }

cucsEquipmentFexPsuInputStatsHistPower OBJECT-TYPE
    SYNTAX       INTEGER
    MAX-ACCESS   read-only
    STATUS       current
    DESCRIPTION
        "Cisco UCS equipment:FexPsuInputStatsHist:power
        managed object property"
    ::= { cucsEquipmentFexPsuInputStatsHistEntry 10 }

cucsEquipmentFexPsuInputStatsHistPowerAvg OBJECT-TYPE
    SYNTAX       INTEGER
    MAX-ACCESS   read-only
    STATUS       current
    DESCRIPTION
        "Cisco UCS equipment:FexPsuInputStatsHist:powerAvg
        managed object property"
    ::= { cucsEquipmentFexPsuInputStatsHistEntry 11 }

cucsEquipmentFexPsuInputStatsHistPowerMax OBJECT-TYPE
    SYNTAX       INTEGER
    MAX-ACCESS   read-only
    STATUS       current
    DESCRIPTION
        "Cisco UCS equipment:FexPsuInputStatsHist:powerMax
        managed object property"
    ::= { cucsEquipmentFexPsuInputStatsHistEntry 12 }

cucsEquipmentFexPsuInputStatsHistPowerMin OBJECT-TYPE
    SYNTAX       INTEGER
    MAX-ACCESS   read-only
    STATUS       current
    DESCRIPTION
        "Cisco UCS equipment:FexPsuInputStatsHist:powerMin
        managed object property"
    ::= { cucsEquipmentFexPsuInputStatsHistEntry 13 }

cucsEquipmentFexPsuInputStatsHistSuspect OBJECT-TYPE
    SYNTAX       TruthValue
    MAX-ACCESS   read-only
    STATUS       current
    DESCRIPTION
        "Cisco UCS equipment:FexPsuInputStatsHist:suspect
        managed object property"
    ::= { cucsEquipmentFexPsuInputStatsHistEntry 14 }

cucsEquipmentFexPsuInputStatsHistThresholded OBJECT-TYPE
    SYNTAX       CucsEquipmentFexPsuInputStatsHistThresholded
    MAX-ACCESS   read-only
    STATUS       current
    DESCRIPTION
        "Cisco UCS equipment:FexPsuInputStatsHist:thresholded
        managed object property"
    ::= { cucsEquipmentFexPsuInputStatsHistEntry 15 }

cucsEquipmentFexPsuInputStatsHistTimeCollected OBJECT-TYPE
    SYNTAX       DateAndTime
    MAX-ACCESS   read-only
    STATUS       current
    DESCRIPTION
        "Cisco UCS equipment:FexPsuInputStatsHist:timeCollected
        managed object property"
    ::= { cucsEquipmentFexPsuInputStatsHistEntry 16 }

cucsEquipmentFexPsuInputStatsHistVoltage OBJECT-TYPE
    SYNTAX       INTEGER
    MAX-ACCESS   read-only
    STATUS       current
    DESCRIPTION
        "Cisco UCS equipment:FexPsuInputStatsHist:voltage
        managed object property"
    ::= { cucsEquipmentFexPsuInputStatsHistEntry 17 }

cucsEquipmentFexPsuInputStatsHistVoltageAvg OBJECT-TYPE
    SYNTAX       INTEGER
    MAX-ACCESS   read-only
    STATUS       current
    DESCRIPTION
        "Cisco UCS equipment:FexPsuInputStatsHist:voltageAvg
        managed object property"
    ::= { cucsEquipmentFexPsuInputStatsHistEntry 18 }

cucsEquipmentFexPsuInputStatsHistVoltageMax OBJECT-TYPE
    SYNTAX       INTEGER
    MAX-ACCESS   read-only
    STATUS       current
    DESCRIPTION
        "Cisco UCS equipment:FexPsuInputStatsHist:voltageMax
        managed object property"
    ::= { cucsEquipmentFexPsuInputStatsHistEntry 19 }

cucsEquipmentFexPsuInputStatsHistVoltageMin OBJECT-TYPE
    SYNTAX       INTEGER
    MAX-ACCESS   read-only
    STATUS       current
    DESCRIPTION
        "Cisco UCS equipment:FexPsuInputStatsHist:voltageMin
        managed object property"
    ::= { cucsEquipmentFexPsuInputStatsHistEntry 20 }

cucsEquipmentFexSystemStatsTable OBJECT-TYPE
    SYNTAX           SEQUENCE OF CucsEquipmentFexSystemStatsEntry
    MAX-ACCESS       not-accessible
    STATUS           current
    DESCRIPTION
        "Cisco UCS equipment:FexSystemStats managed object table"
    ::= { cucsEquipmentObjects 164 }

cucsEquipmentFexSystemStatsEntry OBJECT-TYPE
    SYNTAX           CucsEquipmentFexSystemStatsEntry
    MAX-ACCESS       not-accessible
    STATUS           current
    DESCRIPTION
        "Entry for the cucsEquipmentFexSystemStatsTable table."
    INDEX { cucsEquipmentFexSystemStatsInstanceId }
    ::= { cucsEquipmentFexSystemStatsTable 1 }

CucsEquipmentFexSystemStatsEntry ::= SEQUENCE {
    cucsEquipmentFexSystemStatsInstanceId                            CucsManagedObjectId,
    cucsEquipmentFexSystemStatsDn                                    CucsManagedObjectDn,
    cucsEquipmentFexSystemStatsRn                                    SnmpAdminString,
    cucsEquipmentFexSystemStatsIntervals                             Gauge32,
    cucsEquipmentFexSystemStatsKernelMemFree                         Gauge32,
    cucsEquipmentFexSystemStatsKernelMemFreeAvg                      Gauge32,
    cucsEquipmentFexSystemStatsKernelMemFreeMax                      Gauge32,
    cucsEquipmentFexSystemStatsKernelMemFreeMin                      Gauge32,
    cucsEquipmentFexSystemStatsKernelMemTotal                        Gauge32,
    cucsEquipmentFexSystemStatsKernelMemTotalAvg                     Gauge32,
    cucsEquipmentFexSystemStatsKernelMemTotalMax                     Gauge32,
    cucsEquipmentFexSystemStatsKernelMemTotalMin                     Gauge32,
    cucsEquipmentFexSystemStatsLoad                                  SnmpAdminString,
    cucsEquipmentFexSystemStatsLoadAvg                               SnmpAdminString,
    cucsEquipmentFexSystemStatsLoadMax                               SnmpAdminString,
    cucsEquipmentFexSystemStatsLoadMin                               SnmpAdminString,
    cucsEquipmentFexSystemStatsMemAvailable                          Gauge32,
    cucsEquipmentFexSystemStatsMemAvailableAvg                       Gauge32,
    cucsEquipmentFexSystemStatsMemAvailableMax                       Gauge32,
    cucsEquipmentFexSystemStatsMemAvailableMin                       Gauge32,
    cucsEquipmentFexSystemStatsMemCached                             Gauge32,
    cucsEquipmentFexSystemStatsMemCachedAvg                          Gauge32,
    cucsEquipmentFexSystemStatsMemCachedMax                          Gauge32,
    cucsEquipmentFexSystemStatsMemCachedMin                          Gauge32,
    cucsEquipmentFexSystemStatsSuspect                               TruthValue,
    cucsEquipmentFexSystemStatsThresholded                           CucsEquipmentFexSystemStatsThresholded,
    cucsEquipmentFexSystemStatsTimeCollected                         DateAndTime,
    cucsEquipmentFexSystemStatsUpdate                                Gauge32
}

cucsEquipmentFexSystemStatsInstanceId OBJECT-TYPE
    SYNTAX       CucsManagedObjectId
    MAX-ACCESS   not-accessible
    STATUS       current
    DESCRIPTION
        "Instance identifier of the managed object."
    ::= { cucsEquipmentFexSystemStatsEntry 1 }

cucsEquipmentFexSystemStatsDn OBJECT-TYPE
    SYNTAX       CucsManagedObjectDn
    MAX-ACCESS   read-only
    STATUS       current
    DESCRIPTION
        "Cisco UCS equipment:FexSystemStats:dn managed object property"
    ::= { cucsEquipmentFexSystemStatsEntry 2 }

cucsEquipmentFexSystemStatsRn OBJECT-TYPE
    SYNTAX       SnmpAdminString
    MAX-ACCESS   read-only
    STATUS       current
    DESCRIPTION
        "Cisco UCS equipment:FexSystemStats:rn managed object property"
    ::= { cucsEquipmentFexSystemStatsEntry 3 }

cucsEquipmentFexSystemStatsIntervals OBJECT-TYPE
    SYNTAX       Gauge32
    MAX-ACCESS   read-only
    STATUS       current
    DESCRIPTION
        "Cisco UCS equipment:FexSystemStats:intervals managed
        object property"
    ::= { cucsEquipmentFexSystemStatsEntry 4 }

cucsEquipmentFexSystemStatsKernelMemFree OBJECT-TYPE
    SYNTAX       Gauge32
    MAX-ACCESS   read-only
    STATUS       current
    DESCRIPTION
        "Cisco UCS equipment:FexSystemStats:kernelMemFree
        managed object property"
    ::= { cucsEquipmentFexSystemStatsEntry 5 }

cucsEquipmentFexSystemStatsKernelMemFreeAvg OBJECT-TYPE
    SYNTAX       Gauge32
    MAX-ACCESS   read-only
    STATUS       current
    DESCRIPTION
        "Cisco UCS equipment:FexSystemStats:kernelMemFreeAvg
        managed object property"
    ::= { cucsEquipmentFexSystemStatsEntry 6 }

cucsEquipmentFexSystemStatsKernelMemFreeMax OBJECT-TYPE
    SYNTAX       Gauge32
    MAX-ACCESS   read-only
    STATUS       current
    DESCRIPTION
        "Cisco UCS equipment:FexSystemStats:kernelMemFreeMax
        managed object property"
    ::= { cucsEquipmentFexSystemStatsEntry 7 }

cucsEquipmentFexSystemStatsKernelMemFreeMin OBJECT-TYPE
    SYNTAX       Gauge32
    MAX-ACCESS   read-only
    STATUS       current
    DESCRIPTION
        "Cisco UCS equipment:FexSystemStats:kernelMemFreeMin
        managed object property"
    ::= { cucsEquipmentFexSystemStatsEntry 8 }

cucsEquipmentFexSystemStatsKernelMemTotal OBJECT-TYPE
    SYNTAX       Gauge32
    MAX-ACCESS   read-only
    STATUS       current
    DESCRIPTION
        "Cisco UCS equipment:FexSystemStats:kernelMemTotal
        managed object property"
    ::= { cucsEquipmentFexSystemStatsEntry 9 }

cucsEquipmentFexSystemStatsKernelMemTotalAvg OBJECT-TYPE
    SYNTAX       Gauge32
    MAX-ACCESS   read-only
    STATUS       current
    DESCRIPTION
        "Cisco UCS equipment:FexSystemStats:kernelMemTotalAvg
        managed object property"
    ::= { cucsEquipmentFexSystemStatsEntry 10 }

cucsEquipmentFexSystemStatsKernelMemTotalMax OBJECT-TYPE
    SYNTAX       Gauge32
    MAX-ACCESS   read-only
    STATUS       current
    DESCRIPTION
        "Cisco UCS equipment:FexSystemStats:kernelMemTotalMax
        managed object property"
    ::= { cucsEquipmentFexSystemStatsEntry 11 }

cucsEquipmentFexSystemStatsKernelMemTotalMin OBJECT-TYPE
    SYNTAX       Gauge32
    MAX-ACCESS   read-only
    STATUS       current
    DESCRIPTION
        "Cisco UCS equipment:FexSystemStats:kernelMemTotalMin
        managed object property"
    ::= { cucsEquipmentFexSystemStatsEntry 12 }

cucsEquipmentFexSystemStatsLoad OBJECT-TYPE
    SYNTAX       SnmpAdminString
    MAX-ACCESS   read-only
    STATUS       current
    DESCRIPTION
        "Cisco UCS equipment:FexSystemStats:load managed object property"
    ::= { cucsEquipmentFexSystemStatsEntry 13 }

cucsEquipmentFexSystemStatsLoadAvg OBJECT-TYPE
    SYNTAX       SnmpAdminString
    MAX-ACCESS   read-only
    STATUS       current
    DESCRIPTION
        "Cisco UCS equipment:FexSystemStats:loadAvg managed
        object property"
    ::= { cucsEquipmentFexSystemStatsEntry 14 }

cucsEquipmentFexSystemStatsLoadMax OBJECT-TYPE
    SYNTAX       SnmpAdminString
    MAX-ACCESS   read-only
    STATUS       current
    DESCRIPTION
        "Cisco UCS equipment:FexSystemStats:loadMax managed
        object property"
    ::= { cucsEquipmentFexSystemStatsEntry 15 }

cucsEquipmentFexSystemStatsLoadMin OBJECT-TYPE
    SYNTAX       SnmpAdminString
    MAX-ACCESS   read-only
    STATUS       current
    DESCRIPTION
        "Cisco UCS equipment:FexSystemStats:loadMin managed
        object property"
    ::= { cucsEquipmentFexSystemStatsEntry 16 }

cucsEquipmentFexSystemStatsMemAvailable OBJECT-TYPE
    SYNTAX       Gauge32
    MAX-ACCESS   read-only
    STATUS       current
    DESCRIPTION
        "Cisco UCS equipment:FexSystemStats:memAvailable
        managed object property"
    ::= { cucsEquipmentFexSystemStatsEntry 17 }

cucsEquipmentFexSystemStatsMemAvailableAvg OBJECT-TYPE
    SYNTAX       Gauge32
    MAX-ACCESS   read-only
    STATUS       current
    DESCRIPTION
        "Cisco UCS equipment:FexSystemStats:memAvailableAvg
        managed object property"
    ::= { cucsEquipmentFexSystemStatsEntry 18 }

cucsEquipmentFexSystemStatsMemAvailableMax OBJECT-TYPE
    SYNTAX       Gauge32
    MAX-ACCESS   read-only
    STATUS       current
    DESCRIPTION
        "Cisco UCS equipment:FexSystemStats:memAvailableMax
        managed object property"
    ::= { cucsEquipmentFexSystemStatsEntry 19 }

cucsEquipmentFexSystemStatsMemAvailableMin OBJECT-TYPE
    SYNTAX       Gauge32
    MAX-ACCESS   read-only
    STATUS       current
    DESCRIPTION
        "Cisco UCS equipment:FexSystemStats:memAvailableMin
        managed object property"
    ::= { cucsEquipmentFexSystemStatsEntry 20 }

cucsEquipmentFexSystemStatsMemCached OBJECT-TYPE
    SYNTAX       Gauge32
    MAX-ACCESS   read-only
    STATUS       current
    DESCRIPTION
        "Cisco UCS equipment:FexSystemStats:memCached managed
        object property"
    ::= { cucsEquipmentFexSystemStatsEntry 21 }

cucsEquipmentFexSystemStatsMemCachedAvg OBJECT-TYPE
    SYNTAX       Gauge32
    MAX-ACCESS   read-only
    STATUS       current
    DESCRIPTION
        "Cisco UCS equipment:FexSystemStats:memCachedAvg
        managed object property"
    ::= { cucsEquipmentFexSystemStatsEntry 22 }

cucsEquipmentFexSystemStatsMemCachedMax OBJECT-TYPE
    SYNTAX       Gauge32
    MAX-ACCESS   read-only
    STATUS       current
    DESCRIPTION
        "Cisco UCS equipment:FexSystemStats:memCachedMax
        managed object property"
    ::= { cucsEquipmentFexSystemStatsEntry 23 }

cucsEquipmentFexSystemStatsMemCachedMin OBJECT-TYPE
    SYNTAX       Gauge32
    MAX-ACCESS   read-only
    STATUS       current
    DESCRIPTION
        "Cisco UCS equipment:FexSystemStats:memCachedMin
        managed object property"
    ::= { cucsEquipmentFexSystemStatsEntry 24 }

cucsEquipmentFexSystemStatsSuspect OBJECT-TYPE
    SYNTAX       TruthValue
    MAX-ACCESS   read-only
    STATUS       current
    DESCRIPTION
        "Cisco UCS equipment:FexSystemStats:suspect managed
        object property"
    ::= { cucsEquipmentFexSystemStatsEntry 25 }

cucsEquipmentFexSystemStatsThresholded OBJECT-TYPE
    SYNTAX       CucsEquipmentFexSystemStatsThresholded
    MAX-ACCESS   read-only
    STATUS       current
    DESCRIPTION
        "Cisco UCS equipment:FexSystemStats:thresholded
        managed object property"
    ::= { cucsEquipmentFexSystemStatsEntry 26 }

cucsEquipmentFexSystemStatsTimeCollected OBJECT-TYPE
    SYNTAX       DateAndTime
    MAX-ACCESS   read-only
    STATUS       current
    DESCRIPTION
        "Cisco UCS equipment:FexSystemStats:timeCollected
        managed object property"
    ::= { cucsEquipmentFexSystemStatsEntry 27 }

cucsEquipmentFexSystemStatsUpdate OBJECT-TYPE
    SYNTAX       Gauge32
    MAX-ACCESS   read-only
    STATUS       current
    DESCRIPTION
        "Cisco UCS equipment:FexSystemStats:update managed
        object property"
    ::= { cucsEquipmentFexSystemStatsEntry 28 }

cucsEquipmentFexSystemStatsHistTable OBJECT-TYPE
    SYNTAX           SEQUENCE OF CucsEquipmentFexSystemStatsHistEntry
    MAX-ACCESS       not-accessible
    STATUS           current
    DESCRIPTION
        "Cisco UCS equipment:FexSystemStatsHist managed object table"
    ::= { cucsEquipmentObjects 165 }

cucsEquipmentFexSystemStatsHistEntry OBJECT-TYPE
    SYNTAX           CucsEquipmentFexSystemStatsHistEntry
    MAX-ACCESS       not-accessible
    STATUS           current
    DESCRIPTION
        "Entry for the cucsEquipmentFexSystemStatsHistTable table."
    INDEX { cucsEquipmentFexSystemStatsHistInstanceId }
    ::= { cucsEquipmentFexSystemStatsHistTable 1 }

CucsEquipmentFexSystemStatsHistEntry ::= SEQUENCE {
    cucsEquipmentFexSystemStatsHistInstanceId                        CucsManagedObjectId,
    cucsEquipmentFexSystemStatsHistDn                                CucsManagedObjectDn,
    cucsEquipmentFexSystemStatsHistRn                                SnmpAdminString,
    cucsEquipmentFexSystemStatsHistId                                Unsigned64,
    cucsEquipmentFexSystemStatsHistKernelMemFree                     Gauge32,
    cucsEquipmentFexSystemStatsHistKernelMemFreeAvg                  Gauge32,
    cucsEquipmentFexSystemStatsHistKernelMemFreeMax                  Gauge32,
    cucsEquipmentFexSystemStatsHistKernelMemFreeMin                  Gauge32,
    cucsEquipmentFexSystemStatsHistKernelMemTotal                    Gauge32,
    cucsEquipmentFexSystemStatsHistKernelMemTotalAvg                 Gauge32,
    cucsEquipmentFexSystemStatsHistKernelMemTotalMax                 Gauge32,
    cucsEquipmentFexSystemStatsHistKernelMemTotalMin                 Gauge32,
    cucsEquipmentFexSystemStatsHistLoad                              SnmpAdminString,
    cucsEquipmentFexSystemStatsHistLoadAvg                           SnmpAdminString,
    cucsEquipmentFexSystemStatsHistLoadMax                           SnmpAdminString,
    cucsEquipmentFexSystemStatsHistLoadMin                           SnmpAdminString,
    cucsEquipmentFexSystemStatsHistMemAvailable                      Gauge32,
    cucsEquipmentFexSystemStatsHistMemAvailableAvg                   Gauge32,
    cucsEquipmentFexSystemStatsHistMemAvailableMax                   Gauge32,
    cucsEquipmentFexSystemStatsHistMemAvailableMin                   Gauge32,
    cucsEquipmentFexSystemStatsHistMemCached                         Gauge32,
    cucsEquipmentFexSystemStatsHistMemCachedAvg                      Gauge32,
    cucsEquipmentFexSystemStatsHistMemCachedMax                      Gauge32,
    cucsEquipmentFexSystemStatsHistMemCachedMin                      Gauge32,
    cucsEquipmentFexSystemStatsHistMostRecent                        TruthValue,
    cucsEquipmentFexSystemStatsHistSuspect                           TruthValue,
    cucsEquipmentFexSystemStatsHistThresholded                       CucsEquipmentFexSystemStatsHistThresholded,
    cucsEquipmentFexSystemStatsHistTimeCollected                     DateAndTime
}

cucsEquipmentFexSystemStatsHistInstanceId OBJECT-TYPE
    SYNTAX       CucsManagedObjectId
    MAX-ACCESS   not-accessible
    STATUS       current
    DESCRIPTION
        "Instance identifier of the managed object."
    ::= { cucsEquipmentFexSystemStatsHistEntry 1 }

cucsEquipmentFexSystemStatsHistDn OBJECT-TYPE
    SYNTAX       CucsManagedObjectDn
    MAX-ACCESS   read-only
    STATUS       current
    DESCRIPTION
        "Cisco UCS equipment:FexSystemStatsHist:dn managed
        object property"
    ::= { cucsEquipmentFexSystemStatsHistEntry 2 }

cucsEquipmentFexSystemStatsHistRn OBJECT-TYPE
    SYNTAX       SnmpAdminString
    MAX-ACCESS   read-only
    STATUS       current
    DESCRIPTION
        "Cisco UCS equipment:FexSystemStatsHist:rn managed
        object property"
    ::= { cucsEquipmentFexSystemStatsHistEntry 3 }

cucsEquipmentFexSystemStatsHistId OBJECT-TYPE
    SYNTAX       Unsigned64
    MAX-ACCESS   read-only
    STATUS       current
    DESCRIPTION
        "Cisco UCS equipment:FexSystemStatsHist:id managed
        object property"
    ::= { cucsEquipmentFexSystemStatsHistEntry 4 }

cucsEquipmentFexSystemStatsHistKernelMemFree OBJECT-TYPE
    SYNTAX       Gauge32
    MAX-ACCESS   read-only
    STATUS       current
    DESCRIPTION
        "Cisco UCS equipment:FexSystemStatsHist:kernelMemFree
        managed object property"
    ::= { cucsEquipmentFexSystemStatsHistEntry 5 }

cucsEquipmentFexSystemStatsHistKernelMemFreeAvg OBJECT-TYPE
    SYNTAX       Gauge32
    MAX-ACCESS   read-only
    STATUS       current
    DESCRIPTION
        "Cisco UCS equipment:FexSystemStatsHist:kernelMemFreeAvg
        managed object property"
    ::= { cucsEquipmentFexSystemStatsHistEntry 6 }

cucsEquipmentFexSystemStatsHistKernelMemFreeMax OBJECT-TYPE
    SYNTAX       Gauge32
    MAX-ACCESS   read-only
    STATUS       current
    DESCRIPTION
        "Cisco UCS equipment:FexSystemStatsHist:kernelMemFreeMax
        managed object property"
    ::= { cucsEquipmentFexSystemStatsHistEntry 7 }

cucsEquipmentFexSystemStatsHistKernelMemFreeMin OBJECT-TYPE
    SYNTAX       Gauge32
    MAX-ACCESS   read-only
    STATUS       current
    DESCRIPTION
        "Cisco UCS equipment:FexSystemStatsHist:kernelMemFreeMin
        managed object property"
    ::= { cucsEquipmentFexSystemStatsHistEntry 8 }

cucsEquipmentFexSystemStatsHistKernelMemTotal OBJECT-TYPE
    SYNTAX       Gauge32
    MAX-ACCESS   read-only
    STATUS       current
    DESCRIPTION
        "Cisco UCS equipment:FexSystemStatsHist:kernelMemTotal
        managed object property"
    ::= { cucsEquipmentFexSystemStatsHistEntry 9 }

cucsEquipmentFexSystemStatsHistKernelMemTotalAvg OBJECT-TYPE
    SYNTAX       Gauge32
    MAX-ACCESS   read-only
    STATUS       current
    DESCRIPTION
        "Cisco UCS equipment:FexSystemStatsHist:kernelMemTotalAvg
        managed object property"
    ::= { cucsEquipmentFexSystemStatsHistEntry 10 }

cucsEquipmentFexSystemStatsHistKernelMemTotalMax OBJECT-TYPE
    SYNTAX       Gauge32
    MAX-ACCESS   read-only
    STATUS       current
    DESCRIPTION
        "Cisco UCS equipment:FexSystemStatsHist:kernelMemTotalMax
        managed object property"
    ::= { cucsEquipmentFexSystemStatsHistEntry 11 }

cucsEquipmentFexSystemStatsHistKernelMemTotalMin OBJECT-TYPE
    SYNTAX       Gauge32
    MAX-ACCESS   read-only
    STATUS       current
    DESCRIPTION
        "Cisco UCS equipment:FexSystemStatsHist:kernelMemTotalMin
        managed object property"
    ::= { cucsEquipmentFexSystemStatsHistEntry 12 }

cucsEquipmentFexSystemStatsHistLoad OBJECT-TYPE
    SYNTAX       SnmpAdminString
    MAX-ACCESS   read-only
    STATUS       current
    DESCRIPTION
        "Cisco UCS equipment:FexSystemStatsHist:load managed
        object property"
    ::= { cucsEquipmentFexSystemStatsHistEntry 13 }

cucsEquipmentFexSystemStatsHistLoadAvg OBJECT-TYPE
    SYNTAX       SnmpAdminString
    MAX-ACCESS   read-only
    STATUS       current
    DESCRIPTION
        "Cisco UCS equipment:FexSystemStatsHist:loadAvg
        managed object property"
    ::= { cucsEquipmentFexSystemStatsHistEntry 14 }

cucsEquipmentFexSystemStatsHistLoadMax OBJECT-TYPE
    SYNTAX       SnmpAdminString
    MAX-ACCESS   read-only
    STATUS       current
    DESCRIPTION
        "Cisco UCS equipment:FexSystemStatsHist:loadMax
        managed object property"
    ::= { cucsEquipmentFexSystemStatsHistEntry 15 }

cucsEquipmentFexSystemStatsHistLoadMin OBJECT-TYPE
    SYNTAX       SnmpAdminString
    MAX-ACCESS   read-only
    STATUS       current
    DESCRIPTION
        "Cisco UCS equipment:FexSystemStatsHist:loadMin
        managed object property"
    ::= { cucsEquipmentFexSystemStatsHistEntry 16 }

cucsEquipmentFexSystemStatsHistMemAvailable OBJECT-TYPE
    SYNTAX       Gauge32
    MAX-ACCESS   read-only
    STATUS       current
    DESCRIPTION
        "Cisco UCS equipment:FexSystemStatsHist:memAvailable
        managed object property"
    ::= { cucsEquipmentFexSystemStatsHistEntry 17 }

cucsEquipmentFexSystemStatsHistMemAvailableAvg OBJECT-TYPE
    SYNTAX       Gauge32
    MAX-ACCESS   read-only
    STATUS       current
    DESCRIPTION
        "Cisco UCS equipment:FexSystemStatsHist:memAvailableAvg
        managed object property"
    ::= { cucsEquipmentFexSystemStatsHistEntry 18 }

cucsEquipmentFexSystemStatsHistMemAvailableMax OBJECT-TYPE
    SYNTAX       Gauge32
    MAX-ACCESS   read-only
    STATUS       current
    DESCRIPTION
        "Cisco UCS equipment:FexSystemStatsHist:memAvailableMax
        managed object property"
    ::= { cucsEquipmentFexSystemStatsHistEntry 19 }

cucsEquipmentFexSystemStatsHistMemAvailableMin OBJECT-TYPE
    SYNTAX       Gauge32
    MAX-ACCESS   read-only
    STATUS       current
    DESCRIPTION
        "Cisco UCS equipment:FexSystemStatsHist:memAvailableMin
        managed object property"
    ::= { cucsEquipmentFexSystemStatsHistEntry 20 }

cucsEquipmentFexSystemStatsHistMemCached OBJECT-TYPE
    SYNTAX       Gauge32
    MAX-ACCESS   read-only
    STATUS       current
    DESCRIPTION
        "Cisco UCS equipment:FexSystemStatsHist:memCached
        managed object property"
    ::= { cucsEquipmentFexSystemStatsHistEntry 21 }

cucsEquipmentFexSystemStatsHistMemCachedAvg OBJECT-TYPE
    SYNTAX       Gauge32
    MAX-ACCESS   read-only
    STATUS       current
    DESCRIPTION
        "Cisco UCS equipment:FexSystemStatsHist:memCachedAvg
        managed object property"
    ::= { cucsEquipmentFexSystemStatsHistEntry 22 }

cucsEquipmentFexSystemStatsHistMemCachedMax OBJECT-TYPE
    SYNTAX       Gauge32
    MAX-ACCESS   read-only
    STATUS       current
    DESCRIPTION
        "Cisco UCS equipment:FexSystemStatsHist:memCachedMax
        managed object property"
    ::= { cucsEquipmentFexSystemStatsHistEntry 23 }

cucsEquipmentFexSystemStatsHistMemCachedMin OBJECT-TYPE
    SYNTAX       Gauge32
    MAX-ACCESS   read-only
    STATUS       current
    DESCRIPTION
        "Cisco UCS equipment:FexSystemStatsHist:memCachedMin
        managed object property"
    ::= { cucsEquipmentFexSystemStatsHistEntry 24 }

cucsEquipmentFexSystemStatsHistMostRecent OBJECT-TYPE
    SYNTAX       TruthValue
    MAX-ACCESS   read-only
    STATUS       current
    DESCRIPTION
        "Cisco UCS equipment:FexSystemStatsHist:mostRecent
        managed object property"
    ::= { cucsEquipmentFexSystemStatsHistEntry 25 }

cucsEquipmentFexSystemStatsHistSuspect OBJECT-TYPE
    SYNTAX       TruthValue
    MAX-ACCESS   read-only
    STATUS       current
    DESCRIPTION
        "Cisco UCS equipment:FexSystemStatsHist:suspect
        managed object property"
    ::= { cucsEquipmentFexSystemStatsHistEntry 26 }

cucsEquipmentFexSystemStatsHistThresholded OBJECT-TYPE
    SYNTAX       CucsEquipmentFexSystemStatsHistThresholded
    MAX-ACCESS   read-only
    STATUS       current
    DESCRIPTION
        "Cisco UCS equipment:FexSystemStatsHist:thresholded
        managed object property"
    ::= { cucsEquipmentFexSystemStatsHistEntry 27 }

cucsEquipmentFexSystemStatsHistTimeCollected OBJECT-TYPE
    SYNTAX       DateAndTime
    MAX-ACCESS   read-only
    STATUS       current
    DESCRIPTION
        "Cisco UCS equipment:FexSystemStatsHist:timeCollected
        managed object property"
    ::= { cucsEquipmentFexSystemStatsHistEntry 28 }

cucsEquipmentFirmwareConstraintTable OBJECT-TYPE
    SYNTAX           SEQUENCE OF CucsEquipmentFirmwareConstraintEntry
    MAX-ACCESS       not-accessible
    STATUS           current
    DESCRIPTION
        "Cisco UCS equipment:FirmwareConstraint managed object table"
    ::= { cucsEquipmentObjects 113 }

cucsEquipmentFirmwareConstraintEntry OBJECT-TYPE
    SYNTAX           CucsEquipmentFirmwareConstraintEntry
    MAX-ACCESS       not-accessible
    STATUS           current
    DESCRIPTION
        "Entry for the cucsEquipmentFirmwareConstraintTable table."
    INDEX { cucsEquipmentFirmwareConstraintInstanceId }
    ::= { cucsEquipmentFirmwareConstraintTable 1 }

CucsEquipmentFirmwareConstraintEntry ::= SEQUENCE {
    cucsEquipmentFirmwareConstraintInstanceId                        CucsManagedObjectId,
    cucsEquipmentFirmwareConstraintDn                                CucsManagedObjectDn,
    cucsEquipmentFirmwareConstraintRn                                SnmpAdminString,
    cucsEquipmentFirmwareConstraintMinVer1                           SnmpAdminString,
    cucsEquipmentFirmwareConstraintMinVer2                           SnmpAdminString
}

cucsEquipmentFirmwareConstraintInstanceId OBJECT-TYPE
    SYNTAX       CucsManagedObjectId
    MAX-ACCESS   not-accessible
    STATUS       current
    DESCRIPTION
        "Instance identifier of the managed object."
    ::= { cucsEquipmentFirmwareConstraintEntry 1 }

cucsEquipmentFirmwareConstraintDn OBJECT-TYPE
    SYNTAX       CucsManagedObjectDn
    MAX-ACCESS   read-only
    STATUS       current
    DESCRIPTION
        "Cisco UCS equipment:FirmwareConstraint:dn managed
        object property"
    ::= { cucsEquipmentFirmwareConstraintEntry 2 }

cucsEquipmentFirmwareConstraintRn OBJECT-TYPE
    SYNTAX       SnmpAdminString
    MAX-ACCESS   read-only
    STATUS       current
    DESCRIPTION
        "Cisco UCS equipment:FirmwareConstraint:rn managed
        object property"
    ::= { cucsEquipmentFirmwareConstraintEntry 3 }

cucsEquipmentFirmwareConstraintMinVer1 OBJECT-TYPE
    SYNTAX       SnmpAdminString
    MAX-ACCESS   read-only
    STATUS       current
    DESCRIPTION
        "Cisco UCS equipment:FirmwareConstraint:minVer1
        managed object property"
    ::= { cucsEquipmentFirmwareConstraintEntry 4 }

cucsEquipmentFirmwareConstraintMinVer2 OBJECT-TYPE
    SYNTAX       SnmpAdminString
    MAX-ACCESS   read-only
    STATUS       current
    DESCRIPTION
        "Cisco UCS equipment:FirmwareConstraint:minVer2
        managed object property"
    ::= { cucsEquipmentFirmwareConstraintEntry 5 }

cucsEquipmentFlashLifeTable OBJECT-TYPE
    SYNTAX           SEQUENCE OF CucsEquipmentFlashLifeEntry
    MAX-ACCESS       not-accessible
    STATUS           current
    DESCRIPTION
        "Cisco UCS equipment:FlashLife managed object table"
    ::= { cucsEquipmentObjects 127 }

cucsEquipmentFlashLifeEntry OBJECT-TYPE
    SYNTAX           CucsEquipmentFlashLifeEntry
    MAX-ACCESS       not-accessible
    STATUS           current
    DESCRIPTION
        "Entry for the cucsEquipmentFlashLifeTable table."
    INDEX { cucsEquipmentFlashLifeInstanceId }
    ::= { cucsEquipmentFlashLifeTable 1 }

CucsEquipmentFlashLifeEntry ::= SEQUENCE {
    cucsEquipmentFlashLifeInstanceId                                 CucsManagedObjectId,
    cucsEquipmentFlashLifeDn                                         CucsManagedObjectDn,
    cucsEquipmentFlashLifeRn                                         SnmpAdminString,
    cucsEquipmentFlashLifeCardParamType                              Gauge32,
    cucsEquipmentFlashLifeDescr                                      SnmpAdminString,
    cucsEquipmentFlashLifeIntId                                      SnmpAdminString,
    cucsEquipmentFlashLifeName                                       SnmpAdminString,
    cucsEquipmentFlashLifePolicyLevel                                Gauge32,
    cucsEquipmentFlashLifePolicyOwner                                CucsPolicyPolicyOwner,
    cucsEquipmentFlashLifeSuportType                                 Gauge32
}

cucsEquipmentFlashLifeInstanceId OBJECT-TYPE
    SYNTAX       CucsManagedObjectId
    MAX-ACCESS   not-accessible
    STATUS       current
    DESCRIPTION
        "Instance identifier of the managed object."
    ::= { cucsEquipmentFlashLifeEntry 1 }

cucsEquipmentFlashLifeDn OBJECT-TYPE
    SYNTAX       CucsManagedObjectDn
    MAX-ACCESS   read-only
    STATUS       current
    DESCRIPTION
        "Cisco UCS equipment:FlashLife:dn managed object property"
    ::= { cucsEquipmentFlashLifeEntry 2 }

cucsEquipmentFlashLifeRn OBJECT-TYPE
    SYNTAX       SnmpAdminString
    MAX-ACCESS   read-only
    STATUS       current
    DESCRIPTION
        "Cisco UCS equipment:FlashLife:rn managed object property"
    ::= { cucsEquipmentFlashLifeEntry 3 }

cucsEquipmentFlashLifeCardParamType OBJECT-TYPE
    SYNTAX       Gauge32
    MAX-ACCESS   read-only
    STATUS       current
    DESCRIPTION
        "Cisco UCS equipment:FlashLife:cardParamType managed
        object property"
    ::= { cucsEquipmentFlashLifeEntry 4 }

cucsEquipmentFlashLifeDescr OBJECT-TYPE
    SYNTAX       SnmpAdminString
    MAX-ACCESS   read-only
    STATUS       current
    DESCRIPTION
        "Cisco UCS equipment:FlashLife:descr managed object property"
    ::= { cucsEquipmentFlashLifeEntry 5 }

cucsEquipmentFlashLifeIntId OBJECT-TYPE
    SYNTAX       SnmpAdminString
    MAX-ACCESS   read-only
    STATUS       current
    DESCRIPTION
        "Cisco UCS equipment:FlashLife:intId managed object property"
    ::= { cucsEquipmentFlashLifeEntry 6 }

cucsEquipmentFlashLifeName OBJECT-TYPE
    SYNTAX       SnmpAdminString
    MAX-ACCESS   read-only
    STATUS       current
    DESCRIPTION
        "Cisco UCS equipment:FlashLife:name managed object property"
    ::= { cucsEquipmentFlashLifeEntry 7 }

cucsEquipmentFlashLifePolicyLevel OBJECT-TYPE
    SYNTAX       Gauge32
    MAX-ACCESS   read-only
    STATUS       current
    DESCRIPTION
        "Cisco UCS equipment:FlashLife:policyLevel managed
        object property"
    ::= { cucsEquipmentFlashLifeEntry 8 }

cucsEquipmentFlashLifePolicyOwner OBJECT-TYPE
    SYNTAX       CucsPolicyPolicyOwner
    MAX-ACCESS   read-only
    STATUS       current
    DESCRIPTION
        "Cisco UCS equipment:FlashLife:policyOwner managed
        object property"
    ::= { cucsEquipmentFlashLifeEntry 9 }

cucsEquipmentFlashLifeSuportType OBJECT-TYPE
    SYNTAX       Gauge32
    MAX-ACCESS   read-only
    STATUS       current
    DESCRIPTION
        "Cisco UCS equipment:FlashLife:suportType managed object property"
    ::= { cucsEquipmentFlashLifeEntry 10 }

cucsEquipmentFruVariantTable OBJECT-TYPE
    SYNTAX           SEQUENCE OF CucsEquipmentFruVariantEntry
    MAX-ACCESS       not-accessible
    STATUS           current
    DESCRIPTION
        "Cisco UCS equipment:FruVariant managed object table"
    ::= { cucsEquipmentObjects 208 }

cucsEquipmentFruVariantEntry OBJECT-TYPE
    SYNTAX           CucsEquipmentFruVariantEntry
    MAX-ACCESS       not-accessible
    STATUS           current
    DESCRIPTION
        "Entry for the cucsEquipmentFruVariantTable table."
    INDEX { cucsEquipmentFruVariantInstanceId }
    ::= { cucsEquipmentFruVariantTable 1 }

CucsEquipmentFruVariantEntry ::= SEQUENCE {
    cucsEquipmentFruVariantInstanceId                                CucsManagedObjectId,
    cucsEquipmentFruVariantDn                                        CucsManagedObjectDn,
    cucsEquipmentFruVariantRn                                        SnmpAdminString,
    cucsEquipmentFruVariantDescription                               SnmpAdminString,
    cucsEquipmentFruVariantPid                                       SnmpAdminString,
    cucsEquipmentFruVariantType                                      SnmpAdminString
}

cucsEquipmentFruVariantInstanceId OBJECT-TYPE
    SYNTAX       CucsManagedObjectId
    MAX-ACCESS   not-accessible
    STATUS       current
    DESCRIPTION
        "Instance identifier of the managed object."
    ::= { cucsEquipmentFruVariantEntry 1 }

cucsEquipmentFruVariantDn OBJECT-TYPE
    SYNTAX       CucsManagedObjectDn
    MAX-ACCESS   read-only
    STATUS       current
    DESCRIPTION
        "Cisco UCS equipment:FruVariant:dn managed object property"
    ::= { cucsEquipmentFruVariantEntry 2 }

cucsEquipmentFruVariantRn OBJECT-TYPE
    SYNTAX       SnmpAdminString
    MAX-ACCESS   read-only
    STATUS       current
    DESCRIPTION
        "Cisco UCS equipment:FruVariant:rn managed object property"
    ::= { cucsEquipmentFruVariantEntry 3 }

cucsEquipmentFruVariantDescription OBJECT-TYPE
    SYNTAX       SnmpAdminString
    MAX-ACCESS   read-only
    STATUS       current
    DESCRIPTION
        "Cisco UCS equipment:FruVariant:description managed
        object property"
    ::= { cucsEquipmentFruVariantEntry 4 }

cucsEquipmentFruVariantPid OBJECT-TYPE
    SYNTAX       SnmpAdminString
    MAX-ACCESS   read-only
    STATUS       current
    DESCRIPTION
        "Cisco UCS equipment:FruVariant:pid managed object property"
    ::= { cucsEquipmentFruVariantEntry 5 }

cucsEquipmentFruVariantType OBJECT-TYPE
    SYNTAX       SnmpAdminString
    MAX-ACCESS   read-only
    STATUS       current
    DESCRIPTION
        "Cisco UCS equipment:FruVariant:type managed object property"
    ::= { cucsEquipmentFruVariantEntry 6 }

cucsEquipmentGemCapProviderTable OBJECT-TYPE
    SYNTAX           SEQUENCE OF CucsEquipmentGemCapProviderEntry
    MAX-ACCESS       not-accessible
    STATUS           current
    DESCRIPTION
        "Cisco UCS equipment:GemCapProvider managed object table"
    ::= { cucsEquipmentObjects 28 }

cucsEquipmentGemCapProviderEntry OBJECT-TYPE
    SYNTAX           CucsEquipmentGemCapProviderEntry
    MAX-ACCESS       not-accessible
    STATUS           current
    DESCRIPTION
        "Entry for the cucsEquipmentGemCapProviderTable table."
    INDEX { cucsEquipmentGemCapProviderInstanceId }
    ::= { cucsEquipmentGemCapProviderTable 1 }

CucsEquipmentGemCapProviderEntry ::= SEQUENCE {
    cucsEquipmentGemCapProviderInstanceId                            CucsManagedObjectId,
    cucsEquipmentGemCapProviderDn                                    CucsManagedObjectDn,
    cucsEquipmentGemCapProviderRn                                    SnmpAdminString,
    cucsEquipmentGemCapProviderDeprecated                            TruthValue,
    cucsEquipmentGemCapProviderGencount                              Gauge32,
    cucsEquipmentGemCapProviderMgmtPlaneVer                          SnmpAdminString,
    cucsEquipmentGemCapProviderModel                                 SnmpAdminString,
    cucsEquipmentGemCapProviderRevision                              SnmpAdminString,
    cucsEquipmentGemCapProviderVendor                                SnmpAdminString,
    cucsEquipmentGemCapProviderPromCardType                          Gauge32,
    cucsEquipmentGemCapProviderDeleted                               TruthValue,
    cucsEquipmentGemCapProviderElementLoadFailures                   Gauge32,
    cucsEquipmentGemCapProviderElementsLoaded                        Gauge32,
    cucsEquipmentGemCapProviderLoadErrors                            Gauge32,
    cucsEquipmentGemCapProviderLoadWarnings                          Gauge32
}

cucsEquipmentGemCapProviderInstanceId OBJECT-TYPE
    SYNTAX       CucsManagedObjectId
    MAX-ACCESS   not-accessible
    STATUS       current
    DESCRIPTION
        "Instance identifier of the managed object."
    ::= { cucsEquipmentGemCapProviderEntry 1 }

cucsEquipmentGemCapProviderDn OBJECT-TYPE
    SYNTAX       CucsManagedObjectDn
    MAX-ACCESS   read-only
    STATUS       current
    DESCRIPTION
        "Cisco UCS equipment:GemCapProvider:dn managed object property"
    ::= { cucsEquipmentGemCapProviderEntry 2 }

cucsEquipmentGemCapProviderRn OBJECT-TYPE
    SYNTAX       SnmpAdminString
    MAX-ACCESS   read-only
    STATUS       current
    DESCRIPTION
        "Cisco UCS equipment:GemCapProvider:rn managed object property"
    ::= { cucsEquipmentGemCapProviderEntry 3 }

cucsEquipmentGemCapProviderDeprecated OBJECT-TYPE
    SYNTAX       TruthValue
    MAX-ACCESS   read-only
    STATUS       current
    DESCRIPTION
        "Cisco UCS equipment:GemCapProvider:deprecated
        managed object property"
    ::= { cucsEquipmentGemCapProviderEntry 4 }

cucsEquipmentGemCapProviderGencount OBJECT-TYPE
    SYNTAX       Gauge32
    MAX-ACCESS   read-only
    STATUS       current
    DESCRIPTION
        "Cisco UCS equipment:GemCapProvider:gencount managed
        object property"
    ::= { cucsEquipmentGemCapProviderEntry 5 }

cucsEquipmentGemCapProviderMgmtPlaneVer OBJECT-TYPE
    SYNTAX       SnmpAdminString
    MAX-ACCESS   read-only
    STATUS       current
    DESCRIPTION
        "Cisco UCS equipment:GemCapProvider:mgmtPlaneVer
        managed object property"
    ::= { cucsEquipmentGemCapProviderEntry 6 }

cucsEquipmentGemCapProviderModel OBJECT-TYPE
    SYNTAX       SnmpAdminString
    MAX-ACCESS   read-only
    STATUS       current
    DESCRIPTION
        "Cisco UCS equipment:GemCapProvider:model managed object property"
    ::= { cucsEquipmentGemCapProviderEntry 7 }

cucsEquipmentGemCapProviderRevision OBJECT-TYPE
    SYNTAX       SnmpAdminString
    MAX-ACCESS   read-only
    STATUS       current
    DESCRIPTION
        "Cisco UCS equipment:GemCapProvider:revision managed
        object property"
    ::= { cucsEquipmentGemCapProviderEntry 8 }

cucsEquipmentGemCapProviderVendor OBJECT-TYPE
    SYNTAX       SnmpAdminString
    MAX-ACCESS   read-only
    STATUS       current
    DESCRIPTION
        "Cisco UCS equipment:GemCapProvider:vendor managed
        object property"
    ::= { cucsEquipmentGemCapProviderEntry 9 }

cucsEquipmentGemCapProviderPromCardType OBJECT-TYPE
    SYNTAX       Gauge32
    MAX-ACCESS   read-only
    STATUS       current
    DESCRIPTION
        "Cisco UCS equipment:GemCapProvider:promCardType
        managed object property"
    ::= { cucsEquipmentGemCapProviderEntry 10 }

cucsEquipmentGemCapProviderDeleted OBJECT-TYPE
    SYNTAX       TruthValue
    MAX-ACCESS   read-only
    STATUS       current
    DESCRIPTION
        "Cisco UCS equipment:GemCapProvider:deleted managed
        object property"
    ::= { cucsEquipmentGemCapProviderEntry 11 }

cucsEquipmentGemCapProviderElementLoadFailures OBJECT-TYPE
    SYNTAX       Gauge32
    MAX-ACCESS   read-only
    STATUS       current
    DESCRIPTION
        "Cisco UCS equipment:GemCapProvider:elementLoadFailures
        managed object property"
    ::= { cucsEquipmentGemCapProviderEntry 12 }

cucsEquipmentGemCapProviderElementsLoaded OBJECT-TYPE
    SYNTAX       Gauge32
    MAX-ACCESS   read-only
    STATUS       current
    DESCRIPTION
        "Cisco UCS equipment:GemCapProvider:elementsLoaded
        managed object property"
    ::= { cucsEquipmentGemCapProviderEntry 13 }

cucsEquipmentGemCapProviderLoadErrors OBJECT-TYPE
    SYNTAX       Gauge32
    MAX-ACCESS   read-only
    STATUS       current
    DESCRIPTION
        "Cisco UCS equipment:GemCapProvider:loadErrors
        managed object property"
    ::= { cucsEquipmentGemCapProviderEntry 14 }

cucsEquipmentGemCapProviderLoadWarnings OBJECT-TYPE
    SYNTAX       Gauge32
    MAX-ACCESS   read-only
    STATUS       current
    DESCRIPTION
        "Cisco UCS equipment:GemCapProvider:loadWarnings
        managed object property"
    ::= { cucsEquipmentGemCapProviderEntry 15 }

cucsEquipmentGemPortCapTable OBJECT-TYPE
    SYNTAX           SEQUENCE OF CucsEquipmentGemPortCapEntry
    MAX-ACCESS       not-accessible
    STATUS           current
    DESCRIPTION
        "Cisco UCS equipment:GemPortCap managed object table"
    ::= { cucsEquipmentObjects 78 }

cucsEquipmentGemPortCapEntry OBJECT-TYPE
    SYNTAX           CucsEquipmentGemPortCapEntry
    MAX-ACCESS       not-accessible
    STATUS           current
    DESCRIPTION
        "Entry for the cucsEquipmentGemPortCapTable table."
    INDEX { cucsEquipmentGemPortCapInstanceId }
    ::= { cucsEquipmentGemPortCapTable 1 }

CucsEquipmentGemPortCapEntry ::= SEQUENCE {
    cucsEquipmentGemPortCapInstanceId                                CucsManagedObjectId,
    cucsEquipmentGemPortCapDn                                        CucsManagedObjectDn,
    cucsEquipmentGemPortCapRn                                        SnmpAdminString,
    cucsEquipmentGemPortCapDescr                                     SnmpAdminString,
    cucsEquipmentGemPortCapIntId                                     SnmpAdminString,
    cucsEquipmentGemPortCapMaxFcSpeed                                CucsPortSpeed,
    cucsEquipmentGemPortCapName                                      SnmpAdminString,
    cucsEquipmentGemPortCapPortNumber                                Gauge32,
    cucsEquipmentGemPortCapPolicyLevel                               Gauge32,
    cucsEquipmentGemPortCapPolicyOwner                               CucsPolicyPolicyOwner
}

cucsEquipmentGemPortCapInstanceId OBJECT-TYPE
    SYNTAX       CucsManagedObjectId
    MAX-ACCESS   not-accessible
    STATUS       current
    DESCRIPTION
        "Instance identifier of the managed object."
    ::= { cucsEquipmentGemPortCapEntry 1 }

cucsEquipmentGemPortCapDn OBJECT-TYPE
    SYNTAX       CucsManagedObjectDn
    MAX-ACCESS   read-only
    STATUS       current
    DESCRIPTION
        "Cisco UCS equipment:GemPortCap:dn managed object property"
    ::= { cucsEquipmentGemPortCapEntry 2 }

cucsEquipmentGemPortCapRn OBJECT-TYPE
    SYNTAX       SnmpAdminString
    MAX-ACCESS   read-only
    STATUS       current
    DESCRIPTION
        "Cisco UCS equipment:GemPortCap:rn managed object property"
    ::= { cucsEquipmentGemPortCapEntry 3 }

cucsEquipmentGemPortCapDescr OBJECT-TYPE
    SYNTAX       SnmpAdminString
    MAX-ACCESS   read-only
    STATUS       current
    DESCRIPTION
        "Cisco UCS equipment:GemPortCap:descr managed object property"
    ::= { cucsEquipmentGemPortCapEntry 4 }

cucsEquipmentGemPortCapIntId OBJECT-TYPE
    SYNTAX       SnmpAdminString
    MAX-ACCESS   read-only
    STATUS       current
    DESCRIPTION
        "Cisco UCS equipment:GemPortCap:intId managed object property"
    ::= { cucsEquipmentGemPortCapEntry 5 }

cucsEquipmentGemPortCapMaxFcSpeed OBJECT-TYPE
    SYNTAX       CucsPortSpeed
    MAX-ACCESS   read-only
    STATUS       current
    DESCRIPTION
        "Cisco UCS equipment:GemPortCap:maxFcSpeed managed
        object property"
    ::= { cucsEquipmentGemPortCapEntry 6 }

cucsEquipmentGemPortCapName OBJECT-TYPE
    SYNTAX       SnmpAdminString
    MAX-ACCESS   read-only
    STATUS       current
    DESCRIPTION
        "Cisco UCS equipment:GemPortCap:name managed object property"
    ::= { cucsEquipmentGemPortCapEntry 7 }

cucsEquipmentGemPortCapPortNumber OBJECT-TYPE
    SYNTAX       Gauge32
    MAX-ACCESS   read-only
    STATUS       current
    DESCRIPTION
        "Cisco UCS equipment:GemPortCap:portNumber managed
        object property"
    ::= { cucsEquipmentGemPortCapEntry 8 }

cucsEquipmentGemPortCapPolicyLevel OBJECT-TYPE
    SYNTAX       Gauge32
    MAX-ACCESS   read-only
    STATUS       current
    DESCRIPTION
        "Cisco UCS equipment:GemPortCap:policyLevel managed
        object property"
    ::= { cucsEquipmentGemPortCapEntry 9 }

cucsEquipmentGemPortCapPolicyOwner OBJECT-TYPE
    SYNTAX       CucsPolicyPolicyOwner
    MAX-ACCESS   read-only
    STATUS       current
    DESCRIPTION
        "Cisco UCS equipment:GemPortCap:policyOwner managed
        object property"
    ::= { cucsEquipmentGemPortCapEntry 10 }

cucsEquipmentGraphicsCardCapProviderTable OBJECT-TYPE
    SYNTAX           SEQUENCE OF CucsEquipmentGraphicsCardCapProviderEntry
    MAX-ACCESS       not-accessible
    STATUS           current
    DESCRIPTION
        "Cisco UCS equipment:GraphicsCardCapProvider managed object table"
    ::= { cucsEquipmentObjects 118 }

cucsEquipmentGraphicsCardCapProviderEntry OBJECT-TYPE
    SYNTAX           CucsEquipmentGraphicsCardCapProviderEntry
    MAX-ACCESS       not-accessible
    STATUS           current
    DESCRIPTION
        "Entry for the cucsEquipmentGraphicsCardCapProviderTable table."
    INDEX { cucsEquipmentGraphicsCardCapProviderInstanceId }
    ::= { cucsEquipmentGraphicsCardCapProviderTable 1 }

CucsEquipmentGraphicsCardCapProviderEntry ::= SEQUENCE {
    cucsEquipmentGraphicsCardCapProviderInstanceId                   CucsManagedObjectId,
    cucsEquipmentGraphicsCardCapProviderDn                           CucsManagedObjectDn,
    cucsEquipmentGraphicsCardCapProviderRn                           SnmpAdminString,
    cucsEquipmentGraphicsCardCapProviderDeleted                      TruthValue,
    cucsEquipmentGraphicsCardCapProviderDeprecated                   TruthValue,
    cucsEquipmentGraphicsCardCapProviderElementLoadFailures          Gauge32,
    cucsEquipmentGraphicsCardCapProviderElementsLoaded               Gauge32,
    cucsEquipmentGraphicsCardCapProviderGencount                     Gauge32,
    cucsEquipmentGraphicsCardCapProviderLoadErrors                   Gauge32,
    cucsEquipmentGraphicsCardCapProviderLoadWarnings                 Gauge32,
    cucsEquipmentGraphicsCardCapProviderMgmtPlaneVer                 SnmpAdminString,
    cucsEquipmentGraphicsCardCapProviderModel                        SnmpAdminString,
    cucsEquipmentGraphicsCardCapProviderNumGpu                       Gauge32,
    cucsEquipmentGraphicsCardCapProviderPromCardType                 Gauge32,
    cucsEquipmentGraphicsCardCapProviderRevision                     SnmpAdminString,
    cucsEquipmentGraphicsCardCapProviderVendor                       SnmpAdminString,
    cucsEquipmentGraphicsCardCapProviderStepping                     SnmpAdminString,
    cucsEquipmentGraphicsCardCapProviderModeChangeSupported          TruthValue
}

cucsEquipmentGraphicsCardCapProviderInstanceId OBJECT-TYPE
    SYNTAX       CucsManagedObjectId
    MAX-ACCESS   not-accessible
    STATUS       current
    DESCRIPTION
        "Instance identifier of the managed object."
    ::= { cucsEquipmentGraphicsCardCapProviderEntry 1 }

cucsEquipmentGraphicsCardCapProviderDn OBJECT-TYPE
    SYNTAX       CucsManagedObjectDn
    MAX-ACCESS   read-only
    STATUS       current
    DESCRIPTION
        "Cisco UCS equipment:GraphicsCardCapProvider:dn
        managed object property"
    ::= { cucsEquipmentGraphicsCardCapProviderEntry 2 }

cucsEquipmentGraphicsCardCapProviderRn OBJECT-TYPE
    SYNTAX       SnmpAdminString
    MAX-ACCESS   read-only
    STATUS       current
    DESCRIPTION
        "Cisco UCS equipment:GraphicsCardCapProvider:rn
        managed object property"
    ::= { cucsEquipmentGraphicsCardCapProviderEntry 3 }

cucsEquipmentGraphicsCardCapProviderDeleted OBJECT-TYPE
    SYNTAX       TruthValue
    MAX-ACCESS   read-only
    STATUS       current
    DESCRIPTION
        "Cisco UCS equipment:GraphicsCardCapProvider:deleted
        managed object property"
    ::= { cucsEquipmentGraphicsCardCapProviderEntry 4 }

cucsEquipmentGraphicsCardCapProviderDeprecated OBJECT-TYPE
    SYNTAX       TruthValue
    MAX-ACCESS   read-only
    STATUS       current
    DESCRIPTION
        "Cisco UCS equipment:GraphicsCardCapProvider:deprecated
        managed object property"
    ::= { cucsEquipmentGraphicsCardCapProviderEntry 5 }

cucsEquipmentGraphicsCardCapProviderElementLoadFailures OBJECT-TYPE
    SYNTAX       Gauge32
    MAX-ACCESS   read-only
    STATUS       current
    DESCRIPTION
        "Cisco UCS equipment:GraphicsCardCapProvider:elementLoadFailures
        managed object property"
    ::= { cucsEquipmentGraphicsCardCapProviderEntry 6 }

cucsEquipmentGraphicsCardCapProviderElementsLoaded OBJECT-TYPE
    SYNTAX       Gauge32
    MAX-ACCESS   read-only
    STATUS       current
    DESCRIPTION
        "Cisco UCS equipment:GraphicsCardCapProvider:elementsLoaded
        managed object property"
    ::= { cucsEquipmentGraphicsCardCapProviderEntry 7 }

cucsEquipmentGraphicsCardCapProviderGencount OBJECT-TYPE
    SYNTAX       Gauge32
    MAX-ACCESS   read-only
    STATUS       current
    DESCRIPTION
        "Cisco UCS equipment:GraphicsCardCapProvider:gencount
        managed object property"
    ::= { cucsEquipmentGraphicsCardCapProviderEntry 8 }

cucsEquipmentGraphicsCardCapProviderLoadErrors OBJECT-TYPE
    SYNTAX       Gauge32
    MAX-ACCESS   read-only
    STATUS       current
    DESCRIPTION
        "Cisco UCS equipment:GraphicsCardCapProvider:loadErrors
        managed object property"
    ::= { cucsEquipmentGraphicsCardCapProviderEntry 9 }

cucsEquipmentGraphicsCardCapProviderLoadWarnings OBJECT-TYPE
    SYNTAX       Gauge32
    MAX-ACCESS   read-only
    STATUS       current
    DESCRIPTION
        "Cisco UCS equipment:GraphicsCardCapProvider:loadWarnings
        managed object property"
    ::= { cucsEquipmentGraphicsCardCapProviderEntry 10 }

cucsEquipmentGraphicsCardCapProviderMgmtPlaneVer OBJECT-TYPE
    SYNTAX       SnmpAdminString
    MAX-ACCESS   read-only
    STATUS       current
    DESCRIPTION
        "Cisco UCS equipment:GraphicsCardCapProvider:mgmtPlaneVer
        managed object property"
    ::= { cucsEquipmentGraphicsCardCapProviderEntry 11 }

cucsEquipmentGraphicsCardCapProviderModel OBJECT-TYPE
    SYNTAX       SnmpAdminString
    MAX-ACCESS   read-only
    STATUS       current
    DESCRIPTION
        "Cisco UCS equipment:GraphicsCardCapProvider:model
        managed object property"
    ::= { cucsEquipmentGraphicsCardCapProviderEntry 12 }

cucsEquipmentGraphicsCardCapProviderNumGpu OBJECT-TYPE
    SYNTAX       Gauge32
    MAX-ACCESS   read-only
    STATUS       current
    DESCRIPTION
        "Cisco UCS equipment:GraphicsCardCapProvider:numGpu
        managed object property"
    ::= { cucsEquipmentGraphicsCardCapProviderEntry 13 }

cucsEquipmentGraphicsCardCapProviderPromCardType OBJECT-TYPE
    SYNTAX       Gauge32
    MAX-ACCESS   read-only
    STATUS       current
    DESCRIPTION
        "Cisco UCS equipment:GraphicsCardCapProvider:promCardType
        managed object property"
    ::= { cucsEquipmentGraphicsCardCapProviderEntry 14 }

cucsEquipmentGraphicsCardCapProviderRevision OBJECT-TYPE
    SYNTAX       SnmpAdminString
    MAX-ACCESS   read-only
    STATUS       current
    DESCRIPTION
        "Cisco UCS equipment:GraphicsCardCapProvider:revision
        managed object property"
    ::= { cucsEquipmentGraphicsCardCapProviderEntry 15 }

cucsEquipmentGraphicsCardCapProviderVendor OBJECT-TYPE
    SYNTAX       SnmpAdminString
    MAX-ACCESS   read-only
    STATUS       current
    DESCRIPTION
        "Cisco UCS equipment:GraphicsCardCapProvider:vendor
        managed object property"
    ::= { cucsEquipmentGraphicsCardCapProviderEntry 16 }

cucsEquipmentGraphicsCardCapProviderStepping OBJECT-TYPE
    SYNTAX       SnmpAdminString
    MAX-ACCESS   read-only
    STATUS       current
    DESCRIPTION
        "Cisco UCS equipment:GraphicsCardCapProvider:stepping
        managed object property"
    ::= { cucsEquipmentGraphicsCardCapProviderEntry 17 }

cucsEquipmentGraphicsCardCapProviderModeChangeSupported OBJECT-TYPE
    SYNTAX       TruthValue
    MAX-ACCESS   read-only
    STATUS       current
    DESCRIPTION
        "Cisco UCS equipment:GraphicsCardCapProvider:modeChangeSupported
        managed object property"
    ::= { cucsEquipmentGraphicsCardCapProviderEntry 18 }

cucsEquipmentGraphicsCardCapRefTable OBJECT-TYPE
    SYNTAX           SEQUENCE OF CucsEquipmentGraphicsCardCapRefEntry
    MAX-ACCESS       not-accessible
    STATUS           current
    DESCRIPTION
        "Cisco UCS equipment:GraphicsCardCapRef managed object table"
    ::= { cucsEquipmentObjects 119 }

cucsEquipmentGraphicsCardCapRefEntry OBJECT-TYPE
    SYNTAX           CucsEquipmentGraphicsCardCapRefEntry
    MAX-ACCESS       not-accessible
    STATUS           current
    DESCRIPTION
        "Entry for the cucsEquipmentGraphicsCardCapRefTable table."
    INDEX { cucsEquipmentGraphicsCardCapRefInstanceId }
    ::= { cucsEquipmentGraphicsCardCapRefTable 1 }

CucsEquipmentGraphicsCardCapRefEntry ::= SEQUENCE {
    cucsEquipmentGraphicsCardCapRefInstanceId                        CucsManagedObjectId,
    cucsEquipmentGraphicsCardCapRefDn                                CucsManagedObjectDn,
    cucsEquipmentGraphicsCardCapRefRn                                SnmpAdminString,
    cucsEquipmentGraphicsCardCapRefModel                             SnmpAdminString,
    cucsEquipmentGraphicsCardCapRefRevision                          SnmpAdminString,
    cucsEquipmentGraphicsCardCapRefVendor                            SnmpAdminString,
    cucsEquipmentGraphicsCardCapRefIsSupported                       CucsEquipmentIsSupported
}

cucsEquipmentGraphicsCardCapRefInstanceId OBJECT-TYPE
    SYNTAX       CucsManagedObjectId
    MAX-ACCESS   not-accessible
    STATUS       current
    DESCRIPTION
        "Instance identifier of the managed object."
    ::= { cucsEquipmentGraphicsCardCapRefEntry 1 }

cucsEquipmentGraphicsCardCapRefDn OBJECT-TYPE
    SYNTAX       CucsManagedObjectDn
    MAX-ACCESS   read-only
    STATUS       current
    DESCRIPTION
        "Cisco UCS equipment:GraphicsCardCapRef:dn managed
        object property"
    ::= { cucsEquipmentGraphicsCardCapRefEntry 2 }

cucsEquipmentGraphicsCardCapRefRn OBJECT-TYPE
    SYNTAX       SnmpAdminString
    MAX-ACCESS   read-only
    STATUS       current
    DESCRIPTION
        "Cisco UCS equipment:GraphicsCardCapRef:rn managed
        object property"
    ::= { cucsEquipmentGraphicsCardCapRefEntry 3 }

cucsEquipmentGraphicsCardCapRefModel OBJECT-TYPE
    SYNTAX       SnmpAdminString
    MAX-ACCESS   read-only
    STATUS       current
    DESCRIPTION
        "Cisco UCS equipment:GraphicsCardCapRef:model managed
        object property"
    ::= { cucsEquipmentGraphicsCardCapRefEntry 4 }

cucsEquipmentGraphicsCardCapRefRevision OBJECT-TYPE
    SYNTAX       SnmpAdminString
    MAX-ACCESS   read-only
    STATUS       current
    DESCRIPTION
        "Cisco UCS equipment:GraphicsCardCapRef:revision
        managed object property"
    ::= { cucsEquipmentGraphicsCardCapRefEntry 5 }

cucsEquipmentGraphicsCardCapRefVendor OBJECT-TYPE
    SYNTAX       SnmpAdminString
    MAX-ACCESS   read-only
    STATUS       current
    DESCRIPTION
        "Cisco UCS equipment:GraphicsCardCapRef:vendor
        managed object property"
    ::= { cucsEquipmentGraphicsCardCapRefEntry 6 }

cucsEquipmentGraphicsCardCapRefIsSupported OBJECT-TYPE
    SYNTAX       CucsEquipmentIsSupported
    MAX-ACCESS   read-only
    STATUS       current
    DESCRIPTION
        "Cisco UCS equipment:GraphicsCardCapRef:isSupported
        managed object property"
    ::= { cucsEquipmentGraphicsCardCapRefEntry 7 }

cucsEquipmentHDDFaultMonDefTable OBJECT-TYPE
    SYNTAX           SEQUENCE OF CucsEquipmentHDDFaultMonDefEntry
    MAX-ACCESS       not-accessible
    STATUS           current
    DESCRIPTION
        "Cisco UCS equipment:HDDFaultMonDef managed object table"
    ::= { cucsEquipmentObjects 85 }

cucsEquipmentHDDFaultMonDefEntry OBJECT-TYPE
    SYNTAX           CucsEquipmentHDDFaultMonDefEntry
    MAX-ACCESS       not-accessible
    STATUS           current
    DESCRIPTION
        "Entry for the cucsEquipmentHDDFaultMonDefTable table."
    INDEX { cucsEquipmentHDDFaultMonDefInstanceId }
    ::= { cucsEquipmentHDDFaultMonDefTable 1 }

CucsEquipmentHDDFaultMonDefEntry ::= SEQUENCE {
    cucsEquipmentHDDFaultMonDefInstanceId                            CucsManagedObjectId,
    cucsEquipmentHDDFaultMonDefDn                                    CucsManagedObjectDn,
    cucsEquipmentHDDFaultMonDefRn                                    SnmpAdminString,
    cucsEquipmentHDDFaultMonDefControllerFwVersion                   SnmpAdminString,
    cucsEquipmentHDDFaultMonDefControllerModel                       SnmpAdminString,
    cucsEquipmentHDDFaultMonDefHDDMonSupport                         SnmpAdminString,
    cucsEquipmentHDDFaultMonDefDescr                                 SnmpAdminString,
    cucsEquipmentHDDFaultMonDefIntId                                 SnmpAdminString,
    cucsEquipmentHDDFaultMonDefName                                  SnmpAdminString,
    cucsEquipmentHDDFaultMonDefPolicyLevel                           Gauge32,
    cucsEquipmentHDDFaultMonDefPolicyOwner                           CucsPolicyPolicyOwner
}

cucsEquipmentHDDFaultMonDefInstanceId OBJECT-TYPE
    SYNTAX       CucsManagedObjectId
    MAX-ACCESS   not-accessible
    STATUS       current
    DESCRIPTION
        "Instance identifier of the managed object."
    ::= { cucsEquipmentHDDFaultMonDefEntry 1 }

cucsEquipmentHDDFaultMonDefDn OBJECT-TYPE
    SYNTAX       CucsManagedObjectDn
    MAX-ACCESS   read-only
    STATUS       current
    DESCRIPTION
        "Cisco UCS equipment:HDDFaultMonDef:dn managed object property"
    ::= { cucsEquipmentHDDFaultMonDefEntry 2 }

cucsEquipmentHDDFaultMonDefRn OBJECT-TYPE
    SYNTAX       SnmpAdminString
    MAX-ACCESS   read-only
    STATUS       current
    DESCRIPTION
        "Cisco UCS equipment:HDDFaultMonDef:rn managed object property"
    ::= { cucsEquipmentHDDFaultMonDefEntry 3 }

cucsEquipmentHDDFaultMonDefControllerFwVersion OBJECT-TYPE
    SYNTAX       SnmpAdminString
    MAX-ACCESS   read-only
    STATUS       current
    DESCRIPTION
        "Cisco UCS equipment:HDDFaultMonDef:ControllerFwVersion
        managed object property"
    ::= { cucsEquipmentHDDFaultMonDefEntry 4 }

cucsEquipmentHDDFaultMonDefControllerModel OBJECT-TYPE
    SYNTAX       SnmpAdminString
    MAX-ACCESS   read-only
    STATUS       current
    DESCRIPTION
        "Cisco UCS equipment:HDDFaultMonDef:ControllerModel
        managed object property"
    ::= { cucsEquipmentHDDFaultMonDefEntry 5 }

cucsEquipmentHDDFaultMonDefHDDMonSupport OBJECT-TYPE
    SYNTAX       SnmpAdminString
    MAX-ACCESS   read-only
    STATUS       current
    DESCRIPTION
        "Cisco UCS equipment:HDDFaultMonDef:HDDMonSupport
        managed object property"
    ::= { cucsEquipmentHDDFaultMonDefEntry 6 }

cucsEquipmentHDDFaultMonDefDescr OBJECT-TYPE
    SYNTAX       SnmpAdminString
    MAX-ACCESS   read-only
    STATUS       current
    DESCRIPTION
        "Cisco UCS equipment:HDDFaultMonDef:descr managed object property"
    ::= { cucsEquipmentHDDFaultMonDefEntry 7 }

cucsEquipmentHDDFaultMonDefIntId OBJECT-TYPE
    SYNTAX       SnmpAdminString
    MAX-ACCESS   read-only
    STATUS       current
    DESCRIPTION
        "Cisco UCS equipment:HDDFaultMonDef:intId managed object property"
    ::= { cucsEquipmentHDDFaultMonDefEntry 8 }

cucsEquipmentHDDFaultMonDefName OBJECT-TYPE
    SYNTAX       SnmpAdminString
    MAX-ACCESS   read-only
    STATUS       current
    DESCRIPTION
        "Cisco UCS equipment:HDDFaultMonDef:name managed object property"
    ::= { cucsEquipmentHDDFaultMonDefEntry 9 }

cucsEquipmentHDDFaultMonDefPolicyLevel OBJECT-TYPE
    SYNTAX       Gauge32
    MAX-ACCESS   read-only
    STATUS       current
    DESCRIPTION
        "Cisco UCS equipment:HDDFaultMonDef:policyLevel
        managed object property"
    ::= { cucsEquipmentHDDFaultMonDefEntry 10 }

cucsEquipmentHDDFaultMonDefPolicyOwner OBJECT-TYPE
    SYNTAX       CucsPolicyPolicyOwner
    MAX-ACCESS   read-only
    STATUS       current
    DESCRIPTION
        "Cisco UCS equipment:HDDFaultMonDef:policyOwner
        managed object property"
    ::= { cucsEquipmentHDDFaultMonDefEntry 11 }

cucsEquipmentHealthLedTable OBJECT-TYPE
    SYNTAX           SEQUENCE OF CucsEquipmentHealthLedEntry
    MAX-ACCESS       not-accessible
    STATUS           current
    DESCRIPTION
        "Cisco UCS equipment:HealthLed managed object table"
    ::= { cucsEquipmentObjects 114 }

cucsEquipmentHealthLedEntry OBJECT-TYPE
    SYNTAX           CucsEquipmentHealthLedEntry
    MAX-ACCESS       not-accessible
    STATUS           current
    DESCRIPTION
        "Entry for the cucsEquipmentHealthLedTable table."
    INDEX { cucsEquipmentHealthLedInstanceId }
    ::= { cucsEquipmentHealthLedTable 1 }

CucsEquipmentHealthLedEntry ::= SEQUENCE {
    cucsEquipmentHealthLedInstanceId                                 CucsManagedObjectId,
    cucsEquipmentHealthLedDn                                         CucsManagedObjectDn,
    cucsEquipmentHealthLedRn                                         SnmpAdminString,
    cucsEquipmentHealthLedColor                                      CucsEquipmentLedColor,
    cucsEquipmentHealthLedHealthLedState                             CucsEquipmentHealthLedState,
    cucsEquipmentHealthLedHealthLedStateQualifier                    SnmpAdminString,
    cucsEquipmentHealthLedId                                         Gauge32,
    cucsEquipmentHealthLedName                                       SnmpAdminString,
    cucsEquipmentHealthLedOperState                                  CucsEquipmentLedOperState
}

cucsEquipmentHealthLedInstanceId OBJECT-TYPE
    SYNTAX       CucsManagedObjectId
    MAX-ACCESS   not-accessible
    STATUS       current
    DESCRIPTION
        "Instance identifier of the managed object."
    ::= { cucsEquipmentHealthLedEntry 1 }

cucsEquipmentHealthLedDn OBJECT-TYPE
    SYNTAX       CucsManagedObjectDn
    MAX-ACCESS   read-only
    STATUS       current
    DESCRIPTION
        "Cisco UCS equipment:HealthLed:dn managed object property"
    ::= { cucsEquipmentHealthLedEntry 2 }

cucsEquipmentHealthLedRn OBJECT-TYPE
    SYNTAX       SnmpAdminString
    MAX-ACCESS   read-only
    STATUS       current
    DESCRIPTION
        "Cisco UCS equipment:HealthLed:rn managed object property"
    ::= { cucsEquipmentHealthLedEntry 3 }

cucsEquipmentHealthLedColor OBJECT-TYPE
    SYNTAX       CucsEquipmentLedColor
    MAX-ACCESS   read-only
    STATUS       current
    DESCRIPTION
        "Cisco UCS equipment:HealthLed:color managed object property"
    ::= { cucsEquipmentHealthLedEntry 4 }

cucsEquipmentHealthLedHealthLedState OBJECT-TYPE
    SYNTAX       CucsEquipmentHealthLedState
    MAX-ACCESS   read-only
    STATUS       current
    DESCRIPTION
        "Cisco UCS equipment:HealthLed:healthLedState managed
        object property"
    ::= { cucsEquipmentHealthLedEntry 5 }

cucsEquipmentHealthLedHealthLedStateQualifier OBJECT-TYPE
    SYNTAX       SnmpAdminString
    MAX-ACCESS   read-only
    STATUS       current
    DESCRIPTION
        "Cisco UCS equipment:HealthLed:healthLedStateQualifier
        managed object property"
    ::= { cucsEquipmentHealthLedEntry 6 }

cucsEquipmentHealthLedId OBJECT-TYPE
    SYNTAX       Gauge32
    MAX-ACCESS   read-only
    STATUS       current
    DESCRIPTION
        "Cisco UCS equipment:HealthLed:id managed object property"
    ::= { cucsEquipmentHealthLedEntry 7 }

cucsEquipmentHealthLedName OBJECT-TYPE
    SYNTAX       SnmpAdminString
    MAX-ACCESS   read-only
    STATUS       current
    DESCRIPTION
        "Cisco UCS equipment:HealthLed:name managed object property"
    ::= { cucsEquipmentHealthLedEntry 8 }

cucsEquipmentHealthLedOperState OBJECT-TYPE
    SYNTAX       CucsEquipmentLedOperState
    MAX-ACCESS   read-only
    STATUS       current
    DESCRIPTION
        "Cisco UCS equipment:HealthLed:operState managed object property"
    ::= { cucsEquipmentHealthLedEntry 9 }

cucsEquipmentHostIfCapProviderTable OBJECT-TYPE
    SYNTAX           SEQUENCE OF CucsEquipmentHostIfCapProviderEntry
    MAX-ACCESS       not-accessible
    STATUS           current
    DESCRIPTION
        "Cisco UCS equipment:HostIfCapProvider managed object table"
    ::= { cucsEquipmentObjects 29 }

cucsEquipmentHostIfCapProviderEntry OBJECT-TYPE
    SYNTAX           CucsEquipmentHostIfCapProviderEntry
    MAX-ACCESS       not-accessible
    STATUS           current
    DESCRIPTION
        "Entry for the cucsEquipmentHostIfCapProviderTable table."
    INDEX { cucsEquipmentHostIfCapProviderInstanceId }
    ::= { cucsEquipmentHostIfCapProviderTable 1 }

CucsEquipmentHostIfCapProviderEntry ::= SEQUENCE {
    cucsEquipmentHostIfCapProviderInstanceId                         CucsManagedObjectId,
    cucsEquipmentHostIfCapProviderDn                                 CucsManagedObjectDn,
    cucsEquipmentHostIfCapProviderRn                                 SnmpAdminString,
    cucsEquipmentHostIfCapProviderDeprecated                         TruthValue,
    cucsEquipmentHostIfCapProviderGencount                           Gauge32,
    cucsEquipmentHostIfCapProviderMgmtPlaneVer                       SnmpAdminString,
    cucsEquipmentHostIfCapProviderModel                              SnmpAdminString,
    cucsEquipmentHostIfCapProviderRevision                           SnmpAdminString,
    cucsEquipmentHostIfCapProviderVendor                             SnmpAdminString,
    cucsEquipmentHostIfCapProviderPromCardType                       Gauge32,
    cucsEquipmentHostIfCapProviderDeleted                            TruthValue,
    cucsEquipmentHostIfCapProviderElementLoadFailures                Gauge32,
    cucsEquipmentHostIfCapProviderElementsLoaded                     Gauge32,
    cucsEquipmentHostIfCapProviderLoadErrors                         Gauge32,
    cucsEquipmentHostIfCapProviderLoadWarnings                       Gauge32
}

cucsEquipmentHostIfCapProviderInstanceId OBJECT-TYPE
    SYNTAX       CucsManagedObjectId
    MAX-ACCESS   not-accessible
    STATUS       current
    DESCRIPTION
        "Instance identifier of the managed object."
    ::= { cucsEquipmentHostIfCapProviderEntry 1 }

cucsEquipmentHostIfCapProviderDn OBJECT-TYPE
    SYNTAX       CucsManagedObjectDn
    MAX-ACCESS   read-only
    STATUS       current
    DESCRIPTION
        "Cisco UCS equipment:HostIfCapProvider:dn managed object property"
    ::= { cucsEquipmentHostIfCapProviderEntry 2 }

cucsEquipmentHostIfCapProviderRn OBJECT-TYPE
    SYNTAX       SnmpAdminString
    MAX-ACCESS   read-only
    STATUS       current
    DESCRIPTION
        "Cisco UCS equipment:HostIfCapProvider:rn managed object property"
    ::= { cucsEquipmentHostIfCapProviderEntry 3 }

cucsEquipmentHostIfCapProviderDeprecated OBJECT-TYPE
    SYNTAX       TruthValue
    MAX-ACCESS   read-only
    STATUS       current
    DESCRIPTION
        "Cisco UCS equipment:HostIfCapProvider:deprecated
        managed object property"
    ::= { cucsEquipmentHostIfCapProviderEntry 4 }

cucsEquipmentHostIfCapProviderGencount OBJECT-TYPE
    SYNTAX       Gauge32
    MAX-ACCESS   read-only
    STATUS       current
    DESCRIPTION
        "Cisco UCS equipment:HostIfCapProvider:gencount
        managed object property"
    ::= { cucsEquipmentHostIfCapProviderEntry 5 }

cucsEquipmentHostIfCapProviderMgmtPlaneVer OBJECT-TYPE
    SYNTAX       SnmpAdminString
    MAX-ACCESS   read-only
    STATUS       current
    DESCRIPTION
        "Cisco UCS equipment:HostIfCapProvider:mgmtPlaneVer
        managed object property"
    ::= { cucsEquipmentHostIfCapProviderEntry 6 }

cucsEquipmentHostIfCapProviderModel OBJECT-TYPE
    SYNTAX       SnmpAdminString
    MAX-ACCESS   read-only
    STATUS       current
    DESCRIPTION
        "Cisco UCS equipment:HostIfCapProvider:model managed
        object property"
    ::= { cucsEquipmentHostIfCapProviderEntry 7 }

cucsEquipmentHostIfCapProviderRevision OBJECT-TYPE
    SYNTAX       SnmpAdminString
    MAX-ACCESS   read-only
    STATUS       current
    DESCRIPTION
        "Cisco UCS equipment:HostIfCapProvider:revision
        managed object property"
    ::= { cucsEquipmentHostIfCapProviderEntry 8 }

cucsEquipmentHostIfCapProviderVendor OBJECT-TYPE
    SYNTAX       SnmpAdminString
    MAX-ACCESS   read-only
    STATUS       current
    DESCRIPTION
        "Cisco UCS equipment:HostIfCapProvider:vendor managed
        object property"
    ::= { cucsEquipmentHostIfCapProviderEntry 9 }

cucsEquipmentHostIfCapProviderPromCardType OBJECT-TYPE
    SYNTAX       Gauge32
    MAX-ACCESS   read-only
    STATUS       current
    DESCRIPTION
        "Cisco UCS equipment:HostIfCapProvider:promCardType
        managed object property"
    ::= { cucsEquipmentHostIfCapProviderEntry 10 }

cucsEquipmentHostIfCapProviderDeleted OBJECT-TYPE
    SYNTAX       TruthValue
    MAX-ACCESS   read-only
    STATUS       current
    DESCRIPTION
        "Cisco UCS equipment:HostIfCapProvider:deleted
        managed object property"
    ::= { cucsEquipmentHostIfCapProviderEntry 11 }

cucsEquipmentHostIfCapProviderElementLoadFailures OBJECT-TYPE
    SYNTAX       Gauge32
    MAX-ACCESS   read-only
    STATUS       current
    DESCRIPTION
        "Cisco UCS equipment:HostIfCapProvider:elementLoadFailures
        managed object property"
    ::= { cucsEquipmentHostIfCapProviderEntry 12 }

cucsEquipmentHostIfCapProviderElementsLoaded OBJECT-TYPE
    SYNTAX       Gauge32
    MAX-ACCESS   read-only
    STATUS       current
    DESCRIPTION
        "Cisco UCS equipment:HostIfCapProvider:elementsLoaded
        managed object property"
    ::= { cucsEquipmentHostIfCapProviderEntry 13 }

cucsEquipmentHostIfCapProviderLoadErrors OBJECT-TYPE
    SYNTAX       Gauge32
    MAX-ACCESS   read-only
    STATUS       current
    DESCRIPTION
        "Cisco UCS equipment:HostIfCapProvider:loadErrors
        managed object property"
    ::= { cucsEquipmentHostIfCapProviderEntry 14 }

cucsEquipmentHostIfCapProviderLoadWarnings OBJECT-TYPE
    SYNTAX       Gauge32
    MAX-ACCESS   read-only
    STATUS       current
    DESCRIPTION
        "Cisco UCS equipment:HostIfCapProvider:loadWarnings
        managed object property"
    ::= { cucsEquipmentHostIfCapProviderEntry 15 }

cucsEquipmentHostMgmtControllerCapTable OBJECT-TYPE
    SYNTAX           SEQUENCE OF CucsEquipmentHostMgmtControllerCapEntry
    MAX-ACCESS       not-accessible
    STATUS           current
    DESCRIPTION
        "Cisco UCS equipment:HostMgmtControllerCap managed object table"
    ::= { cucsEquipmentObjects 226 }

cucsEquipmentHostMgmtControllerCapEntry OBJECT-TYPE
    SYNTAX           CucsEquipmentHostMgmtControllerCapEntry
    MAX-ACCESS       not-accessible
    STATUS           current
    DESCRIPTION
        "Entry for the cucsEquipmentHostMgmtControllerCapTable table."
    INDEX { cucsEquipmentHostMgmtControllerCapInstanceId }
    ::= { cucsEquipmentHostMgmtControllerCapTable 1 }

CucsEquipmentHostMgmtControllerCapEntry ::= SEQUENCE {
    cucsEquipmentHostMgmtControllerCapInstanceId                     CucsManagedObjectId,
    cucsEquipmentHostMgmtControllerCapDn                             CucsManagedObjectDn,
    cucsEquipmentHostMgmtControllerCapRn                             SnmpAdminString,
    cucsEquipmentHostMgmtControllerCapCommMethod                     CucsEquipmentHostMgmtControllerCapCommMethod
}

cucsEquipmentHostMgmtControllerCapInstanceId OBJECT-TYPE
    SYNTAX       CucsManagedObjectId
    MAX-ACCESS   not-accessible
    STATUS       current
    DESCRIPTION
        "Instance identifier of the managed object."
    ::= { cucsEquipmentHostMgmtControllerCapEntry 1 }

cucsEquipmentHostMgmtControllerCapDn OBJECT-TYPE
    SYNTAX       CucsManagedObjectDn
    MAX-ACCESS   read-only
    STATUS       current
    DESCRIPTION
        "Cisco UCS equipment:HostMgmtControllerCap:dn managed
        object property"
    ::= { cucsEquipmentHostMgmtControllerCapEntry 2 }

cucsEquipmentHostMgmtControllerCapRn OBJECT-TYPE
    SYNTAX       SnmpAdminString
    MAX-ACCESS   read-only
    STATUS       current
    DESCRIPTION
        "Cisco UCS equipment:HostMgmtControllerCap:rn managed
        object property"
    ::= { cucsEquipmentHostMgmtControllerCapEntry 3 }

cucsEquipmentHostMgmtControllerCapCommMethod OBJECT-TYPE
    SYNTAX       CucsEquipmentHostMgmtControllerCapCommMethod
    MAX-ACCESS   read-only
    STATUS       current
    DESCRIPTION
        "Cisco UCS equipment:HostMgmtControllerCap:commMethod
        managed object property"
    ::= { cucsEquipmentHostMgmtControllerCapEntry 4 }

cucsEquipmentHwCapDerivativeProviderTable OBJECT-TYPE
    SYNTAX           SEQUENCE OF CucsEquipmentHwCapDerivativeProviderEntry
    MAX-ACCESS       not-accessible
    STATUS           current
    DESCRIPTION
        "Cisco UCS equipment:HwCapDerivativeProvider managed object table"
    ::= { cucsEquipmentObjects 174 }

cucsEquipmentHwCapDerivativeProviderEntry OBJECT-TYPE
    SYNTAX           CucsEquipmentHwCapDerivativeProviderEntry
    MAX-ACCESS       not-accessible
    STATUS           current
    DESCRIPTION
        "Entry for the cucsEquipmentHwCapDerivativeProviderTable table."
    INDEX { cucsEquipmentHwCapDerivativeProviderInstanceId }
    ::= { cucsEquipmentHwCapDerivativeProviderTable 1 }

CucsEquipmentHwCapDerivativeProviderEntry ::= SEQUENCE {
    cucsEquipmentHwCapDerivativeProviderInstanceId                   CucsManagedObjectId,
    cucsEquipmentHwCapDerivativeProviderDn                           CucsManagedObjectDn,
    cucsEquipmentHwCapDerivativeProviderRn                           SnmpAdminString,
    cucsEquipmentHwCapDerivativeProviderDeleted                      TruthValue,
    cucsEquipmentHwCapDerivativeProviderDeprecated                   TruthValue,
    cucsEquipmentHwCapDerivativeProviderElementLoadFailures          Gauge32,
    cucsEquipmentHwCapDerivativeProviderElementsLoaded               Gauge32,
    cucsEquipmentHwCapDerivativeProviderGencount                     Gauge32,
    cucsEquipmentHwCapDerivativeProviderLoadErrors                   Gauge32,
    cucsEquipmentHwCapDerivativeProviderLoadWarnings                 Gauge32,
    cucsEquipmentHwCapDerivativeProviderMgmtPlaneVer                 SnmpAdminString,
    cucsEquipmentHwCapDerivativeProviderModel                        SnmpAdminString,
    cucsEquipmentHwCapDerivativeProviderRevision                     SnmpAdminString,
    cucsEquipmentHwCapDerivativeProviderVendor                       SnmpAdminString
}

cucsEquipmentHwCapDerivativeProviderInstanceId OBJECT-TYPE
    SYNTAX       CucsManagedObjectId
    MAX-ACCESS   not-accessible
    STATUS       current
    DESCRIPTION
        "Instance identifier of the managed object."
    ::= { cucsEquipmentHwCapDerivativeProviderEntry 1 }

cucsEquipmentHwCapDerivativeProviderDn OBJECT-TYPE
    SYNTAX       CucsManagedObjectDn
    MAX-ACCESS   read-only
    STATUS       current
    DESCRIPTION
        "Cisco UCS equipment:HwCapDerivativeProvider:dn
        managed object property"
    ::= { cucsEquipmentHwCapDerivativeProviderEntry 2 }

cucsEquipmentHwCapDerivativeProviderRn OBJECT-TYPE
    SYNTAX       SnmpAdminString
    MAX-ACCESS   read-only
    STATUS       current
    DESCRIPTION
        "Cisco UCS equipment:HwCapDerivativeProvider:rn
        managed object property"
    ::= { cucsEquipmentHwCapDerivativeProviderEntry 3 }

cucsEquipmentHwCapDerivativeProviderDeleted OBJECT-TYPE
    SYNTAX       TruthValue
    MAX-ACCESS   read-only
    STATUS       current
    DESCRIPTION
        "Cisco UCS equipment:HwCapDerivativeProvider:deleted
        managed object property"
    ::= { cucsEquipmentHwCapDerivativeProviderEntry 4 }

cucsEquipmentHwCapDerivativeProviderDeprecated OBJECT-TYPE
    SYNTAX       TruthValue
    MAX-ACCESS   read-only
    STATUS       current
    DESCRIPTION
        "Cisco UCS equipment:HwCapDerivativeProvider:deprecated
        managed object property"
    ::= { cucsEquipmentHwCapDerivativeProviderEntry 5 }

cucsEquipmentHwCapDerivativeProviderElementLoadFailures OBJECT-TYPE
    SYNTAX       Gauge32
    MAX-ACCESS   read-only
    STATUS       current
    DESCRIPTION
        "Cisco UCS equipment:HwCapDerivativeProvider:elementLoadFailures
        managed object property"
    ::= { cucsEquipmentHwCapDerivativeProviderEntry 6 }

cucsEquipmentHwCapDerivativeProviderElementsLoaded OBJECT-TYPE
    SYNTAX       Gauge32
    MAX-ACCESS   read-only
    STATUS       current
    DESCRIPTION
        "Cisco UCS equipment:HwCapDerivativeProvider:elementsLoaded
        managed object property"
    ::= { cucsEquipmentHwCapDerivativeProviderEntry 7 }

cucsEquipmentHwCapDerivativeProviderGencount OBJECT-TYPE
    SYNTAX       Gauge32
    MAX-ACCESS   read-only
    STATUS       current
    DESCRIPTION
        "Cisco UCS equipment:HwCapDerivativeProvider:gencount
        managed object property"
    ::= { cucsEquipmentHwCapDerivativeProviderEntry 8 }

cucsEquipmentHwCapDerivativeProviderLoadErrors OBJECT-TYPE
    SYNTAX       Gauge32
    MAX-ACCESS   read-only
    STATUS       current
    DESCRIPTION
        "Cisco UCS equipment:HwCapDerivativeProvider:loadErrors
        managed object property"
    ::= { cucsEquipmentHwCapDerivativeProviderEntry 9 }

cucsEquipmentHwCapDerivativeProviderLoadWarnings OBJECT-TYPE
    SYNTAX       Gauge32
    MAX-ACCESS   read-only
    STATUS       current
    DESCRIPTION
        "Cisco UCS equipment:HwCapDerivativeProvider:loadWarnings
        managed object property"
    ::= { cucsEquipmentHwCapDerivativeProviderEntry 10 }

cucsEquipmentHwCapDerivativeProviderMgmtPlaneVer OBJECT-TYPE
    SYNTAX       SnmpAdminString
    MAX-ACCESS   read-only
    STATUS       current
    DESCRIPTION
        "Cisco UCS equipment:HwCapDerivativeProvider:mgmtPlaneVer
        managed object property"
    ::= { cucsEquipmentHwCapDerivativeProviderEntry 11 }

cucsEquipmentHwCapDerivativeProviderModel OBJECT-TYPE
    SYNTAX       SnmpAdminString
    MAX-ACCESS   read-only
    STATUS       current
    DESCRIPTION
        "Cisco UCS equipment:HwCapDerivativeProvider:model
        managed object property"
    ::= { cucsEquipmentHwCapDerivativeProviderEntry 12 }

cucsEquipmentHwCapDerivativeProviderRevision OBJECT-TYPE
    SYNTAX       SnmpAdminString
    MAX-ACCESS   read-only
    STATUS       current
    DESCRIPTION
        "Cisco UCS equipment:HwCapDerivativeProvider:revision
        managed object property"
    ::= { cucsEquipmentHwCapDerivativeProviderEntry 13 }

cucsEquipmentHwCapDerivativeProviderVendor OBJECT-TYPE
    SYNTAX       SnmpAdminString
    MAX-ACCESS   read-only
    STATUS       current
    DESCRIPTION
        "Cisco UCS equipment:HwCapDerivativeProvider:vendor
        managed object property"
    ::= { cucsEquipmentHwCapDerivativeProviderEntry 14 }

cucsEquipmentHwRevisionModifierTable OBJECT-TYPE
    SYNTAX           SEQUENCE OF CucsEquipmentHwRevisionModifierEntry
    MAX-ACCESS       not-accessible
    STATUS           current
    DESCRIPTION
        "Cisco UCS equipment:HwRevisionModifier managed object table"
    ::= { cucsEquipmentObjects 209 }

cucsEquipmentHwRevisionModifierEntry OBJECT-TYPE
    SYNTAX           CucsEquipmentHwRevisionModifierEntry
    MAX-ACCESS       not-accessible
    STATUS           current
    DESCRIPTION
        "Entry for the cucsEquipmentHwRevisionModifierTable table."
    INDEX { cucsEquipmentHwRevisionModifierInstanceId }
    ::= { cucsEquipmentHwRevisionModifierTable 1 }

CucsEquipmentHwRevisionModifierEntry ::= SEQUENCE {
    cucsEquipmentHwRevisionModifierInstanceId                        CucsManagedObjectId,
    cucsEquipmentHwRevisionModifierDn                                CucsManagedObjectDn,
    cucsEquipmentHwRevisionModifierRn                                SnmpAdminString,
    cucsEquipmentHwRevisionModifierHwType                            CucsEquipmentHwType,
    cucsEquipmentHwRevisionModifierRevision                          SnmpAdminString
}

cucsEquipmentHwRevisionModifierInstanceId OBJECT-TYPE
    SYNTAX       CucsManagedObjectId
    MAX-ACCESS   not-accessible
    STATUS       current
    DESCRIPTION
        "Instance identifier of the managed object."
    ::= { cucsEquipmentHwRevisionModifierEntry 1 }

cucsEquipmentHwRevisionModifierDn OBJECT-TYPE
    SYNTAX       CucsManagedObjectDn
    MAX-ACCESS   read-only
    STATUS       current
    DESCRIPTION
        "Cisco UCS equipment:HwRevisionModifier:dn managed
        object property"
    ::= { cucsEquipmentHwRevisionModifierEntry 2 }

cucsEquipmentHwRevisionModifierRn OBJECT-TYPE
    SYNTAX       SnmpAdminString
    MAX-ACCESS   read-only
    STATUS       current
    DESCRIPTION
        "Cisco UCS equipment:HwRevisionModifier:rn managed
        object property"
    ::= { cucsEquipmentHwRevisionModifierEntry 3 }

cucsEquipmentHwRevisionModifierHwType OBJECT-TYPE
    SYNTAX       CucsEquipmentHwType
    MAX-ACCESS   read-only
    STATUS       current
    DESCRIPTION
        "Cisco UCS equipment:HwRevisionModifier:hwType
        managed object property"
    ::= { cucsEquipmentHwRevisionModifierEntry 4 }

cucsEquipmentHwRevisionModifierRevision OBJECT-TYPE
    SYNTAX       SnmpAdminString
    MAX-ACCESS   read-only
    STATUS       current
    DESCRIPTION
        "Cisco UCS equipment:HwRevisionModifier:revision
        managed object property"
    ::= { cucsEquipmentHwRevisionModifierEntry 5 }

cucsEquipmentHxCapTable OBJECT-TYPE
    SYNTAX           SEQUENCE OF CucsEquipmentHxCapEntry
    MAX-ACCESS       not-accessible
    STATUS           current
    DESCRIPTION
        "Cisco UCS equipment:HxCap managed object table"
    ::= { cucsEquipmentObjects 227 }

cucsEquipmentHxCapEntry OBJECT-TYPE
    SYNTAX           CucsEquipmentHxCapEntry
    MAX-ACCESS       not-accessible
    STATUS           current
    DESCRIPTION
        "Entry for the cucsEquipmentHxCapTable table."
    INDEX { cucsEquipmentHxCapInstanceId }
    ::= { cucsEquipmentHxCapTable 1 }

CucsEquipmentHxCapEntry ::= SEQUENCE {
    cucsEquipmentHxCapInstanceId                                     CucsManagedObjectId,
    cucsEquipmentHxCapDn                                             CucsManagedObjectDn,
    cucsEquipmentHxCapRn                                             SnmpAdminString,
    cucsEquipmentHxCapIsSedSupported                                 CucsEquipmentHxCapIsSedSupported,
    cucsEquipmentHxCapIsUsbNicSupported                              CucsEquipmentHxCapIsUsbNicSupported
}

cucsEquipmentHxCapInstanceId OBJECT-TYPE
    SYNTAX       CucsManagedObjectId
    MAX-ACCESS   not-accessible
    STATUS       current
    DESCRIPTION
        "Instance identifier of the managed object."
    ::= { cucsEquipmentHxCapEntry 1 }

cucsEquipmentHxCapDn OBJECT-TYPE
    SYNTAX       CucsManagedObjectDn
    MAX-ACCESS   read-only
    STATUS       current
    DESCRIPTION
        "Cisco UCS equipment:HxCap:dn managed object property"
    ::= { cucsEquipmentHxCapEntry 2 }

cucsEquipmentHxCapRn OBJECT-TYPE
    SYNTAX       SnmpAdminString
    MAX-ACCESS   read-only
    STATUS       current
    DESCRIPTION
        "Cisco UCS equipment:HxCap:rn managed object property"
    ::= { cucsEquipmentHxCapEntry 3 }

cucsEquipmentHxCapIsSedSupported OBJECT-TYPE
    SYNTAX       CucsEquipmentHxCapIsSedSupported
    MAX-ACCESS   read-only
    STATUS       current
    DESCRIPTION
        "Cisco UCS equipment:HxCap:isSedSupported managed object property"
    ::= { cucsEquipmentHxCapEntry 4 }

cucsEquipmentHxCapIsUsbNicSupported OBJECT-TYPE
    SYNTAX       CucsEquipmentHxCapIsUsbNicSupported
    MAX-ACCESS   read-only
    STATUS       current
    DESCRIPTION
        "Cisco UCS equipment:HxCap:isUsbNicSupported managed
        object property"
    ::= { cucsEquipmentHxCapEntry 5 }

cucsEquipmentIOCardTable OBJECT-TYPE
    SYNTAX           SEQUENCE OF CucsEquipmentIOCardEntry
    MAX-ACCESS       not-accessible
    STATUS           current
    DESCRIPTION
        "Cisco UCS equipment:IOCard managed object table"
    ::= { cucsEquipmentObjects 30 }

cucsEquipmentIOCardEntry OBJECT-TYPE
    SYNTAX           CucsEquipmentIOCardEntry
    MAX-ACCESS       not-accessible
    STATUS           current
    DESCRIPTION
        "Entry for the cucsEquipmentIOCardTable table."
    INDEX { cucsEquipmentIOCardInstanceId }
    ::= { cucsEquipmentIOCardTable 1 }

CucsEquipmentIOCardEntry ::= SEQUENCE {
    cucsEquipmentIOCardInstanceId                                    CucsManagedObjectId,
    cucsEquipmentIOCardDn                                            CucsManagedObjectDn,
    cucsEquipmentIOCardRn                                            SnmpAdminString,
    cucsEquipmentIOCardAdminPowerState                               CucsEquipmentAdminPowerState,
    cucsEquipmentIOCardBaseAddr                                      InetAddressIPv4,
    cucsEquipmentIOCardChassisId                                     Gauge32,
    cucsEquipmentIOCardConfigState                                   CucsEquipmentChassisConfigState,
    cucsEquipmentIOCardDiscovery                                     CucsEquipmentDiscoveryState,
    cucsEquipmentIOCardFltAggr                                       Unsigned64,
    cucsEquipmentIOCardFsmDescr                                      SnmpAdminString,
    cucsEquipmentIOCardFsmPrev                                       SnmpAdminString,
    cucsEquipmentIOCardFsmProgr                                      Gauge32,
    cucsEquipmentIOCardFsmRmtInvErrCode                              Gauge32,
    cucsEquipmentIOCardFsmRmtInvErrDescr                             SnmpAdminString,
    cucsEquipmentIOCardFsmRmtInvRslt                                 CucsConditionRemoteInvRslt,
    cucsEquipmentIOCardFsmStageDescr                                 SnmpAdminString,
    cucsEquipmentIOCardFsmStamp                                      DateAndTime,
    cucsEquipmentIOCardFsmStatus                                     SnmpAdminString,
    cucsEquipmentIOCardFsmTry                                        Gauge32,
    cucsEquipmentIOCardId                                            CucsEquipmentIOCardId,
    cucsEquipmentIOCardLcName                                        SnmpAdminString,
    cucsEquipmentIOCardLcTs                                          DateAndTime,
    cucsEquipmentIOCardModel                                         SnmpAdminString,
    cucsEquipmentIOCardOperQualifier                                 CucsEquipmentIOCardIssues,
    cucsEquipmentIOCardOperState                                     CucsEquipmentOperability,
    cucsEquipmentIOCardOperability                                   CucsEquipmentOperability,
    cucsEquipmentIOCardPeerCommStatus                                CucsEquipmentCommStatus,
    cucsEquipmentIOCardPeerDn                                        SnmpAdminString,
    cucsEquipmentIOCardPerf                                          CucsEquipmentSensorThresholdStatus,
    cucsEquipmentIOCardPower                                         CucsEquipmentPowerState,
    cucsEquipmentIOCardPresence                                      CucsEquipmentPresence,
    cucsEquipmentIOCardRevision                                      SnmpAdminString,
    cucsEquipmentIOCardSerial                                        SnmpAdminString,
    cucsEquipmentIOCardSide                                          CucsNetworkSide,
    cucsEquipmentIOCardSwitchId                                      CucsNetworkSwitchId,
    cucsEquipmentIOCardThermal                                       CucsEquipmentSensorThresholdStatus,
    cucsEquipmentIOCardUpgradeStatus                                 CucsMgmtUpgradeStatus,
    cucsEquipmentIOCardUsrLbl                                        SnmpAdminString,
    cucsEquipmentIOCardVendor                                        SnmpAdminString,
    cucsEquipmentIOCardVoltage                                       CucsEquipmentSensorThresholdStatus,
    cucsEquipmentIOCardFeOfflineTs                                   Unsigned64,
    cucsEquipmentIOCardFeReadyTs                                     Unsigned64,
    cucsEquipmentIOCardMfgTime                                       DateAndTime,
    cucsEquipmentIOCardOperQualifierReason                           SnmpAdminString,
    cucsEquipmentIOCardPartNumber                                    SnmpAdminString,
    cucsEquipmentIOCardVid                                           SnmpAdminString,
    cucsEquipmentIOCardFsmFlags                                      SnmpAdminString,
    cucsEquipmentIOCardProcessorThermalState                         CucsEquipmentSensorThresholdStatus,
    cucsEquipmentIOCardAdminState                                    CucsEquipmentChassisAdminState,
    cucsEquipmentIOCardOperEvacState                                 CucsNetworkEvacState,
    cucsEquipmentIOCardAdminPeerPowerState                           CucsEquipmentAdminPowerState,
    cucsEquipmentIOCardAssetTag                                      SnmpAdminString
}

cucsEquipmentIOCardInstanceId OBJECT-TYPE
    SYNTAX       CucsManagedObjectId
    MAX-ACCESS   not-accessible
    STATUS       current
    DESCRIPTION
        "Instance identifier of the managed object."
    ::= { cucsEquipmentIOCardEntry 1 }

cucsEquipmentIOCardDn OBJECT-TYPE
    SYNTAX       CucsManagedObjectDn
    MAX-ACCESS   read-only
    STATUS       current
    DESCRIPTION
        "Cisco UCS equipment:IOCard:dn managed object property"
    ::= { cucsEquipmentIOCardEntry 2 }

cucsEquipmentIOCardRn OBJECT-TYPE
    SYNTAX       SnmpAdminString
    MAX-ACCESS   read-only
    STATUS       current
    DESCRIPTION
        "Cisco UCS equipment:IOCard:rn managed object property"
    ::= { cucsEquipmentIOCardEntry 3 }

cucsEquipmentIOCardAdminPowerState OBJECT-TYPE
    SYNTAX       CucsEquipmentAdminPowerState
    MAX-ACCESS   read-only
    STATUS       current
    DESCRIPTION
        "Cisco UCS equipment:IOCard:adminPowerState managed
        object property"
    ::= { cucsEquipmentIOCardEntry 4 }

cucsEquipmentIOCardBaseAddr OBJECT-TYPE
    SYNTAX       InetAddressIPv4
    MAX-ACCESS   read-only
    STATUS       current
    DESCRIPTION
        "Cisco UCS equipment:IOCard:baseAddr managed object property"
    ::= { cucsEquipmentIOCardEntry 5 }

cucsEquipmentIOCardChassisId OBJECT-TYPE
    SYNTAX       Gauge32
    MAX-ACCESS   read-only
    STATUS       current
    DESCRIPTION
        "Cisco UCS equipment:IOCard:chassisId managed object property"
    ::= { cucsEquipmentIOCardEntry 6 }

cucsEquipmentIOCardConfigState OBJECT-TYPE
    SYNTAX       CucsEquipmentChassisConfigState
    MAX-ACCESS   read-only
    STATUS       current
    DESCRIPTION
        "Cisco UCS equipment:IOCard:configState managed object property"
    ::= { cucsEquipmentIOCardEntry 7 }

cucsEquipmentIOCardDiscovery OBJECT-TYPE
    SYNTAX       CucsEquipmentDiscoveryState
    MAX-ACCESS   read-only
    STATUS       current
    DESCRIPTION
        "Cisco UCS equipment:IOCard:discovery managed object property"
    ::= { cucsEquipmentIOCardEntry 8 }

cucsEquipmentIOCardFltAggr OBJECT-TYPE
    SYNTAX       Unsigned64
    MAX-ACCESS   read-only
    STATUS       current
    DESCRIPTION
        "Cisco UCS equipment:IOCard:fltAggr managed object property"
    ::= { cucsEquipmentIOCardEntry 9 }

cucsEquipmentIOCardFsmDescr OBJECT-TYPE
    SYNTAX       SnmpAdminString
    MAX-ACCESS   read-only
    STATUS       current
    DESCRIPTION
        "Cisco UCS equipment:IOCard:fsmDescr managed object property"
    ::= { cucsEquipmentIOCardEntry 10 }

cucsEquipmentIOCardFsmPrev OBJECT-TYPE
    SYNTAX       SnmpAdminString
    MAX-ACCESS   read-only
    STATUS       current
    DESCRIPTION
        "Cisco UCS equipment:IOCard:fsmPrev managed object property"
    ::= { cucsEquipmentIOCardEntry 11 }

cucsEquipmentIOCardFsmProgr OBJECT-TYPE
    SYNTAX       Gauge32
    MAX-ACCESS   read-only
    STATUS       current
    DESCRIPTION
        "Cisco UCS equipment:IOCard:fsmProgr managed object property"
    ::= { cucsEquipmentIOCardEntry 12 }

cucsEquipmentIOCardFsmRmtInvErrCode OBJECT-TYPE
    SYNTAX       Gauge32
    MAX-ACCESS   read-only
    STATUS       current
    DESCRIPTION
        "Cisco UCS equipment:IOCard:fsmRmtInvErrCode managed
        object property"
    ::= { cucsEquipmentIOCardEntry 13 }

cucsEquipmentIOCardFsmRmtInvErrDescr OBJECT-TYPE
    SYNTAX       SnmpAdminString
    MAX-ACCESS   read-only
    STATUS       current
    DESCRIPTION
        "Cisco UCS equipment:IOCard:fsmRmtInvErrDescr managed
        object property"
    ::= { cucsEquipmentIOCardEntry 14 }

cucsEquipmentIOCardFsmRmtInvRslt OBJECT-TYPE
    SYNTAX       CucsConditionRemoteInvRslt
    MAX-ACCESS   read-only
    STATUS       current
    DESCRIPTION
        "Cisco UCS equipment:IOCard:fsmRmtInvRslt managed object property"
    ::= { cucsEquipmentIOCardEntry 15 }

cucsEquipmentIOCardFsmStageDescr OBJECT-TYPE
    SYNTAX       SnmpAdminString
    MAX-ACCESS   read-only
    STATUS       current
    DESCRIPTION
        "Cisco UCS equipment:IOCard:fsmStageDescr managed object property"
    ::= { cucsEquipmentIOCardEntry 16 }

cucsEquipmentIOCardFsmStamp OBJECT-TYPE
    SYNTAX       DateAndTime
    MAX-ACCESS   read-only
    STATUS       current
    DESCRIPTION
        "Cisco UCS equipment:IOCard:fsmStamp managed object property"
    ::= { cucsEquipmentIOCardEntry 17 }

cucsEquipmentIOCardFsmStatus OBJECT-TYPE
    SYNTAX       SnmpAdminString
    MAX-ACCESS   read-only
    STATUS       current
    DESCRIPTION
        "Cisco UCS equipment:IOCard:fsmStatus managed object property"
    ::= { cucsEquipmentIOCardEntry 18 }

cucsEquipmentIOCardFsmTry OBJECT-TYPE
    SYNTAX       Gauge32
    MAX-ACCESS   read-only
    STATUS       current
    DESCRIPTION
        "Cisco UCS equipment:IOCard:fsmTry managed object property"
    ::= { cucsEquipmentIOCardEntry 19 }

cucsEquipmentIOCardId OBJECT-TYPE
    SYNTAX       CucsEquipmentIOCardId
    MAX-ACCESS   read-only
    STATUS       current
    DESCRIPTION
        "Cisco UCS equipment:IOCard:id managed object property"
    ::= { cucsEquipmentIOCardEntry 20 }

cucsEquipmentIOCardLcName OBJECT-TYPE
    SYNTAX       SnmpAdminString
    MAX-ACCESS   read-only
    STATUS       current
    DESCRIPTION
        "Cisco UCS equipment:IOCard:lcName managed object property"
    ::= { cucsEquipmentIOCardEntry 21 }

cucsEquipmentIOCardLcTs OBJECT-TYPE
    SYNTAX       DateAndTime
    MAX-ACCESS   read-only
    STATUS       current
    DESCRIPTION
        "Cisco UCS equipment:IOCard:lcTs managed object property"
    ::= { cucsEquipmentIOCardEntry 22 }

cucsEquipmentIOCardModel OBJECT-TYPE
    SYNTAX       SnmpAdminString
    MAX-ACCESS   read-only
    STATUS       current
    DESCRIPTION
        "Cisco UCS equipment:IOCard:model managed object property"
    ::= { cucsEquipmentIOCardEntry 23 }

cucsEquipmentIOCardOperQualifier OBJECT-TYPE
    SYNTAX       CucsEquipmentIOCardIssues
    MAX-ACCESS   read-only
    STATUS       current
    DESCRIPTION
        "Cisco UCS equipment:IOCard:operQualifier managed object property"
    ::= { cucsEquipmentIOCardEntry 24 }

cucsEquipmentIOCardOperState OBJECT-TYPE
    SYNTAX       CucsEquipmentOperability
    MAX-ACCESS   read-only
    STATUS       current
    DESCRIPTION
        "Cisco UCS equipment:IOCard:operState managed object property"
    ::= { cucsEquipmentIOCardEntry 25 }

cucsEquipmentIOCardOperability OBJECT-TYPE
    SYNTAX       CucsEquipmentOperability
    MAX-ACCESS   read-only
    STATUS       current
    DESCRIPTION
        "Cisco UCS equipment:IOCard:operability managed object property"
    ::= { cucsEquipmentIOCardEntry 26 }

cucsEquipmentIOCardPeerCommStatus OBJECT-TYPE
    SYNTAX       CucsEquipmentCommStatus
    MAX-ACCESS   read-only
    STATUS       current
    DESCRIPTION
        "Cisco UCS equipment:IOCard:peerCommStatus managed
        object property"
    ::= { cucsEquipmentIOCardEntry 27 }

cucsEquipmentIOCardPeerDn OBJECT-TYPE
    SYNTAX       SnmpAdminString
    MAX-ACCESS   read-only
    STATUS       current
    DESCRIPTION
        "Cisco UCS equipment:IOCard:peerDn managed object property"
    ::= { cucsEquipmentIOCardEntry 28 }

cucsEquipmentIOCardPerf OBJECT-TYPE
    SYNTAX       CucsEquipmentSensorThresholdStatus
    MAX-ACCESS   read-only
    STATUS       current
    DESCRIPTION
        "Cisco UCS equipment:IOCard:perf managed object property"
    ::= { cucsEquipmentIOCardEntry 29 }

cucsEquipmentIOCardPower OBJECT-TYPE
    SYNTAX       CucsEquipmentPowerState
    MAX-ACCESS   read-only
    STATUS       current
    DESCRIPTION
        "Cisco UCS equipment:IOCard:power managed object property"
    ::= { cucsEquipmentIOCardEntry 30 }

cucsEquipmentIOCardPresence OBJECT-TYPE
    SYNTAX       CucsEquipmentPresence
    MAX-ACCESS   read-only
    STATUS       current
    DESCRIPTION
        "Cisco UCS equipment:IOCard:presence managed object property"
    ::= { cucsEquipmentIOCardEntry 31 }

cucsEquipmentIOCardRevision OBJECT-TYPE
    SYNTAX       SnmpAdminString
    MAX-ACCESS   read-only
    STATUS       current
    DESCRIPTION
        "Cisco UCS equipment:IOCard:revision managed object property"
    ::= { cucsEquipmentIOCardEntry 32 }

cucsEquipmentIOCardSerial OBJECT-TYPE
    SYNTAX       SnmpAdminString
    MAX-ACCESS   read-only
    STATUS       current
    DESCRIPTION
        "Cisco UCS equipment:IOCard:serial managed object property"
    ::= { cucsEquipmentIOCardEntry 33 }

cucsEquipmentIOCardSide OBJECT-TYPE
    SYNTAX       CucsNetworkSide
    MAX-ACCESS   read-only
    STATUS       current
    DESCRIPTION
        "Cisco UCS equipment:IOCard:side managed object property"
    ::= { cucsEquipmentIOCardEntry 34 }

cucsEquipmentIOCardSwitchId OBJECT-TYPE
    SYNTAX       CucsNetworkSwitchId
    MAX-ACCESS   read-only
    STATUS       current
    DESCRIPTION
        "Cisco UCS equipment:IOCard:switchId managed object property"
    ::= { cucsEquipmentIOCardEntry 35 }

cucsEquipmentIOCardThermal OBJECT-TYPE
    SYNTAX       CucsEquipmentSensorThresholdStatus
    MAX-ACCESS   read-only
    STATUS       current
    DESCRIPTION
        "Cisco UCS equipment:IOCard:thermal managed object property"
    ::= { cucsEquipmentIOCardEntry 36 }

cucsEquipmentIOCardUpgradeStatus OBJECT-TYPE
    SYNTAX       CucsMgmtUpgradeStatus
    MAX-ACCESS   read-only
    STATUS       current
    DESCRIPTION
        "Cisco UCS equipment:IOCard:upgradeStatus managed object property"
    ::= { cucsEquipmentIOCardEntry 37 }

cucsEquipmentIOCardUsrLbl OBJECT-TYPE
    SYNTAX       SnmpAdminString
    MAX-ACCESS   read-only
    STATUS       current
    DESCRIPTION
        "Cisco UCS equipment:IOCard:usrLbl managed object property"
    ::= { cucsEquipmentIOCardEntry 38 }

cucsEquipmentIOCardVendor OBJECT-TYPE
    SYNTAX       SnmpAdminString
    MAX-ACCESS   read-only
    STATUS       current
    DESCRIPTION
        "Cisco UCS equipment:IOCard:vendor managed object property"
    ::= { cucsEquipmentIOCardEntry 39 }

cucsEquipmentIOCardVoltage OBJECT-TYPE
    SYNTAX       CucsEquipmentSensorThresholdStatus
    MAX-ACCESS   read-only
    STATUS       current
    DESCRIPTION
        "Cisco UCS equipment:IOCard:voltage managed object property"
    ::= { cucsEquipmentIOCardEntry 40 }

cucsEquipmentIOCardFeOfflineTs OBJECT-TYPE
    SYNTAX       Unsigned64
    MAX-ACCESS   read-only
    STATUS       current
    DESCRIPTION
        "Cisco UCS equipment:IOCard:feOfflineTs managed object property"
    ::= { cucsEquipmentIOCardEntry 41 }

cucsEquipmentIOCardFeReadyTs OBJECT-TYPE
    SYNTAX       Unsigned64
    MAX-ACCESS   read-only
    STATUS       current
    DESCRIPTION
        "Cisco UCS equipment:IOCard:feReadyTs managed object property"
    ::= { cucsEquipmentIOCardEntry 42 }

cucsEquipmentIOCardMfgTime OBJECT-TYPE
    SYNTAX       DateAndTime
    MAX-ACCESS   read-only
    STATUS       current
    DESCRIPTION
        "Cisco UCS equipment:IOCard:mfgTime managed object property"
    ::= { cucsEquipmentIOCardEntry 43 }

cucsEquipmentIOCardOperQualifierReason OBJECT-TYPE
    SYNTAX       SnmpAdminString
    MAX-ACCESS   read-only
    STATUS       current
    DESCRIPTION
        "Cisco UCS equipment:IOCard:operQualifierReason
        managed object property"
    ::= { cucsEquipmentIOCardEntry 44 }

cucsEquipmentIOCardPartNumber OBJECT-TYPE
    SYNTAX       SnmpAdminString
    MAX-ACCESS   read-only
    STATUS       current
    DESCRIPTION
        "Cisco UCS equipment:IOCard:partNumber managed object property"
    ::= { cucsEquipmentIOCardEntry 45 }

cucsEquipmentIOCardVid OBJECT-TYPE
    SYNTAX       SnmpAdminString
    MAX-ACCESS   read-only
    STATUS       current
    DESCRIPTION
        "Cisco UCS equipment:IOCard:vid managed object property"
    ::= { cucsEquipmentIOCardEntry 46 }

cucsEquipmentIOCardFsmFlags OBJECT-TYPE
    SYNTAX       SnmpAdminString
    MAX-ACCESS   read-only
    STATUS       current
    DESCRIPTION
        "Cisco UCS equipment:IOCard:fsmFlags managed object property"
    ::= { cucsEquipmentIOCardEntry 47 }

cucsEquipmentIOCardProcessorThermalState OBJECT-TYPE
    SYNTAX       CucsEquipmentSensorThresholdStatus
    MAX-ACCESS   read-only
    STATUS       current
    DESCRIPTION
        "Cisco UCS equipment:IOCard:processorThermalState
        managed object property"
    ::= { cucsEquipmentIOCardEntry 48 }

cucsEquipmentIOCardAdminState OBJECT-TYPE
    SYNTAX       CucsEquipmentChassisAdminState
    MAX-ACCESS   read-only
    STATUS       current
    DESCRIPTION
        "Cisco UCS equipment:IOCard:adminState managed object property"
    ::= { cucsEquipmentIOCardEntry 49 }

cucsEquipmentIOCardOperEvacState OBJECT-TYPE
    SYNTAX       CucsNetworkEvacState
    MAX-ACCESS   read-only
    STATUS       current
    DESCRIPTION
        "Cisco UCS equipment:IOCard:operEvacState managed object property"
    ::= { cucsEquipmentIOCardEntry 50 }

cucsEquipmentIOCardAdminPeerPowerState OBJECT-TYPE
    SYNTAX       CucsEquipmentAdminPowerState
    MAX-ACCESS   read-only
    STATUS       current
    DESCRIPTION
        "Cisco UCS equipment:IOCard:adminPeerPowerState
        managed object property"
    ::= { cucsEquipmentIOCardEntry 51 }

cucsEquipmentIOCardAssetTag OBJECT-TYPE
    SYNTAX       SnmpAdminString
    MAX-ACCESS   read-only
    STATUS       current
    DESCRIPTION
        "Cisco UCS equipment:IOCard:assetTag managed object property"
    ::= { cucsEquipmentIOCardEntry 52 }

cucsEquipmentIOCardBaseFsmTable OBJECT-TYPE
    SYNTAX           SEQUENCE OF CucsEquipmentIOCardBaseFsmEntry
    MAX-ACCESS       not-accessible
    STATUS           current
    DESCRIPTION
        "Cisco UCS equipment:IOCardBaseFsm managed object table"
    ::= { cucsEquipmentObjects 131 }

cucsEquipmentIOCardBaseFsmEntry OBJECT-TYPE
    SYNTAX           CucsEquipmentIOCardBaseFsmEntry
    MAX-ACCESS       not-accessible
    STATUS           current
    DESCRIPTION
        "Entry for the cucsEquipmentIOCardBaseFsmTable table."
    INDEX { cucsEquipmentIOCardBaseFsmInstanceId }
    ::= { cucsEquipmentIOCardBaseFsmTable 1 }

CucsEquipmentIOCardBaseFsmEntry ::= SEQUENCE {
    cucsEquipmentIOCardBaseFsmInstanceId                             CucsManagedObjectId,
    cucsEquipmentIOCardBaseFsmDn                                     CucsManagedObjectDn,
    cucsEquipmentIOCardBaseFsmRn                                     SnmpAdminString,
    cucsEquipmentIOCardBaseFsmCompletionTime                         DateAndTime,
    cucsEquipmentIOCardBaseFsmCurrentFsm                             CucsEquipmentIOCardBaseFsmCurrentFsm,
    cucsEquipmentIOCardBaseFsmDescr                                  SnmpAdminString,
    cucsEquipmentIOCardBaseFsmFsmStatus                              CucsFsmFsmStageStatus,
    cucsEquipmentIOCardBaseFsmProgress                               Gauge32,
    cucsEquipmentIOCardBaseFsmRmtErrCode                             Gauge32,
    cucsEquipmentIOCardBaseFsmRmtErrDescr                            SnmpAdminString,
    cucsEquipmentIOCardBaseFsmRmtRslt                                CucsConditionRemoteInvRslt
}

cucsEquipmentIOCardBaseFsmInstanceId OBJECT-TYPE
    SYNTAX       CucsManagedObjectId
    MAX-ACCESS   not-accessible
    STATUS       current
    DESCRIPTION
        "Instance identifier of the managed object."
    ::= { cucsEquipmentIOCardBaseFsmEntry 1 }

cucsEquipmentIOCardBaseFsmDn OBJECT-TYPE
    SYNTAX       CucsManagedObjectDn
    MAX-ACCESS   read-only
    STATUS       current
    DESCRIPTION
        "Cisco UCS equipment:IOCardBaseFsm:dn managed object property"
    ::= { cucsEquipmentIOCardBaseFsmEntry 2 }

cucsEquipmentIOCardBaseFsmRn OBJECT-TYPE
    SYNTAX       SnmpAdminString
    MAX-ACCESS   read-only
    STATUS       current
    DESCRIPTION
        "Cisco UCS equipment:IOCardBaseFsm:rn managed object property"
    ::= { cucsEquipmentIOCardBaseFsmEntry 3 }

cucsEquipmentIOCardBaseFsmCompletionTime OBJECT-TYPE
    SYNTAX       DateAndTime
    MAX-ACCESS   read-only
    STATUS       current
    DESCRIPTION
        "Cisco UCS equipment:IOCardBaseFsm:completionTime
        managed object property"
    ::= { cucsEquipmentIOCardBaseFsmEntry 4 }

cucsEquipmentIOCardBaseFsmCurrentFsm OBJECT-TYPE
    SYNTAX       CucsEquipmentIOCardBaseFsmCurrentFsm
    MAX-ACCESS   read-only
    STATUS       current
    DESCRIPTION
        "Cisco UCS equipment:IOCardBaseFsm:currentFsm managed
        object property"
    ::= { cucsEquipmentIOCardBaseFsmEntry 5 }

cucsEquipmentIOCardBaseFsmDescr OBJECT-TYPE
    SYNTAX       SnmpAdminString
    MAX-ACCESS   read-only
    STATUS       current
    DESCRIPTION
        "Cisco UCS equipment:IOCardBaseFsm:descr managed object property"
    ::= { cucsEquipmentIOCardBaseFsmEntry 6 }

cucsEquipmentIOCardBaseFsmFsmStatus OBJECT-TYPE
    SYNTAX       CucsFsmFsmStageStatus
    MAX-ACCESS   read-only
    STATUS       current
    DESCRIPTION
        "Cisco UCS equipment:IOCardBaseFsm:fsmStatus managed
        object property"
    ::= { cucsEquipmentIOCardBaseFsmEntry 7 }

cucsEquipmentIOCardBaseFsmProgress OBJECT-TYPE
    SYNTAX       Gauge32
    MAX-ACCESS   read-only
    STATUS       current
    DESCRIPTION
        "Cisco UCS equipment:IOCardBaseFsm:progress managed
        object property"
    ::= { cucsEquipmentIOCardBaseFsmEntry 8 }

cucsEquipmentIOCardBaseFsmRmtErrCode OBJECT-TYPE
    SYNTAX       Gauge32
    MAX-ACCESS   read-only
    STATUS       current
    DESCRIPTION
        "Cisco UCS equipment:IOCardBaseFsm:rmtErrCode managed
        object property"
    ::= { cucsEquipmentIOCardBaseFsmEntry 9 }

cucsEquipmentIOCardBaseFsmRmtErrDescr OBJECT-TYPE
    SYNTAX       SnmpAdminString
    MAX-ACCESS   read-only
    STATUS       current
    DESCRIPTION
        "Cisco UCS equipment:IOCardBaseFsm:rmtErrDescr
        managed object property"
    ::= { cucsEquipmentIOCardBaseFsmEntry 10 }

cucsEquipmentIOCardBaseFsmRmtRslt OBJECT-TYPE
    SYNTAX       CucsConditionRemoteInvRslt
    MAX-ACCESS   read-only
    STATUS       current
    DESCRIPTION
        "Cisco UCS equipment:IOCardBaseFsm:rmtRslt managed
        object property"
    ::= { cucsEquipmentIOCardBaseFsmEntry 11 }

cucsEquipmentIOCardBaseFsmStageTable OBJECT-TYPE
    SYNTAX           SEQUENCE OF CucsEquipmentIOCardBaseFsmStageEntry
    MAX-ACCESS       not-accessible
    STATUS           current
    DESCRIPTION
        "Cisco UCS equipment:IOCardBaseFsmStage managed object table"
    ::= { cucsEquipmentObjects 132 }

cucsEquipmentIOCardBaseFsmStageEntry OBJECT-TYPE
    SYNTAX           CucsEquipmentIOCardBaseFsmStageEntry
    MAX-ACCESS       not-accessible
    STATUS           current
    DESCRIPTION
        "Entry for the cucsEquipmentIOCardBaseFsmStageTable table."
    INDEX { cucsEquipmentIOCardBaseFsmStageInstanceId }
    ::= { cucsEquipmentIOCardBaseFsmStageTable 1 }

CucsEquipmentIOCardBaseFsmStageEntry ::= SEQUENCE {
    cucsEquipmentIOCardBaseFsmStageInstanceId                        CucsManagedObjectId,
    cucsEquipmentIOCardBaseFsmStageDn                                CucsManagedObjectDn,
    cucsEquipmentIOCardBaseFsmStageRn                                SnmpAdminString,
    cucsEquipmentIOCardBaseFsmStageDescr                             SnmpAdminString,
    cucsEquipmentIOCardBaseFsmStageLastUpdateTime                    DateAndTime,
    cucsEquipmentIOCardBaseFsmStageName                              CucsEquipmentIOCardBaseFsmStageName,
    cucsEquipmentIOCardBaseFsmStageOrder                             Gauge32,
    cucsEquipmentIOCardBaseFsmStageRetry                             Gauge32,
    cucsEquipmentIOCardBaseFsmStageStageStatus                       CucsFsmFsmStageStatus
}

cucsEquipmentIOCardBaseFsmStageInstanceId OBJECT-TYPE
    SYNTAX       CucsManagedObjectId
    MAX-ACCESS   not-accessible
    STATUS       current
    DESCRIPTION
        "Instance identifier of the managed object."
    ::= { cucsEquipmentIOCardBaseFsmStageEntry 1 }

cucsEquipmentIOCardBaseFsmStageDn OBJECT-TYPE
    SYNTAX       CucsManagedObjectDn
    MAX-ACCESS   read-only
    STATUS       current
    DESCRIPTION
        "Cisco UCS equipment:IOCardBaseFsmStage:dn managed
        object property"
    ::= { cucsEquipmentIOCardBaseFsmStageEntry 2 }

cucsEquipmentIOCardBaseFsmStageRn OBJECT-TYPE
    SYNTAX       SnmpAdminString
    MAX-ACCESS   read-only
    STATUS       current
    DESCRIPTION
        "Cisco UCS equipment:IOCardBaseFsmStage:rn managed
        object property"
    ::= { cucsEquipmentIOCardBaseFsmStageEntry 3 }

cucsEquipmentIOCardBaseFsmStageDescr OBJECT-TYPE
    SYNTAX       SnmpAdminString
    MAX-ACCESS   read-only
    STATUS       current
    DESCRIPTION
        "Cisco UCS equipment:IOCardBaseFsmStage:descr managed
        object property"
    ::= { cucsEquipmentIOCardBaseFsmStageEntry 4 }

cucsEquipmentIOCardBaseFsmStageLastUpdateTime OBJECT-TYPE
    SYNTAX       DateAndTime
    MAX-ACCESS   read-only
    STATUS       current
    DESCRIPTION
        "Cisco UCS equipment:IOCardBaseFsmStage:lastUpdateTime
        managed object property"
    ::= { cucsEquipmentIOCardBaseFsmStageEntry 5 }

cucsEquipmentIOCardBaseFsmStageName OBJECT-TYPE
    SYNTAX       CucsEquipmentIOCardBaseFsmStageName
    MAX-ACCESS   read-only
    STATUS       current
    DESCRIPTION
        "Cisco UCS equipment:IOCardBaseFsmStage:name managed
        object property"
    ::= { cucsEquipmentIOCardBaseFsmStageEntry 6 }

cucsEquipmentIOCardBaseFsmStageOrder OBJECT-TYPE
    SYNTAX       Gauge32
    MAX-ACCESS   read-only
    STATUS       current
    DESCRIPTION
        "Cisco UCS equipment:IOCardBaseFsmStage:order managed
        object property"
    ::= { cucsEquipmentIOCardBaseFsmStageEntry 7 }

cucsEquipmentIOCardBaseFsmStageRetry OBJECT-TYPE
    SYNTAX       Gauge32
    MAX-ACCESS   read-only
    STATUS       current
    DESCRIPTION
        "Cisco UCS equipment:IOCardBaseFsmStage:retry managed
        object property"
    ::= { cucsEquipmentIOCardBaseFsmStageEntry 8 }

cucsEquipmentIOCardBaseFsmStageStageStatus OBJECT-TYPE
    SYNTAX       CucsFsmFsmStageStatus
    MAX-ACCESS   read-only
    STATUS       current
    DESCRIPTION
        "Cisco UCS equipment:IOCardBaseFsmStage:stageStatus
        managed object property"
    ::= { cucsEquipmentIOCardBaseFsmStageEntry 9 }

cucsEquipmentIOCardBaseFsmTaskTable OBJECT-TYPE
    SYNTAX           SEQUENCE OF CucsEquipmentIOCardBaseFsmTaskEntry
    MAX-ACCESS       not-accessible
    STATUS           current
    DESCRIPTION
        "Cisco UCS equipment:IOCardBaseFsmTask managed object table"
    ::= { cucsEquipmentObjects 133 }

cucsEquipmentIOCardBaseFsmTaskEntry OBJECT-TYPE
    SYNTAX           CucsEquipmentIOCardBaseFsmTaskEntry
    MAX-ACCESS       not-accessible
    STATUS           current
    DESCRIPTION
        "Entry for the cucsEquipmentIOCardBaseFsmTaskTable table."
    INDEX { cucsEquipmentIOCardBaseFsmTaskInstanceId }
    ::= { cucsEquipmentIOCardBaseFsmTaskTable 1 }

CucsEquipmentIOCardBaseFsmTaskEntry ::= SEQUENCE {
    cucsEquipmentIOCardBaseFsmTaskInstanceId                         CucsManagedObjectId,
    cucsEquipmentIOCardBaseFsmTaskDn                                 CucsManagedObjectDn,
    cucsEquipmentIOCardBaseFsmTaskRn                                 SnmpAdminString,
    cucsEquipmentIOCardBaseFsmTaskCompletion                         CucsFsmCompletion,
    cucsEquipmentIOCardBaseFsmTaskFlags                              CucsEquipmentIOCardBaseFsmTaskFlags,
    cucsEquipmentIOCardBaseFsmTaskItem                               CucsEquipmentIOCardBaseFsmTaskItem,
    cucsEquipmentIOCardBaseFsmTaskSeqId                              Gauge32
}

cucsEquipmentIOCardBaseFsmTaskInstanceId OBJECT-TYPE
    SYNTAX       CucsManagedObjectId
    MAX-ACCESS   not-accessible
    STATUS       current
    DESCRIPTION
        "Instance identifier of the managed object."
    ::= { cucsEquipmentIOCardBaseFsmTaskEntry 1 }

cucsEquipmentIOCardBaseFsmTaskDn OBJECT-TYPE
    SYNTAX       CucsManagedObjectDn
    MAX-ACCESS   read-only
    STATUS       current
    DESCRIPTION
        "Cisco UCS equipment:IOCardBaseFsmTask:dn managed object property"
    ::= { cucsEquipmentIOCardBaseFsmTaskEntry 2 }

cucsEquipmentIOCardBaseFsmTaskRn OBJECT-TYPE
    SYNTAX       SnmpAdminString
    MAX-ACCESS   read-only
    STATUS       current
    DESCRIPTION
        "Cisco UCS equipment:IOCardBaseFsmTask:rn managed object property"
    ::= { cucsEquipmentIOCardBaseFsmTaskEntry 3 }

cucsEquipmentIOCardBaseFsmTaskCompletion OBJECT-TYPE
    SYNTAX       CucsFsmCompletion
    MAX-ACCESS   read-only
    STATUS       current
    DESCRIPTION
        "Cisco UCS equipment:IOCardBaseFsmTask:completion
        managed object property"
    ::= { cucsEquipmentIOCardBaseFsmTaskEntry 4 }

cucsEquipmentIOCardBaseFsmTaskFlags OBJECT-TYPE
    SYNTAX       CucsEquipmentIOCardBaseFsmTaskFlags
    MAX-ACCESS   read-only
    STATUS       current
    DESCRIPTION
        "Cisco UCS equipment:IOCardBaseFsmTask:flags managed
        object property"
    ::= { cucsEquipmentIOCardBaseFsmTaskEntry 5 }

cucsEquipmentIOCardBaseFsmTaskItem OBJECT-TYPE
    SYNTAX       CucsEquipmentIOCardBaseFsmTaskItem
    MAX-ACCESS   read-only
    STATUS       current
    DESCRIPTION
        "Cisco UCS equipment:IOCardBaseFsmTask:item managed
        object property"
    ::= { cucsEquipmentIOCardBaseFsmTaskEntry 6 }

cucsEquipmentIOCardBaseFsmTaskSeqId OBJECT-TYPE
    SYNTAX       Gauge32
    MAX-ACCESS   read-only
    STATUS       current
    DESCRIPTION
        "Cisco UCS equipment:IOCardBaseFsmTask:seqId managed
        object property"
    ::= { cucsEquipmentIOCardBaseFsmTaskEntry 7 }

cucsEquipmentIOCardCapProviderTable OBJECT-TYPE
    SYNTAX           SEQUENCE OF CucsEquipmentIOCardCapProviderEntry
    MAX-ACCESS       not-accessible
    STATUS           current
    DESCRIPTION
        "Cisco UCS equipment:IOCardCapProvider managed object table"
    ::= { cucsEquipmentObjects 31 }

cucsEquipmentIOCardCapProviderEntry OBJECT-TYPE
    SYNTAX           CucsEquipmentIOCardCapProviderEntry
    MAX-ACCESS       not-accessible
    STATUS           current
    DESCRIPTION
        "Entry for the cucsEquipmentIOCardCapProviderTable table."
    INDEX { cucsEquipmentIOCardCapProviderInstanceId }
    ::= { cucsEquipmentIOCardCapProviderTable 1 }

CucsEquipmentIOCardCapProviderEntry ::= SEQUENCE {
    cucsEquipmentIOCardCapProviderInstanceId                         CucsManagedObjectId,
    cucsEquipmentIOCardCapProviderDn                                 CucsManagedObjectDn,
    cucsEquipmentIOCardCapProviderRn                                 SnmpAdminString,
    cucsEquipmentIOCardCapProviderDeprecated                         TruthValue,
    cucsEquipmentIOCardCapProviderGencount                           Gauge32,
    cucsEquipmentIOCardCapProviderMgmtPlaneVer                       SnmpAdminString,
    cucsEquipmentIOCardCapProviderModel                              SnmpAdminString,
    cucsEquipmentIOCardCapProviderRevision                           SnmpAdminString,
    cucsEquipmentIOCardCapProviderVendor                             SnmpAdminString,
    cucsEquipmentIOCardCapProviderPromCardType                       Gauge32,
    cucsEquipmentIOCardCapProviderDeleted                            TruthValue,
    cucsEquipmentIOCardCapProviderElementLoadFailures                Gauge32,
    cucsEquipmentIOCardCapProviderElementsLoaded                     Gauge32,
    cucsEquipmentIOCardCapProviderLoadErrors                         Gauge32,
    cucsEquipmentIOCardCapProviderLoadWarnings                       Gauge32
}

cucsEquipmentIOCardCapProviderInstanceId OBJECT-TYPE
    SYNTAX       CucsManagedObjectId
    MAX-ACCESS   not-accessible
    STATUS       current
    DESCRIPTION
        "Instance identifier of the managed object."
    ::= { cucsEquipmentIOCardCapProviderEntry 1 }

cucsEquipmentIOCardCapProviderDn OBJECT-TYPE
    SYNTAX       CucsManagedObjectDn
    MAX-ACCESS   read-only
    STATUS       current
    DESCRIPTION
        "Cisco UCS equipment:IOCardCapProvider:dn managed object property"
    ::= { cucsEquipmentIOCardCapProviderEntry 2 }

cucsEquipmentIOCardCapProviderRn OBJECT-TYPE
    SYNTAX       SnmpAdminString
    MAX-ACCESS   read-only
    STATUS       current
    DESCRIPTION
        "Cisco UCS equipment:IOCardCapProvider:rn managed object property"
    ::= { cucsEquipmentIOCardCapProviderEntry 3 }

cucsEquipmentIOCardCapProviderDeprecated OBJECT-TYPE
    SYNTAX       TruthValue
    MAX-ACCESS   read-only
    STATUS       current
    DESCRIPTION
        "Cisco UCS equipment:IOCardCapProvider:deprecated
        managed object property"
    ::= { cucsEquipmentIOCardCapProviderEntry 4 }

cucsEquipmentIOCardCapProviderGencount OBJECT-TYPE
    SYNTAX       Gauge32
    MAX-ACCESS   read-only
    STATUS       current
    DESCRIPTION
        "Cisco UCS equipment:IOCardCapProvider:gencount
        managed object property"
    ::= { cucsEquipmentIOCardCapProviderEntry 5 }

cucsEquipmentIOCardCapProviderMgmtPlaneVer OBJECT-TYPE
    SYNTAX       SnmpAdminString
    MAX-ACCESS   read-only
    STATUS       current
    DESCRIPTION
        "Cisco UCS equipment:IOCardCapProvider:mgmtPlaneVer
        managed object property"
    ::= { cucsEquipmentIOCardCapProviderEntry 6 }

cucsEquipmentIOCardCapProviderModel OBJECT-TYPE
    SYNTAX       SnmpAdminString
    MAX-ACCESS   read-only
    STATUS       current
    DESCRIPTION
        "Cisco UCS equipment:IOCardCapProvider:model managed
        object property"
    ::= { cucsEquipmentIOCardCapProviderEntry 7 }

cucsEquipmentIOCardCapProviderRevision OBJECT-TYPE
    SYNTAX       SnmpAdminString
    MAX-ACCESS   read-only
    STATUS       current
    DESCRIPTION
        "Cisco UCS equipment:IOCardCapProvider:revision
        managed object property"
    ::= { cucsEquipmentIOCardCapProviderEntry 8 }

cucsEquipmentIOCardCapProviderVendor OBJECT-TYPE
    SYNTAX       SnmpAdminString
    MAX-ACCESS   read-only
    STATUS       current
    DESCRIPTION
        "Cisco UCS equipment:IOCardCapProvider:vendor managed
        object property"
    ::= { cucsEquipmentIOCardCapProviderEntry 9 }

cucsEquipmentIOCardCapProviderPromCardType OBJECT-TYPE
    SYNTAX       Gauge32
    MAX-ACCESS   read-only
    STATUS       current
    DESCRIPTION
        "Cisco UCS equipment:IOCardCapProvider:promCardType
        managed object property"
    ::= { cucsEquipmentIOCardCapProviderEntry 10 }

cucsEquipmentIOCardCapProviderDeleted OBJECT-TYPE
    SYNTAX       TruthValue
    MAX-ACCESS   read-only
    STATUS       current
    DESCRIPTION
        "Cisco UCS equipment:IOCardCapProvider:deleted
        managed object property"
    ::= { cucsEquipmentIOCardCapProviderEntry 11 }

cucsEquipmentIOCardCapProviderElementLoadFailures OBJECT-TYPE
    SYNTAX       Gauge32
    MAX-ACCESS   read-only
    STATUS       current
    DESCRIPTION
        "Cisco UCS equipment:IOCardCapProvider:elementLoadFailures
        managed object property"
    ::= { cucsEquipmentIOCardCapProviderEntry 12 }

cucsEquipmentIOCardCapProviderElementsLoaded OBJECT-TYPE
    SYNTAX       Gauge32
    MAX-ACCESS   read-only
    STATUS       current
    DESCRIPTION
        "Cisco UCS equipment:IOCardCapProvider:elementsLoaded
        managed object property"
    ::= { cucsEquipmentIOCardCapProviderEntry 13 }

cucsEquipmentIOCardCapProviderLoadErrors OBJECT-TYPE
    SYNTAX       Gauge32
    MAX-ACCESS   read-only
    STATUS       current
    DESCRIPTION
        "Cisco UCS equipment:IOCardCapProvider:loadErrors
        managed object property"
    ::= { cucsEquipmentIOCardCapProviderEntry 14 }

cucsEquipmentIOCardCapProviderLoadWarnings OBJECT-TYPE
    SYNTAX       Gauge32
    MAX-ACCESS   read-only
    STATUS       current
    DESCRIPTION
        "Cisco UCS equipment:IOCardCapProvider:loadWarnings
        managed object property"
    ::= { cucsEquipmentIOCardCapProviderEntry 15 }

cucsEquipmentIOCardFsmTable OBJECT-TYPE
    SYNTAX           SEQUENCE OF CucsEquipmentIOCardFsmEntry
    MAX-ACCESS       not-accessible
    STATUS           current
    DESCRIPTION
        "Cisco UCS equipment:IOCardFsm managed object table"
    ::= { cucsEquipmentObjects 109 }

cucsEquipmentIOCardFsmEntry OBJECT-TYPE
    SYNTAX           CucsEquipmentIOCardFsmEntry
    MAX-ACCESS       not-accessible
    STATUS           current
    DESCRIPTION
        "Entry for the cucsEquipmentIOCardFsmTable table."
    INDEX { cucsEquipmentIOCardFsmInstanceId }
    ::= { cucsEquipmentIOCardFsmTable 1 }

CucsEquipmentIOCardFsmEntry ::= SEQUENCE {
    cucsEquipmentIOCardFsmInstanceId                                 CucsManagedObjectId,
    cucsEquipmentIOCardFsmDn                                         CucsManagedObjectDn,
    cucsEquipmentIOCardFsmRn                                         SnmpAdminString,
    cucsEquipmentIOCardFsmCompletionTime                             DateAndTime,
    cucsEquipmentIOCardFsmCurrentFsm                                 CucsEquipmentIOCardFsmCurrentFsm,
    cucsEquipmentIOCardFsmDescrData                                  SnmpAdminString,
    cucsEquipmentIOCardFsmFsmStatus                                  CucsFsmFsmStageStatus,
    cucsEquipmentIOCardFsmProgress                                   Gauge32,
    cucsEquipmentIOCardFsmRmtErrCode                                 Gauge32,
    cucsEquipmentIOCardFsmRmtErrDescr                                SnmpAdminString,
    cucsEquipmentIOCardFsmRmtRslt                                    CucsConditionRemoteInvRslt
}

cucsEquipmentIOCardFsmInstanceId OBJECT-TYPE
    SYNTAX       CucsManagedObjectId
    MAX-ACCESS   not-accessible
    STATUS       current
    DESCRIPTION
        "Instance identifier of the managed object."
    ::= { cucsEquipmentIOCardFsmEntry 1 }

cucsEquipmentIOCardFsmDn OBJECT-TYPE
    SYNTAX       CucsManagedObjectDn
    MAX-ACCESS   read-only
    STATUS       current
    DESCRIPTION
        "Cisco UCS equipment:IOCardFsm:dn managed object property"
    ::= { cucsEquipmentIOCardFsmEntry 2 }

cucsEquipmentIOCardFsmRn OBJECT-TYPE
    SYNTAX       SnmpAdminString
    MAX-ACCESS   read-only
    STATUS       current
    DESCRIPTION
        "Cisco UCS equipment:IOCardFsm:rn managed object property"
    ::= { cucsEquipmentIOCardFsmEntry 3 }

cucsEquipmentIOCardFsmCompletionTime OBJECT-TYPE
    SYNTAX       DateAndTime
    MAX-ACCESS   read-only
    STATUS       current
    DESCRIPTION
        "Cisco UCS equipment:IOCardFsm:completionTime managed
        object property"
    ::= { cucsEquipmentIOCardFsmEntry 4 }

cucsEquipmentIOCardFsmCurrentFsm OBJECT-TYPE
    SYNTAX       CucsEquipmentIOCardFsmCurrentFsm
    MAX-ACCESS   read-only
    STATUS       current
    DESCRIPTION
        "Cisco UCS equipment:IOCardFsm:currentFsm managed object property"
    ::= { cucsEquipmentIOCardFsmEntry 5 }

cucsEquipmentIOCardFsmDescrData OBJECT-TYPE
    SYNTAX       SnmpAdminString
    MAX-ACCESS   read-only
    STATUS       current
    DESCRIPTION
        "Cisco UCS equipment:IOCardFsm:descr managed object property"
    ::= { cucsEquipmentIOCardFsmEntry 6 }

cucsEquipmentIOCardFsmFsmStatus OBJECT-TYPE
    SYNTAX       CucsFsmFsmStageStatus
    MAX-ACCESS   read-only
    STATUS       current
    DESCRIPTION
        "Cisco UCS equipment:IOCardFsm:fsmStatus managed object property"
    ::= { cucsEquipmentIOCardFsmEntry 7 }

cucsEquipmentIOCardFsmProgress OBJECT-TYPE
    SYNTAX       Gauge32
    MAX-ACCESS   read-only
    STATUS       current
    DESCRIPTION
        "Cisco UCS equipment:IOCardFsm:progress managed object property"
    ::= { cucsEquipmentIOCardFsmEntry 8 }

cucsEquipmentIOCardFsmRmtErrCode OBJECT-TYPE
    SYNTAX       Gauge32
    MAX-ACCESS   read-only
    STATUS       current
    DESCRIPTION
        "Cisco UCS equipment:IOCardFsm:rmtErrCode managed object property"
    ::= { cucsEquipmentIOCardFsmEntry 9 }

cucsEquipmentIOCardFsmRmtErrDescr OBJECT-TYPE
    SYNTAX       SnmpAdminString
    MAX-ACCESS   read-only
    STATUS       current
    DESCRIPTION
        "Cisco UCS equipment:IOCardFsm:rmtErrDescr managed
        object property"
    ::= { cucsEquipmentIOCardFsmEntry 10 }

cucsEquipmentIOCardFsmRmtRslt OBJECT-TYPE
    SYNTAX       CucsConditionRemoteInvRslt
    MAX-ACCESS   read-only
    STATUS       current
    DESCRIPTION
        "Cisco UCS equipment:IOCardFsm:rmtRslt managed object property"
    ::= { cucsEquipmentIOCardFsmEntry 11 }

cucsEquipmentIOCardFsmStageTable OBJECT-TYPE
    SYNTAX           SEQUENCE OF CucsEquipmentIOCardFsmStageEntry
    MAX-ACCESS       not-accessible
    STATUS           current
    DESCRIPTION
        "Cisco UCS equipment:IOCardFsmStage managed object table"
    ::= { cucsEquipmentObjects 110 }

cucsEquipmentIOCardFsmStageEntry OBJECT-TYPE
    SYNTAX           CucsEquipmentIOCardFsmStageEntry
    MAX-ACCESS       not-accessible
    STATUS           current
    DESCRIPTION
        "Entry for the cucsEquipmentIOCardFsmStageTable table."
    INDEX { cucsEquipmentIOCardFsmStageInstanceId }
    ::= { cucsEquipmentIOCardFsmStageTable 1 }

CucsEquipmentIOCardFsmStageEntry ::= SEQUENCE {
    cucsEquipmentIOCardFsmStageInstanceId                            CucsManagedObjectId,
    cucsEquipmentIOCardFsmStageDn                                    CucsManagedObjectDn,
    cucsEquipmentIOCardFsmStageRn                                    SnmpAdminString,
    cucsEquipmentIOCardFsmStageDescrData                             SnmpAdminString,
    cucsEquipmentIOCardFsmStageLastUpdateTime                        DateAndTime,
    cucsEquipmentIOCardFsmStageName                                  CucsEquipmentIOCardFsmStageName,
    cucsEquipmentIOCardFsmStageOrder                                 Gauge32,
    cucsEquipmentIOCardFsmStageRetry                                 Gauge32,
    cucsEquipmentIOCardFsmStageStageStatus                           CucsFsmFsmStageStatus
}

cucsEquipmentIOCardFsmStageInstanceId OBJECT-TYPE
    SYNTAX       CucsManagedObjectId
    MAX-ACCESS   not-accessible
    STATUS       current
    DESCRIPTION
        "Instance identifier of the managed object."
    ::= { cucsEquipmentIOCardFsmStageEntry 1 }

cucsEquipmentIOCardFsmStageDn OBJECT-TYPE
    SYNTAX       CucsManagedObjectDn
    MAX-ACCESS   read-only
    STATUS       current
    DESCRIPTION
        "Cisco UCS equipment:IOCardFsmStage:dn managed object property"
    ::= { cucsEquipmentIOCardFsmStageEntry 2 }

cucsEquipmentIOCardFsmStageRn OBJECT-TYPE
    SYNTAX       SnmpAdminString
    MAX-ACCESS   read-only
    STATUS       current
    DESCRIPTION
        "Cisco UCS equipment:IOCardFsmStage:rn managed object property"
    ::= { cucsEquipmentIOCardFsmStageEntry 3 }

cucsEquipmentIOCardFsmStageDescrData OBJECT-TYPE
    SYNTAX       SnmpAdminString
    MAX-ACCESS   read-only
    STATUS       current
    DESCRIPTION
        "Cisco UCS equipment:IOCardFsmStage:descr managed object property"
    ::= { cucsEquipmentIOCardFsmStageEntry 4 }

cucsEquipmentIOCardFsmStageLastUpdateTime OBJECT-TYPE
    SYNTAX       DateAndTime
    MAX-ACCESS   read-only
    STATUS       current
    DESCRIPTION
        "Cisco UCS equipment:IOCardFsmStage:lastUpdateTime
        managed object property"
    ::= { cucsEquipmentIOCardFsmStageEntry 5 }

cucsEquipmentIOCardFsmStageName OBJECT-TYPE
    SYNTAX       CucsEquipmentIOCardFsmStageName
    MAX-ACCESS   read-only
    STATUS       current
    DESCRIPTION
        "Cisco UCS equipment:IOCardFsmStage:name managed object property"
    ::= { cucsEquipmentIOCardFsmStageEntry 6 }

cucsEquipmentIOCardFsmStageOrder OBJECT-TYPE
    SYNTAX       Gauge32
    MAX-ACCESS   read-only
    STATUS       current
    DESCRIPTION
        "Cisco UCS equipment:IOCardFsmStage:order managed object property"
    ::= { cucsEquipmentIOCardFsmStageEntry 7 }

cucsEquipmentIOCardFsmStageRetry OBJECT-TYPE
    SYNTAX       Gauge32
    MAX-ACCESS   read-only
    STATUS       current
    DESCRIPTION
        "Cisco UCS equipment:IOCardFsmStage:retry managed object property"
    ::= { cucsEquipmentIOCardFsmStageEntry 8 }

cucsEquipmentIOCardFsmStageStageStatus OBJECT-TYPE
    SYNTAX       CucsFsmFsmStageStatus
    MAX-ACCESS   read-only
    STATUS       current
    DESCRIPTION
        "Cisco UCS equipment:IOCardFsmStage:stageStatus
        managed object property"
    ::= { cucsEquipmentIOCardFsmStageEntry 9 }

cucsEquipmentIOCardFsmTaskTable OBJECT-TYPE
    SYNTAX           SEQUENCE OF CucsEquipmentIOCardFsmTaskEntry
    MAX-ACCESS       not-accessible
    STATUS           current
    DESCRIPTION
        "Cisco UCS equipment:IOCardFsmTask managed object table"
    ::= { cucsEquipmentObjects 32 }

cucsEquipmentIOCardFsmTaskEntry OBJECT-TYPE
    SYNTAX           CucsEquipmentIOCardFsmTaskEntry
    MAX-ACCESS       not-accessible
    STATUS           current
    DESCRIPTION
        "Entry for the cucsEquipmentIOCardFsmTaskTable table."
    INDEX { cucsEquipmentIOCardFsmTaskInstanceId }
    ::= { cucsEquipmentIOCardFsmTaskTable 1 }

CucsEquipmentIOCardFsmTaskEntry ::= SEQUENCE {
    cucsEquipmentIOCardFsmTaskInstanceId                             CucsManagedObjectId,
    cucsEquipmentIOCardFsmTaskDn                                     CucsManagedObjectDn,
    cucsEquipmentIOCardFsmTaskRn                                     SnmpAdminString,
    cucsEquipmentIOCardFsmTaskCompletion                             CucsFsmCompletion,
    cucsEquipmentIOCardFsmTaskFlags                                  CucsFsmFlags,
    cucsEquipmentIOCardFsmTaskItem                                   CucsEquipmentIOCardFsmTaskItem,
    cucsEquipmentIOCardFsmTaskSeqId                                  Gauge32
}

cucsEquipmentIOCardFsmTaskInstanceId OBJECT-TYPE
    SYNTAX       CucsManagedObjectId
    MAX-ACCESS   not-accessible
    STATUS       current
    DESCRIPTION
        "Instance identifier of the managed object."
    ::= { cucsEquipmentIOCardFsmTaskEntry 1 }

cucsEquipmentIOCardFsmTaskDn OBJECT-TYPE
    SYNTAX       CucsManagedObjectDn
    MAX-ACCESS   read-only
    STATUS       current
    DESCRIPTION
        "Cisco UCS equipment:IOCardFsmTask:dn managed object property"
    ::= { cucsEquipmentIOCardFsmTaskEntry 2 }

cucsEquipmentIOCardFsmTaskRn OBJECT-TYPE
    SYNTAX       SnmpAdminString
    MAX-ACCESS   read-only
    STATUS       current
    DESCRIPTION
        "Cisco UCS equipment:IOCardFsmTask:rn managed object property"
    ::= { cucsEquipmentIOCardFsmTaskEntry 3 }

cucsEquipmentIOCardFsmTaskCompletion OBJECT-TYPE
    SYNTAX       CucsFsmCompletion
    MAX-ACCESS   read-only
    STATUS       current
    DESCRIPTION
        "Cisco UCS equipment:IOCardFsmTask:completion managed
        object property"
    ::= { cucsEquipmentIOCardFsmTaskEntry 4 }

cucsEquipmentIOCardFsmTaskFlags OBJECT-TYPE
    SYNTAX       CucsFsmFlags
    MAX-ACCESS   read-only
    STATUS       current
    DESCRIPTION
        "Cisco UCS equipment:IOCardFsmTask:flags managed object property"
    ::= { cucsEquipmentIOCardFsmTaskEntry 5 }

cucsEquipmentIOCardFsmTaskItem OBJECT-TYPE
    SYNTAX       CucsEquipmentIOCardFsmTaskItem
    MAX-ACCESS   read-only
    STATUS       current
    DESCRIPTION
        "Cisco UCS equipment:IOCardFsmTask:item managed object property"
    ::= { cucsEquipmentIOCardFsmTaskEntry 6 }

cucsEquipmentIOCardFsmTaskSeqId OBJECT-TYPE
    SYNTAX       Gauge32
    MAX-ACCESS   read-only
    STATUS       current
    DESCRIPTION
        "Cisco UCS equipment:IOCardFsmTask:seqId managed object property"
    ::= { cucsEquipmentIOCardFsmTaskEntry 7 }

cucsEquipmentIOCardStatsTable OBJECT-TYPE
    SYNTAX           SEQUENCE OF CucsEquipmentIOCardStatsEntry
    MAX-ACCESS       not-accessible
    STATUS           current
    DESCRIPTION
        "Cisco UCS equipment:IOCardStats managed object table"
    ::= { cucsEquipmentObjects 33 }

cucsEquipmentIOCardStatsEntry OBJECT-TYPE
    SYNTAX           CucsEquipmentIOCardStatsEntry
    MAX-ACCESS       not-accessible
    STATUS           current
    DESCRIPTION
        "Entry for the cucsEquipmentIOCardStatsTable table."
    INDEX { cucsEquipmentIOCardStatsInstanceId }
    ::= { cucsEquipmentIOCardStatsTable 1 }

CucsEquipmentIOCardStatsEntry ::= SEQUENCE {
    cucsEquipmentIOCardStatsInstanceId                               CucsManagedObjectId,
    cucsEquipmentIOCardStatsDn                                       CucsManagedObjectDn,
    cucsEquipmentIOCardStatsRn                                       SnmpAdminString,
    cucsEquipmentIOCardStatsAmbientTemp                              INTEGER,
    cucsEquipmentIOCardStatsAmbientTempAvg                           INTEGER,
    cucsEquipmentIOCardStatsAmbientTempMax                           INTEGER,
    cucsEquipmentIOCardStatsAmbientTempMin                           INTEGER,
    cucsEquipmentIOCardStatsIntervals                                Gauge32,
    cucsEquipmentIOCardStatsSuspect                                  TruthValue,
    cucsEquipmentIOCardStatsTemp                                     INTEGER,
    cucsEquipmentIOCardStatsTempAvg                                  INTEGER,
    cucsEquipmentIOCardStatsTempMax                                  INTEGER,
    cucsEquipmentIOCardStatsTempMin                                  INTEGER,
    cucsEquipmentIOCardStatsThresholded                              CucsEquipmentIOCardStatsThresholded,
    cucsEquipmentIOCardStatsTimeCollected                            DateAndTime,
    cucsEquipmentIOCardStatsUpdate                                   Gauge32,
    cucsEquipmentIOCardStatsDimmTemp                                 SnmpAdminString,
    cucsEquipmentIOCardStatsDimmTempAvg                              SnmpAdminString,
    cucsEquipmentIOCardStatsDimmTempMax                              SnmpAdminString,
    cucsEquipmentIOCardStatsDimmTempMin                              SnmpAdminString,
    cucsEquipmentIOCardStatsProcTemp                                 SnmpAdminString,
    cucsEquipmentIOCardStatsProcTempAvg                              SnmpAdminString,
    cucsEquipmentIOCardStatsProcTempMax                              SnmpAdminString,
    cucsEquipmentIOCardStatsProcTempMin                              SnmpAdminString,
    cucsEquipmentIOCardStatsIomI2CErrors                             Unsigned64,
    cucsEquipmentIOCardStatsIomI2CErrorsAvg                          Unsigned64,
    cucsEquipmentIOCardStatsIomI2CErrorsMax                          Unsigned64,
    cucsEquipmentIOCardStatsIomI2CErrorsMin                          Unsigned64
}

cucsEquipmentIOCardStatsInstanceId OBJECT-TYPE
    SYNTAX       CucsManagedObjectId
    MAX-ACCESS   not-accessible
    STATUS       current
    DESCRIPTION
        "Instance identifier of the managed object."
    ::= { cucsEquipmentIOCardStatsEntry 1 }

cucsEquipmentIOCardStatsDn OBJECT-TYPE
    SYNTAX       CucsManagedObjectDn
    MAX-ACCESS   read-only
    STATUS       current
    DESCRIPTION
        "Cisco UCS equipment:IOCardStats:dn managed object property"
    ::= { cucsEquipmentIOCardStatsEntry 2 }

cucsEquipmentIOCardStatsRn OBJECT-TYPE
    SYNTAX       SnmpAdminString
    MAX-ACCESS   read-only
    STATUS       current
    DESCRIPTION
        "Cisco UCS equipment:IOCardStats:rn managed object property"
    ::= { cucsEquipmentIOCardStatsEntry 3 }

cucsEquipmentIOCardStatsAmbientTemp OBJECT-TYPE
    SYNTAX       INTEGER
    MAX-ACCESS   read-only
    STATUS       current
    DESCRIPTION
        "Cisco UCS equipment:IOCardStats:ambientTemp managed
        object property"
    ::= { cucsEquipmentIOCardStatsEntry 4 }

cucsEquipmentIOCardStatsAmbientTempAvg OBJECT-TYPE
    SYNTAX       INTEGER
    MAX-ACCESS   read-only
    STATUS       current
    DESCRIPTION
        "Cisco UCS equipment:IOCardStats:ambientTempAvg
        managed object property"
    ::= { cucsEquipmentIOCardStatsEntry 5 }

cucsEquipmentIOCardStatsAmbientTempMax OBJECT-TYPE
    SYNTAX       INTEGER
    MAX-ACCESS   read-only
    STATUS       current
    DESCRIPTION
        "Cisco UCS equipment:IOCardStats:ambientTempMax
        managed object property"
    ::= { cucsEquipmentIOCardStatsEntry 6 }

cucsEquipmentIOCardStatsAmbientTempMin OBJECT-TYPE
    SYNTAX       INTEGER
    MAX-ACCESS   read-only
    STATUS       current
    DESCRIPTION
        "Cisco UCS equipment:IOCardStats:ambientTempMin
        managed object property"
    ::= { cucsEquipmentIOCardStatsEntry 7 }

cucsEquipmentIOCardStatsIntervals OBJECT-TYPE
    SYNTAX       Gauge32
    MAX-ACCESS   read-only
    STATUS       current
    DESCRIPTION
        "Cisco UCS equipment:IOCardStats:intervals managed
        object property"
    ::= { cucsEquipmentIOCardStatsEntry 8 }

cucsEquipmentIOCardStatsSuspect OBJECT-TYPE
    SYNTAX       TruthValue
    MAX-ACCESS   read-only
    STATUS       current
    DESCRIPTION
        "Cisco UCS equipment:IOCardStats:suspect managed object property"
    ::= { cucsEquipmentIOCardStatsEntry 9 }

cucsEquipmentIOCardStatsTemp OBJECT-TYPE
    SYNTAX       INTEGER
    MAX-ACCESS   read-only
    STATUS       current
    DESCRIPTION
        "Cisco UCS equipment:IOCardStats:temp managed object property"
    ::= { cucsEquipmentIOCardStatsEntry 10 }

cucsEquipmentIOCardStatsTempAvg OBJECT-TYPE
    SYNTAX       INTEGER
    MAX-ACCESS   read-only
    STATUS       current
    DESCRIPTION
        "Cisco UCS equipment:IOCardStats:tempAvg managed object property"
    ::= { cucsEquipmentIOCardStatsEntry 11 }

cucsEquipmentIOCardStatsTempMax OBJECT-TYPE
    SYNTAX       INTEGER
    MAX-ACCESS   read-only
    STATUS       current
    DESCRIPTION
        "Cisco UCS equipment:IOCardStats:tempMax managed object property"
    ::= { cucsEquipmentIOCardStatsEntry 12 }

cucsEquipmentIOCardStatsTempMin OBJECT-TYPE
    SYNTAX       INTEGER
    MAX-ACCESS   read-only
    STATUS       current
    DESCRIPTION
        "Cisco UCS equipment:IOCardStats:tempMin managed object property"
    ::= { cucsEquipmentIOCardStatsEntry 13 }

cucsEquipmentIOCardStatsThresholded OBJECT-TYPE
    SYNTAX       CucsEquipmentIOCardStatsThresholded
    MAX-ACCESS   read-only
    STATUS       current
    DESCRIPTION
        "Cisco UCS equipment:IOCardStats:thresholded managed
        object property"
    ::= { cucsEquipmentIOCardStatsEntry 14 }

cucsEquipmentIOCardStatsTimeCollected OBJECT-TYPE
    SYNTAX       DateAndTime
    MAX-ACCESS   read-only
    STATUS       current
    DESCRIPTION
        "Cisco UCS equipment:IOCardStats:timeCollected
        managed object property"
    ::= { cucsEquipmentIOCardStatsEntry 15 }

cucsEquipmentIOCardStatsUpdate OBJECT-TYPE
    SYNTAX       Gauge32
    MAX-ACCESS   read-only
    STATUS       current
    DESCRIPTION
        "Cisco UCS equipment:IOCardStats:update managed object property"
    ::= { cucsEquipmentIOCardStatsEntry 16 }

cucsEquipmentIOCardStatsDimmTemp OBJECT-TYPE
    SYNTAX       SnmpAdminString
    MAX-ACCESS   read-only
    STATUS       current
    DESCRIPTION
        "Cisco UCS equipment:IOCardStats:dimmTemp managed object property"
    ::= { cucsEquipmentIOCardStatsEntry 17 }

cucsEquipmentIOCardStatsDimmTempAvg OBJECT-TYPE
    SYNTAX       SnmpAdminString
    MAX-ACCESS   read-only
    STATUS       current
    DESCRIPTION
        "Cisco UCS equipment:IOCardStats:dimmTempAvg managed
        object property"
    ::= { cucsEquipmentIOCardStatsEntry 18 }

cucsEquipmentIOCardStatsDimmTempMax OBJECT-TYPE
    SYNTAX       SnmpAdminString
    MAX-ACCESS   read-only
    STATUS       current
    DESCRIPTION
        "Cisco UCS equipment:IOCardStats:dimmTempMax managed
        object property"
    ::= { cucsEquipmentIOCardStatsEntry 19 }

cucsEquipmentIOCardStatsDimmTempMin OBJECT-TYPE
    SYNTAX       SnmpAdminString
    MAX-ACCESS   read-only
    STATUS       current
    DESCRIPTION
        "Cisco UCS equipment:IOCardStats:dimmTempMin managed
        object property"
    ::= { cucsEquipmentIOCardStatsEntry 20 }

cucsEquipmentIOCardStatsProcTemp OBJECT-TYPE
    SYNTAX       SnmpAdminString
    MAX-ACCESS   read-only
    STATUS       current
    DESCRIPTION
        "Cisco UCS equipment:IOCardStats:procTemp managed object property"
    ::= { cucsEquipmentIOCardStatsEntry 21 }

cucsEquipmentIOCardStatsProcTempAvg OBJECT-TYPE
    SYNTAX       SnmpAdminString
    MAX-ACCESS   read-only
    STATUS       current
    DESCRIPTION
        "Cisco UCS equipment:IOCardStats:procTempAvg managed
        object property"
    ::= { cucsEquipmentIOCardStatsEntry 22 }

cucsEquipmentIOCardStatsProcTempMax OBJECT-TYPE
    SYNTAX       SnmpAdminString
    MAX-ACCESS   read-only
    STATUS       current
    DESCRIPTION
        "Cisco UCS equipment:IOCardStats:procTempMax managed
        object property"
    ::= { cucsEquipmentIOCardStatsEntry 23 }

cucsEquipmentIOCardStatsProcTempMin OBJECT-TYPE
    SYNTAX       SnmpAdminString
    MAX-ACCESS   read-only
    STATUS       current
    DESCRIPTION
        "Cisco UCS equipment:IOCardStats:procTempMin managed
        object property"
    ::= { cucsEquipmentIOCardStatsEntry 24 }

cucsEquipmentIOCardStatsIomI2CErrors OBJECT-TYPE
    SYNTAX       Unsigned64
    MAX-ACCESS   read-only
    STATUS       current
    DESCRIPTION
        "Cisco UCS equipment:IOCardStats:IomI2CErrors managed
        object property"
    ::= { cucsEquipmentIOCardStatsEntry 25 }

cucsEquipmentIOCardStatsIomI2CErrorsAvg OBJECT-TYPE
    SYNTAX       Unsigned64
    MAX-ACCESS   read-only
    STATUS       current
    DESCRIPTION
        "Cisco UCS equipment:IOCardStats:IomI2CErrorsAvg
        managed object property"
    ::= { cucsEquipmentIOCardStatsEntry 32 }

cucsEquipmentIOCardStatsIomI2CErrorsMax OBJECT-TYPE
    SYNTAX       Unsigned64
    MAX-ACCESS   read-only
    STATUS       current
    DESCRIPTION
        "Cisco UCS equipment:IOCardStats:IomI2CErrorsMax
        managed object property"
    ::= { cucsEquipmentIOCardStatsEntry 33 }

cucsEquipmentIOCardStatsIomI2CErrorsMin OBJECT-TYPE
    SYNTAX       Unsigned64
    MAX-ACCESS   read-only
    STATUS       current
    DESCRIPTION
        "Cisco UCS equipment:IOCardStats:IomI2CErrorsMin
        managed object property"
    ::= { cucsEquipmentIOCardStatsEntry 34 }

cucsEquipmentIOCardStatsHistTable OBJECT-TYPE
    SYNTAX           SEQUENCE OF CucsEquipmentIOCardStatsHistEntry
    MAX-ACCESS       not-accessible
    STATUS           current
    DESCRIPTION
        "Cisco UCS equipment:IOCardStatsHist managed object table"
    ::= { cucsEquipmentObjects 34 }

cucsEquipmentIOCardStatsHistEntry OBJECT-TYPE
    SYNTAX           CucsEquipmentIOCardStatsHistEntry
    MAX-ACCESS       not-accessible
    STATUS           current
    DESCRIPTION
        "Entry for the cucsEquipmentIOCardStatsHistTable table."
    INDEX { cucsEquipmentIOCardStatsHistInstanceId }
    ::= { cucsEquipmentIOCardStatsHistTable 1 }

CucsEquipmentIOCardStatsHistEntry ::= SEQUENCE {
    cucsEquipmentIOCardStatsHistInstanceId                           CucsManagedObjectId,
    cucsEquipmentIOCardStatsHistDn                                   CucsManagedObjectDn,
    cucsEquipmentIOCardStatsHistRn                                   SnmpAdminString,
    cucsEquipmentIOCardStatsHistAmbientTemp                          INTEGER,
    cucsEquipmentIOCardStatsHistAmbientTempAvg                       INTEGER,
    cucsEquipmentIOCardStatsHistAmbientTempMax                       INTEGER,
    cucsEquipmentIOCardStatsHistAmbientTempMin                       INTEGER,
    cucsEquipmentIOCardStatsHistId                                   Unsigned64,
    cucsEquipmentIOCardStatsHistMostRecent                           TruthValue,
    cucsEquipmentIOCardStatsHistSuspect                              TruthValue,
    cucsEquipmentIOCardStatsHistTemp                                 INTEGER,
    cucsEquipmentIOCardStatsHistTempAvg                              INTEGER,
    cucsEquipmentIOCardStatsHistTempMax                              INTEGER,
    cucsEquipmentIOCardStatsHistTempMin                              INTEGER,
    cucsEquipmentIOCardStatsHistThresholded                          CucsEquipmentIOCardStatsHistThresholded,
    cucsEquipmentIOCardStatsHistTimeCollected                        DateAndTime,
    cucsEquipmentIOCardStatsHistDimmTemp                             SnmpAdminString,
    cucsEquipmentIOCardStatsHistDimmTempAvg                          SnmpAdminString,
    cucsEquipmentIOCardStatsHistDimmTempMax                          SnmpAdminString,
    cucsEquipmentIOCardStatsHistDimmTempMin                          SnmpAdminString,
    cucsEquipmentIOCardStatsHistProcTemp                             SnmpAdminString,
    cucsEquipmentIOCardStatsHistProcTempAvg                          SnmpAdminString,
    cucsEquipmentIOCardStatsHistProcTempMax                          SnmpAdminString,
    cucsEquipmentIOCardStatsHistProcTempMin                          SnmpAdminString,
    cucsEquipmentIOCardStatsHistIomI2CErrors                         Unsigned64,
    cucsEquipmentIOCardStatsHistIomI2CErrorsAvg                      Unsigned64,
    cucsEquipmentIOCardStatsHistIomI2CErrorsMax                      Unsigned64,
    cucsEquipmentIOCardStatsHistIomI2CErrorsMin                      Unsigned64
}

cucsEquipmentIOCardStatsHistInstanceId OBJECT-TYPE
    SYNTAX       CucsManagedObjectId
    MAX-ACCESS   not-accessible
    STATUS       current
    DESCRIPTION
        "Instance identifier of the managed object."
    ::= { cucsEquipmentIOCardStatsHistEntry 1 }

cucsEquipmentIOCardStatsHistDn OBJECT-TYPE
    SYNTAX       CucsManagedObjectDn
    MAX-ACCESS   read-only
    STATUS       current
    DESCRIPTION
        "Cisco UCS equipment:IOCardStatsHist:dn managed object property"
    ::= { cucsEquipmentIOCardStatsHistEntry 2 }

cucsEquipmentIOCardStatsHistRn OBJECT-TYPE
    SYNTAX       SnmpAdminString
    MAX-ACCESS   read-only
    STATUS       current
    DESCRIPTION
        "Cisco UCS equipment:IOCardStatsHist:rn managed object property"
    ::= { cucsEquipmentIOCardStatsHistEntry 3 }

cucsEquipmentIOCardStatsHistAmbientTemp OBJECT-TYPE
    SYNTAX       INTEGER
    MAX-ACCESS   read-only
    STATUS       current
    DESCRIPTION
        "Cisco UCS equipment:IOCardStatsHist:ambientTemp
        managed object property"
    ::= { cucsEquipmentIOCardStatsHistEntry 4 }

cucsEquipmentIOCardStatsHistAmbientTempAvg OBJECT-TYPE
    SYNTAX       INTEGER
    MAX-ACCESS   read-only
    STATUS       current
    DESCRIPTION
        "Cisco UCS equipment:IOCardStatsHist:ambientTempAvg
        managed object property"
    ::= { cucsEquipmentIOCardStatsHistEntry 5 }

cucsEquipmentIOCardStatsHistAmbientTempMax OBJECT-TYPE
    SYNTAX       INTEGER
    MAX-ACCESS   read-only
    STATUS       current
    DESCRIPTION
        "Cisco UCS equipment:IOCardStatsHist:ambientTempMax
        managed object property"
    ::= { cucsEquipmentIOCardStatsHistEntry 6 }

cucsEquipmentIOCardStatsHistAmbientTempMin OBJECT-TYPE
    SYNTAX       INTEGER
    MAX-ACCESS   read-only
    STATUS       current
    DESCRIPTION
        "Cisco UCS equipment:IOCardStatsHist:ambientTempMin
        managed object property"
    ::= { cucsEquipmentIOCardStatsHistEntry 7 }

cucsEquipmentIOCardStatsHistId OBJECT-TYPE
    SYNTAX       Unsigned64
    MAX-ACCESS   read-only
    STATUS       current
    DESCRIPTION
        "Cisco UCS equipment:IOCardStatsHist:id managed object property"
    ::= { cucsEquipmentIOCardStatsHistEntry 8 }

cucsEquipmentIOCardStatsHistMostRecent OBJECT-TYPE
    SYNTAX       TruthValue
    MAX-ACCESS   read-only
    STATUS       current
    DESCRIPTION
        "Cisco UCS equipment:IOCardStatsHist:mostRecent
        managed object property"
    ::= { cucsEquipmentIOCardStatsHistEntry 9 }

cucsEquipmentIOCardStatsHistSuspect OBJECT-TYPE
    SYNTAX       TruthValue
    MAX-ACCESS   read-only
    STATUS       current
    DESCRIPTION
        "Cisco UCS equipment:IOCardStatsHist:suspect managed
        object property"
    ::= { cucsEquipmentIOCardStatsHistEntry 10 }

cucsEquipmentIOCardStatsHistTemp OBJECT-TYPE
    SYNTAX       INTEGER
    MAX-ACCESS   read-only
    STATUS       current
    DESCRIPTION
        "Cisco UCS equipment:IOCardStatsHist:temp managed object property"
    ::= { cucsEquipmentIOCardStatsHistEntry 11 }

cucsEquipmentIOCardStatsHistTempAvg OBJECT-TYPE
    SYNTAX       INTEGER
    MAX-ACCESS   read-only
    STATUS       current
    DESCRIPTION
        "Cisco UCS equipment:IOCardStatsHist:tempAvg managed
        object property"
    ::= { cucsEquipmentIOCardStatsHistEntry 12 }

cucsEquipmentIOCardStatsHistTempMax OBJECT-TYPE
    SYNTAX       INTEGER
    MAX-ACCESS   read-only
    STATUS       current
    DESCRIPTION
        "Cisco UCS equipment:IOCardStatsHist:tempMax managed
        object property"
    ::= { cucsEquipmentIOCardStatsHistEntry 13 }

cucsEquipmentIOCardStatsHistTempMin OBJECT-TYPE
    SYNTAX       INTEGER
    MAX-ACCESS   read-only
    STATUS       current
    DESCRIPTION
        "Cisco UCS equipment:IOCardStatsHist:tempMin managed
        object property"
    ::= { cucsEquipmentIOCardStatsHistEntry 14 }

cucsEquipmentIOCardStatsHistThresholded OBJECT-TYPE
    SYNTAX       CucsEquipmentIOCardStatsHistThresholded
    MAX-ACCESS   read-only
    STATUS       current
    DESCRIPTION
        "Cisco UCS equipment:IOCardStatsHist:thresholded
        managed object property"
    ::= { cucsEquipmentIOCardStatsHistEntry 15 }

cucsEquipmentIOCardStatsHistTimeCollected OBJECT-TYPE
    SYNTAX       DateAndTime
    MAX-ACCESS   read-only
    STATUS       current
    DESCRIPTION
        "Cisco UCS equipment:IOCardStatsHist:timeCollected
        managed object property"
    ::= { cucsEquipmentIOCardStatsHistEntry 16 }

cucsEquipmentIOCardStatsHistDimmTemp OBJECT-TYPE
    SYNTAX       SnmpAdminString
    MAX-ACCESS   read-only
    STATUS       current
    DESCRIPTION
        "Cisco UCS equipment:IOCardStatsHist:dimmTemp managed
        object property"
    ::= { cucsEquipmentIOCardStatsHistEntry 17 }

cucsEquipmentIOCardStatsHistDimmTempAvg OBJECT-TYPE
    SYNTAX       SnmpAdminString
    MAX-ACCESS   read-only
    STATUS       current
    DESCRIPTION
        "Cisco UCS equipment:IOCardStatsHist:dimmTempAvg
        managed object property"
    ::= { cucsEquipmentIOCardStatsHistEntry 18 }

cucsEquipmentIOCardStatsHistDimmTempMax OBJECT-TYPE
    SYNTAX       SnmpAdminString
    MAX-ACCESS   read-only
    STATUS       current
    DESCRIPTION
        "Cisco UCS equipment:IOCardStatsHist:dimmTempMax
        managed object property"
    ::= { cucsEquipmentIOCardStatsHistEntry 19 }

cucsEquipmentIOCardStatsHistDimmTempMin OBJECT-TYPE
    SYNTAX       SnmpAdminString
    MAX-ACCESS   read-only
    STATUS       current
    DESCRIPTION
        "Cisco UCS equipment:IOCardStatsHist:dimmTempMin
        managed object property"
    ::= { cucsEquipmentIOCardStatsHistEntry 20 }

cucsEquipmentIOCardStatsHistProcTemp OBJECT-TYPE
    SYNTAX       SnmpAdminString
    MAX-ACCESS   read-only
    STATUS       current
    DESCRIPTION
        "Cisco UCS equipment:IOCardStatsHist:procTemp managed
        object property"
    ::= { cucsEquipmentIOCardStatsHistEntry 21 }

cucsEquipmentIOCardStatsHistProcTempAvg OBJECT-TYPE
    SYNTAX       SnmpAdminString
    MAX-ACCESS   read-only
    STATUS       current
    DESCRIPTION
        "Cisco UCS equipment:IOCardStatsHist:procTempAvg
        managed object property"
    ::= { cucsEquipmentIOCardStatsHistEntry 22 }

cucsEquipmentIOCardStatsHistProcTempMax OBJECT-TYPE
    SYNTAX       SnmpAdminString
    MAX-ACCESS   read-only
    STATUS       current
    DESCRIPTION
        "Cisco UCS equipment:IOCardStatsHist:procTempMax
        managed object property"
    ::= { cucsEquipmentIOCardStatsHistEntry 23 }

cucsEquipmentIOCardStatsHistProcTempMin OBJECT-TYPE
    SYNTAX       SnmpAdminString
    MAX-ACCESS   read-only
    STATUS       current
    DESCRIPTION
        "Cisco UCS equipment:IOCardStatsHist:procTempMin
        managed object property"
    ::= { cucsEquipmentIOCardStatsHistEntry 24 }

cucsEquipmentIOCardStatsHistIomI2CErrors OBJECT-TYPE
    SYNTAX       Unsigned64
    MAX-ACCESS   read-only
    STATUS       current
    DESCRIPTION
        "Cisco UCS equipment:IOCardStatsHist:IomI2CErrors
        managed object property"
    ::= { cucsEquipmentIOCardStatsHistEntry 25 }

cucsEquipmentIOCardStatsHistIomI2CErrorsAvg OBJECT-TYPE
    SYNTAX       Unsigned64
    MAX-ACCESS   read-only
    STATUS       current
    DESCRIPTION
        "Cisco UCS equipment:IOCardStatsHist:IomI2CErrorsAvg
        managed object property"
    ::= { cucsEquipmentIOCardStatsHistEntry 30 }

cucsEquipmentIOCardStatsHistIomI2CErrorsMax OBJECT-TYPE
    SYNTAX       Unsigned64
    MAX-ACCESS   read-only
    STATUS       current
    DESCRIPTION
        "Cisco UCS equipment:IOCardStatsHist:IomI2CErrorsMax
        managed object property"
    ::= { cucsEquipmentIOCardStatsHistEntry 31 }

cucsEquipmentIOCardStatsHistIomI2CErrorsMin OBJECT-TYPE
    SYNTAX       Unsigned64
    MAX-ACCESS   read-only
    STATUS       current
    DESCRIPTION
        "Cisco UCS equipment:IOCardStatsHist:IomI2CErrorsMin
        managed object property"
    ::= { cucsEquipmentIOCardStatsHistEntry 32 }

cucsEquipmentIOCardTypeDefTable OBJECT-TYPE
    SYNTAX           SEQUENCE OF CucsEquipmentIOCardTypeDefEntry
    MAX-ACCESS       not-accessible
    STATUS           current
    DESCRIPTION
        "Cisco UCS equipment:IOCardTypeDef managed object table"
    ::= { cucsEquipmentObjects 101 }

cucsEquipmentIOCardTypeDefEntry OBJECT-TYPE
    SYNTAX           CucsEquipmentIOCardTypeDefEntry
    MAX-ACCESS       not-accessible
    STATUS           current
    DESCRIPTION
        "Entry for the cucsEquipmentIOCardTypeDefTable table."
    INDEX { cucsEquipmentIOCardTypeDefInstanceId }
    ::= { cucsEquipmentIOCardTypeDefTable 1 }

CucsEquipmentIOCardTypeDefEntry ::= SEQUENCE {
    cucsEquipmentIOCardTypeDefInstanceId                             CucsManagedObjectId,
    cucsEquipmentIOCardTypeDefDn                                     CucsManagedObjectDn,
    cucsEquipmentIOCardTypeDefRn                                     SnmpAdminString,
    cucsEquipmentIOCardTypeDefDescr                                  SnmpAdminString,
    cucsEquipmentIOCardTypeDefIntId                                  SnmpAdminString,
    cucsEquipmentIOCardTypeDefName                                   SnmpAdminString,
    cucsEquipmentIOCardTypeDefType                                   SnmpAdminString,
    cucsEquipmentIOCardTypeDefPolicyLevel                            Gauge32,
    cucsEquipmentIOCardTypeDefPolicyOwner                            CucsPolicyPolicyOwner
}

cucsEquipmentIOCardTypeDefInstanceId OBJECT-TYPE
    SYNTAX       CucsManagedObjectId
    MAX-ACCESS   not-accessible
    STATUS       current
    DESCRIPTION
        "Instance identifier of the managed object."
    ::= { cucsEquipmentIOCardTypeDefEntry 1 }

cucsEquipmentIOCardTypeDefDn OBJECT-TYPE
    SYNTAX       CucsManagedObjectDn
    MAX-ACCESS   read-only
    STATUS       current
    DESCRIPTION
        "Cisco UCS equipment:IOCardTypeDef:dn managed object property"
    ::= { cucsEquipmentIOCardTypeDefEntry 2 }

cucsEquipmentIOCardTypeDefRn OBJECT-TYPE
    SYNTAX       SnmpAdminString
    MAX-ACCESS   read-only
    STATUS       current
    DESCRIPTION
        "Cisco UCS equipment:IOCardTypeDef:rn managed object property"
    ::= { cucsEquipmentIOCardTypeDefEntry 3 }

cucsEquipmentIOCardTypeDefDescr OBJECT-TYPE
    SYNTAX       SnmpAdminString
    MAX-ACCESS   read-only
    STATUS       current
    DESCRIPTION
        "Cisco UCS equipment:IOCardTypeDef:descr managed object property"
    ::= { cucsEquipmentIOCardTypeDefEntry 4 }

cucsEquipmentIOCardTypeDefIntId OBJECT-TYPE
    SYNTAX       SnmpAdminString
    MAX-ACCESS   read-only
    STATUS       current
    DESCRIPTION
        "Cisco UCS equipment:IOCardTypeDef:intId managed object property"
    ::= { cucsEquipmentIOCardTypeDefEntry 5 }

cucsEquipmentIOCardTypeDefName OBJECT-TYPE
    SYNTAX       SnmpAdminString
    MAX-ACCESS   read-only
    STATUS       current
    DESCRIPTION
        "Cisco UCS equipment:IOCardTypeDef:name managed object property"
    ::= { cucsEquipmentIOCardTypeDefEntry 6 }

cucsEquipmentIOCardTypeDefType OBJECT-TYPE
    SYNTAX       SnmpAdminString
    MAX-ACCESS   read-only
    STATUS       current
    DESCRIPTION
        "Cisco UCS equipment:IOCardTypeDef:type managed object property"
    ::= { cucsEquipmentIOCardTypeDefEntry 7 }

cucsEquipmentIOCardTypeDefPolicyLevel OBJECT-TYPE
    SYNTAX       Gauge32
    MAX-ACCESS   read-only
    STATUS       current
    DESCRIPTION
        "Cisco UCS equipment:IOCardTypeDef:policyLevel
        managed object property"
    ::= { cucsEquipmentIOCardTypeDefEntry 8 }

cucsEquipmentIOCardTypeDefPolicyOwner OBJECT-TYPE
    SYNTAX       CucsPolicyPolicyOwner
    MAX-ACCESS   read-only
    STATUS       current
    DESCRIPTION
        "Cisco UCS equipment:IOCardTypeDef:policyOwner
        managed object property"
    ::= { cucsEquipmentIOCardTypeDefEntry 9 }

cucsEquipmentIOExpanderTable OBJECT-TYPE
    SYNTAX           SEQUENCE OF CucsEquipmentIOExpanderEntry
    MAX-ACCESS       not-accessible
    STATUS           current
    DESCRIPTION
        "Cisco UCS equipment:IOExpander managed object table"
    ::= { cucsEquipmentObjects 210 }

cucsEquipmentIOExpanderEntry OBJECT-TYPE
    SYNTAX           CucsEquipmentIOExpanderEntry
    MAX-ACCESS       not-accessible
    STATUS           current
    DESCRIPTION
        "Entry for the cucsEquipmentIOExpanderTable table."
    INDEX { cucsEquipmentIOExpanderInstanceId }
    ::= { cucsEquipmentIOExpanderTable 1 }

CucsEquipmentIOExpanderEntry ::= SEQUENCE {
    cucsEquipmentIOExpanderInstanceId                                CucsManagedObjectId,
    cucsEquipmentIOExpanderDn                                        CucsManagedObjectDn,
    cucsEquipmentIOExpanderRn                                        SnmpAdminString,
    cucsEquipmentIOExpanderId                                        Gauge32,
    cucsEquipmentIOExpanderLocationDn                                SnmpAdminString,
    cucsEquipmentIOExpanderModel                                     SnmpAdminString,
    cucsEquipmentIOExpanderOperQualifierReason                       SnmpAdminString,
    cucsEquipmentIOExpanderOperState                                 CucsEquipmentOperability,
    cucsEquipmentIOExpanderOperability                               CucsEquipmentOperability,
    cucsEquipmentIOExpanderPartNumber                                SnmpAdminString,
    cucsEquipmentIOExpanderPerf                                      CucsEquipmentSensorThresholdStatus,
    cucsEquipmentIOExpanderPower                                     CucsEquipmentPowerState,
    cucsEquipmentIOExpanderPresence                                  CucsEquipmentPresence,
    cucsEquipmentIOExpanderRevision                                  SnmpAdminString,
    cucsEquipmentIOExpanderSerial                                    SnmpAdminString,
    cucsEquipmentIOExpanderThermal                                   CucsEquipmentSensorThresholdStatus,
    cucsEquipmentIOExpanderVendor                                    SnmpAdminString,
    cucsEquipmentIOExpanderVid                                       SnmpAdminString,
    cucsEquipmentIOExpanderVoltage                                   CucsEquipmentSensorThresholdStatus,
    cucsEquipmentIOExpanderAssetTag                                  SnmpAdminString
}

cucsEquipmentIOExpanderInstanceId OBJECT-TYPE
    SYNTAX       CucsManagedObjectId
    MAX-ACCESS   not-accessible
    STATUS       current
    DESCRIPTION
        "Instance identifier of the managed object."
    ::= { cucsEquipmentIOExpanderEntry 1 }

cucsEquipmentIOExpanderDn OBJECT-TYPE
    SYNTAX       CucsManagedObjectDn
    MAX-ACCESS   read-only
    STATUS       current
    DESCRIPTION
        "Cisco UCS equipment:IOExpander:dn managed object property"
    ::= { cucsEquipmentIOExpanderEntry 2 }

cucsEquipmentIOExpanderRn OBJECT-TYPE
    SYNTAX       SnmpAdminString
    MAX-ACCESS   read-only
    STATUS       current
    DESCRIPTION
        "Cisco UCS equipment:IOExpander:rn managed object property"
    ::= { cucsEquipmentIOExpanderEntry 3 }

cucsEquipmentIOExpanderId OBJECT-TYPE
    SYNTAX       Gauge32
    MAX-ACCESS   read-only
    STATUS       current
    DESCRIPTION
        "Cisco UCS equipment:IOExpander:id managed object property"
    ::= { cucsEquipmentIOExpanderEntry 4 }

cucsEquipmentIOExpanderLocationDn OBJECT-TYPE
    SYNTAX       SnmpAdminString
    MAX-ACCESS   read-only
    STATUS       current
    DESCRIPTION
        "Cisco UCS equipment:IOExpander:locationDn managed
        object property"
    ::= { cucsEquipmentIOExpanderEntry 5 }

cucsEquipmentIOExpanderModel OBJECT-TYPE
    SYNTAX       SnmpAdminString
    MAX-ACCESS   read-only
    STATUS       current
    DESCRIPTION
        "Cisco UCS equipment:IOExpander:model managed object property"
    ::= { cucsEquipmentIOExpanderEntry 6 }

cucsEquipmentIOExpanderOperQualifierReason OBJECT-TYPE
    SYNTAX       SnmpAdminString
    MAX-ACCESS   read-only
    STATUS       current
    DESCRIPTION
        "Cisco UCS equipment:IOExpander:operQualifierReason
        managed object property"
    ::= { cucsEquipmentIOExpanderEntry 7 }

cucsEquipmentIOExpanderOperState OBJECT-TYPE
    SYNTAX       CucsEquipmentOperability
    MAX-ACCESS   read-only
    STATUS       current
    DESCRIPTION
        "Cisco UCS equipment:IOExpander:operState managed object property"
    ::= { cucsEquipmentIOExpanderEntry 8 }

cucsEquipmentIOExpanderOperability OBJECT-TYPE
    SYNTAX       CucsEquipmentOperability
    MAX-ACCESS   read-only
    STATUS       current
    DESCRIPTION
        "Cisco UCS equipment:IOExpander:operability managed
        object property"
    ::= { cucsEquipmentIOExpanderEntry 9 }

cucsEquipmentIOExpanderPartNumber OBJECT-TYPE
    SYNTAX       SnmpAdminString
    MAX-ACCESS   read-only
    STATUS       current
    DESCRIPTION
        "Cisco UCS equipment:IOExpander:partNumber managed
        object property"
    ::= { cucsEquipmentIOExpanderEntry 10 }

cucsEquipmentIOExpanderPerf OBJECT-TYPE
    SYNTAX       CucsEquipmentSensorThresholdStatus
    MAX-ACCESS   read-only
    STATUS       current
    DESCRIPTION
        "Cisco UCS equipment:IOExpander:perf managed object property"
    ::= { cucsEquipmentIOExpanderEntry 11 }

cucsEquipmentIOExpanderPower OBJECT-TYPE
    SYNTAX       CucsEquipmentPowerState
    MAX-ACCESS   read-only
    STATUS       current
    DESCRIPTION
        "Cisco UCS equipment:IOExpander:power managed object property"
    ::= { cucsEquipmentIOExpanderEntry 12 }

cucsEquipmentIOExpanderPresence OBJECT-TYPE
    SYNTAX       CucsEquipmentPresence
    MAX-ACCESS   read-only
    STATUS       current
    DESCRIPTION
        "Cisco UCS equipment:IOExpander:presence managed object property"
    ::= { cucsEquipmentIOExpanderEntry 13 }

cucsEquipmentIOExpanderRevision OBJECT-TYPE
    SYNTAX       SnmpAdminString
    MAX-ACCESS   read-only
    STATUS       current
    DESCRIPTION
        "Cisco UCS equipment:IOExpander:revision managed object property"
    ::= { cucsEquipmentIOExpanderEntry 14 }

cucsEquipmentIOExpanderSerial OBJECT-TYPE
    SYNTAX       SnmpAdminString
    MAX-ACCESS   read-only
    STATUS       current
    DESCRIPTION
        "Cisco UCS equipment:IOExpander:serial managed object property"
    ::= { cucsEquipmentIOExpanderEntry 15 }

cucsEquipmentIOExpanderThermal OBJECT-TYPE
    SYNTAX       CucsEquipmentSensorThresholdStatus
    MAX-ACCESS   read-only
    STATUS       current
    DESCRIPTION
        "Cisco UCS equipment:IOExpander:thermal managed object property"
    ::= { cucsEquipmentIOExpanderEntry 16 }

cucsEquipmentIOExpanderVendor OBJECT-TYPE
    SYNTAX       SnmpAdminString
    MAX-ACCESS   read-only
    STATUS       current
    DESCRIPTION
        "Cisco UCS equipment:IOExpander:vendor managed object property"
    ::= { cucsEquipmentIOExpanderEntry 17 }

cucsEquipmentIOExpanderVid OBJECT-TYPE
    SYNTAX       SnmpAdminString
    MAX-ACCESS   read-only
    STATUS       current
    DESCRIPTION
        "Cisco UCS equipment:IOExpander:vid managed object property"
    ::= { cucsEquipmentIOExpanderEntry 18 }

cucsEquipmentIOExpanderVoltage OBJECT-TYPE
    SYNTAX       CucsEquipmentSensorThresholdStatus
    MAX-ACCESS   read-only
    STATUS       current
    DESCRIPTION
        "Cisco UCS equipment:IOExpander:voltage managed object property"
    ::= { cucsEquipmentIOExpanderEntry 19 }

cucsEquipmentIOExpanderAssetTag OBJECT-TYPE
    SYNTAX       SnmpAdminString
    MAX-ACCESS   read-only
    STATUS       current
    DESCRIPTION
        "Cisco UCS equipment:IOExpander:assetTag managed object property"
    ::= { cucsEquipmentIOExpanderEntry 20 }

cucsEquipmentIOExpanderCapProviderTable OBJECT-TYPE
    SYNTAX           SEQUENCE OF CucsEquipmentIOExpanderCapProviderEntry
    MAX-ACCESS       not-accessible
    STATUS           current
    DESCRIPTION
        "Cisco UCS equipment:IOExpanderCapProvider managed object table"
    ::= { cucsEquipmentObjects 211 }

cucsEquipmentIOExpanderCapProviderEntry OBJECT-TYPE
    SYNTAX           CucsEquipmentIOExpanderCapProviderEntry
    MAX-ACCESS       not-accessible
    STATUS           current
    DESCRIPTION
        "Entry for the cucsEquipmentIOExpanderCapProviderTable table."
    INDEX { cucsEquipmentIOExpanderCapProviderInstanceId }
    ::= { cucsEquipmentIOExpanderCapProviderTable 1 }

CucsEquipmentIOExpanderCapProviderEntry ::= SEQUENCE {
    cucsEquipmentIOExpanderCapProviderInstanceId                     CucsManagedObjectId,
    cucsEquipmentIOExpanderCapProviderDn                             CucsManagedObjectDn,
    cucsEquipmentIOExpanderCapProviderRn                             SnmpAdminString,
    cucsEquipmentIOExpanderCapProviderDeleted                        TruthValue,
    cucsEquipmentIOExpanderCapProviderDeprecated                     TruthValue,
    cucsEquipmentIOExpanderCapProviderElementLoadFailures            Gauge32,
    cucsEquipmentIOExpanderCapProviderElementsLoaded                 Gauge32,
    cucsEquipmentIOExpanderCapProviderGencount                       Gauge32,
    cucsEquipmentIOExpanderCapProviderLoadErrors                     Gauge32,
    cucsEquipmentIOExpanderCapProviderLoadWarnings                   Gauge32,
    cucsEquipmentIOExpanderCapProviderMgmtPlaneVer                   SnmpAdminString,
    cucsEquipmentIOExpanderCapProviderModel                          SnmpAdminString,
    cucsEquipmentIOExpanderCapProviderPromCardType                   Gauge32,
    cucsEquipmentIOExpanderCapProviderRevision                       SnmpAdminString,
    cucsEquipmentIOExpanderCapProviderVendor                         SnmpAdminString
}

cucsEquipmentIOExpanderCapProviderInstanceId OBJECT-TYPE
    SYNTAX       CucsManagedObjectId
    MAX-ACCESS   not-accessible
    STATUS       current
    DESCRIPTION
        "Instance identifier of the managed object."
    ::= { cucsEquipmentIOExpanderCapProviderEntry 1 }

cucsEquipmentIOExpanderCapProviderDn OBJECT-TYPE
    SYNTAX       CucsManagedObjectDn
    MAX-ACCESS   read-only
    STATUS       current
    DESCRIPTION
        "Cisco UCS equipment:IOExpanderCapProvider:dn managed
        object property"
    ::= { cucsEquipmentIOExpanderCapProviderEntry 2 }

cucsEquipmentIOExpanderCapProviderRn OBJECT-TYPE
    SYNTAX       SnmpAdminString
    MAX-ACCESS   read-only
    STATUS       current
    DESCRIPTION
        "Cisco UCS equipment:IOExpanderCapProvider:rn managed
        object property"
    ::= { cucsEquipmentIOExpanderCapProviderEntry 3 }

cucsEquipmentIOExpanderCapProviderDeleted OBJECT-TYPE
    SYNTAX       TruthValue
    MAX-ACCESS   read-only
    STATUS       current
    DESCRIPTION
        "Cisco UCS equipment:IOExpanderCapProvider:deleted
        managed object property"
    ::= { cucsEquipmentIOExpanderCapProviderEntry 4 }

cucsEquipmentIOExpanderCapProviderDeprecated OBJECT-TYPE
    SYNTAX       TruthValue
    MAX-ACCESS   read-only
    STATUS       current
    DESCRIPTION
        "Cisco UCS equipment:IOExpanderCapProvider:deprecated
        managed object property"
    ::= { cucsEquipmentIOExpanderCapProviderEntry 5 }

cucsEquipmentIOExpanderCapProviderElementLoadFailures OBJECT-TYPE
    SYNTAX       Gauge32
    MAX-ACCESS   read-only
    STATUS       current
    DESCRIPTION
        "Cisco UCS equipment:IOExpanderCapProvider:elementLoadFailures
        managed object property"
    ::= { cucsEquipmentIOExpanderCapProviderEntry 6 }

cucsEquipmentIOExpanderCapProviderElementsLoaded OBJECT-TYPE
    SYNTAX       Gauge32
    MAX-ACCESS   read-only
    STATUS       current
    DESCRIPTION
        "Cisco UCS equipment:IOExpanderCapProvider:elementsLoaded
        managed object property"
    ::= { cucsEquipmentIOExpanderCapProviderEntry 7 }

cucsEquipmentIOExpanderCapProviderGencount OBJECT-TYPE
    SYNTAX       Gauge32
    MAX-ACCESS   read-only
    STATUS       current
    DESCRIPTION
        "Cisco UCS equipment:IOExpanderCapProvider:gencount
        managed object property"
    ::= { cucsEquipmentIOExpanderCapProviderEntry 8 }

cucsEquipmentIOExpanderCapProviderLoadErrors OBJECT-TYPE
    SYNTAX       Gauge32
    MAX-ACCESS   read-only
    STATUS       current
    DESCRIPTION
        "Cisco UCS equipment:IOExpanderCapProvider:loadErrors
        managed object property"
    ::= { cucsEquipmentIOExpanderCapProviderEntry 9 }

cucsEquipmentIOExpanderCapProviderLoadWarnings OBJECT-TYPE
    SYNTAX       Gauge32
    MAX-ACCESS   read-only
    STATUS       current
    DESCRIPTION
        "Cisco UCS equipment:IOExpanderCapProvider:loadWarnings
        managed object property"
    ::= { cucsEquipmentIOExpanderCapProviderEntry 10 }

cucsEquipmentIOExpanderCapProviderMgmtPlaneVer OBJECT-TYPE
    SYNTAX       SnmpAdminString
    MAX-ACCESS   read-only
    STATUS       current
    DESCRIPTION
        "Cisco UCS equipment:IOExpanderCapProvider:mgmtPlaneVer
        managed object property"
    ::= { cucsEquipmentIOExpanderCapProviderEntry 11 }

cucsEquipmentIOExpanderCapProviderModel OBJECT-TYPE
    SYNTAX       SnmpAdminString
    MAX-ACCESS   read-only
    STATUS       current
    DESCRIPTION
        "Cisco UCS equipment:IOExpanderCapProvider:model
        managed object property"
    ::= { cucsEquipmentIOExpanderCapProviderEntry 12 }

cucsEquipmentIOExpanderCapProviderPromCardType OBJECT-TYPE
    SYNTAX       Gauge32
    MAX-ACCESS   read-only
    STATUS       current
    DESCRIPTION
        "Cisco UCS equipment:IOExpanderCapProvider:promCardType
        managed object property"
    ::= { cucsEquipmentIOExpanderCapProviderEntry 13 }

cucsEquipmentIOExpanderCapProviderRevision OBJECT-TYPE
    SYNTAX       SnmpAdminString
    MAX-ACCESS   read-only
    STATUS       current
    DESCRIPTION
        "Cisco UCS equipment:IOExpanderCapProvider:revision
        managed object property"
    ::= { cucsEquipmentIOExpanderCapProviderEntry 14 }

cucsEquipmentIOExpanderCapProviderVendor OBJECT-TYPE
    SYNTAX       SnmpAdminString
    MAX-ACCESS   read-only
    STATUS       current
    DESCRIPTION
        "Cisco UCS equipment:IOExpanderCapProvider:vendor
        managed object property"
    ::= { cucsEquipmentIOExpanderCapProviderEntry 15 }

cucsEquipmentInbandMgmtCapTable OBJECT-TYPE
    SYNTAX           SEQUENCE OF CucsEquipmentInbandMgmtCapEntry
    MAX-ACCESS       not-accessible
    STATUS           current
    DESCRIPTION
        "Cisco UCS equipment:InbandMgmtCap managed object table"
    ::= { cucsEquipmentObjects 124 }

cucsEquipmentInbandMgmtCapEntry OBJECT-TYPE
    SYNTAX           CucsEquipmentInbandMgmtCapEntry
    MAX-ACCESS       not-accessible
    STATUS           current
    DESCRIPTION
        "Entry for the cucsEquipmentInbandMgmtCapTable table."
    INDEX { cucsEquipmentInbandMgmtCapInstanceId }
    ::= { cucsEquipmentInbandMgmtCapTable 1 }

CucsEquipmentInbandMgmtCapEntry ::= SEQUENCE {
    cucsEquipmentInbandMgmtCapInstanceId                             CucsManagedObjectId,
    cucsEquipmentInbandMgmtCapDn                                     CucsManagedObjectDn,
    cucsEquipmentInbandMgmtCapRn                                     SnmpAdminString,
    cucsEquipmentInbandMgmtCapIsSupported                            CucsEquipmentIsSupported,
    cucsEquipmentInbandMgmtCapMinCimcVersion                         SnmpAdminString,
    cucsEquipmentInbandMgmtCapMinCmcVersion                          SnmpAdminString
}

cucsEquipmentInbandMgmtCapInstanceId OBJECT-TYPE
    SYNTAX       CucsManagedObjectId
    MAX-ACCESS   not-accessible
    STATUS       current
    DESCRIPTION
        "Instance identifier of the managed object."
    ::= { cucsEquipmentInbandMgmtCapEntry 1 }

cucsEquipmentInbandMgmtCapDn OBJECT-TYPE
    SYNTAX       CucsManagedObjectDn
    MAX-ACCESS   read-only
    STATUS       current
    DESCRIPTION
        "Cisco UCS equipment:InbandMgmtCap:dn managed object property"
    ::= { cucsEquipmentInbandMgmtCapEntry 2 }

cucsEquipmentInbandMgmtCapRn OBJECT-TYPE
    SYNTAX       SnmpAdminString
    MAX-ACCESS   read-only
    STATUS       current
    DESCRIPTION
        "Cisco UCS equipment:InbandMgmtCap:rn managed object property"
    ::= { cucsEquipmentInbandMgmtCapEntry 3 }

cucsEquipmentInbandMgmtCapIsSupported OBJECT-TYPE
    SYNTAX       CucsEquipmentIsSupported
    MAX-ACCESS   read-only
    STATUS       current
    DESCRIPTION
        "Cisco UCS equipment:InbandMgmtCap:isSupported
        managed object property"
    ::= { cucsEquipmentInbandMgmtCapEntry 4 }

cucsEquipmentInbandMgmtCapMinCimcVersion OBJECT-TYPE
    SYNTAX       SnmpAdminString
    MAX-ACCESS   read-only
    STATUS       current
    DESCRIPTION
        "Cisco UCS equipment:InbandMgmtCap:minCimcVersion
        managed object property"
    ::= { cucsEquipmentInbandMgmtCapEntry 5 }

cucsEquipmentInbandMgmtCapMinCmcVersion OBJECT-TYPE
    SYNTAX       SnmpAdminString
    MAX-ACCESS   read-only
    STATUS       current
    DESCRIPTION
        "Cisco UCS equipment:InbandMgmtCap:minCmcVersion
        managed object property"
    ::= { cucsEquipmentInbandMgmtCapEntry 6 }

cucsEquipmentIndicatorLedTable OBJECT-TYPE
    SYNTAX           SEQUENCE OF CucsEquipmentIndicatorLedEntry
    MAX-ACCESS       not-accessible
    STATUS           current
    DESCRIPTION
        "Cisco UCS equipment:IndicatorLed managed object table"
    ::= { cucsEquipmentObjects 35 }

cucsEquipmentIndicatorLedEntry OBJECT-TYPE
    SYNTAX           CucsEquipmentIndicatorLedEntry
    MAX-ACCESS       not-accessible
    STATUS           current
    DESCRIPTION
        "Entry for the cucsEquipmentIndicatorLedTable table."
    INDEX { cucsEquipmentIndicatorLedInstanceId }
    ::= { cucsEquipmentIndicatorLedTable 1 }

CucsEquipmentIndicatorLedEntry ::= SEQUENCE {
    cucsEquipmentIndicatorLedInstanceId                              CucsManagedObjectId,
    cucsEquipmentIndicatorLedDn                                      CucsManagedObjectDn,
    cucsEquipmentIndicatorLedRn                                      SnmpAdminString,
    cucsEquipmentIndicatorLedColor                                   CucsEquipmentLedColor,
    cucsEquipmentIndicatorLedId                                      Gauge32,
    cucsEquipmentIndicatorLedName                                    SnmpAdminString,
    cucsEquipmentIndicatorLedOperState                               CucsEquipmentLedOperState
}

cucsEquipmentIndicatorLedInstanceId OBJECT-TYPE
    SYNTAX       CucsManagedObjectId
    MAX-ACCESS   not-accessible
    STATUS       current
    DESCRIPTION
        "Instance identifier of the managed object."
    ::= { cucsEquipmentIndicatorLedEntry 1 }

cucsEquipmentIndicatorLedDn OBJECT-TYPE
    SYNTAX       CucsManagedObjectDn
    MAX-ACCESS   read-only
    STATUS       current
    DESCRIPTION
        "Cisco UCS equipment:IndicatorLed:dn managed object property"
    ::= { cucsEquipmentIndicatorLedEntry 2 }

cucsEquipmentIndicatorLedRn OBJECT-TYPE
    SYNTAX       SnmpAdminString
    MAX-ACCESS   read-only
    STATUS       current
    DESCRIPTION
        "Cisco UCS equipment:IndicatorLed:rn managed object property"
    ::= { cucsEquipmentIndicatorLedEntry 3 }

cucsEquipmentIndicatorLedColor OBJECT-TYPE
    SYNTAX       CucsEquipmentLedColor
    MAX-ACCESS   read-only
    STATUS       current
    DESCRIPTION
        "Cisco UCS equipment:IndicatorLed:color managed object property"
    ::= { cucsEquipmentIndicatorLedEntry 4 }

cucsEquipmentIndicatorLedId OBJECT-TYPE
    SYNTAX       Gauge32
    MAX-ACCESS   read-only
    STATUS       current
    DESCRIPTION
        "Cisco UCS equipment:IndicatorLed:id managed object property"
    ::= { cucsEquipmentIndicatorLedEntry 5 }

cucsEquipmentIndicatorLedName OBJECT-TYPE
    SYNTAX       SnmpAdminString
    MAX-ACCESS   read-only
    STATUS       current
    DESCRIPTION
        "Cisco UCS equipment:IndicatorLed:name managed object property"
    ::= { cucsEquipmentIndicatorLedEntry 6 }

cucsEquipmentIndicatorLedOperState OBJECT-TYPE
    SYNTAX       CucsEquipmentLedOperState
    MAX-ACCESS   read-only
    STATUS       current
    DESCRIPTION
        "Cisco UCS equipment:IndicatorLed:operState managed
        object property"
    ::= { cucsEquipmentIndicatorLedEntry 7 }

cucsEquipmentInventoryStatusTable OBJECT-TYPE
    SYNTAX           SEQUENCE OF CucsEquipmentInventoryStatusEntry
    MAX-ACCESS       not-accessible
    STATUS           current
    DESCRIPTION
        "Cisco UCS equipment:InventoryStatus managed object table"
    ::= { cucsEquipmentObjects 228 }

cucsEquipmentInventoryStatusEntry OBJECT-TYPE
    SYNTAX           CucsEquipmentInventoryStatusEntry
    MAX-ACCESS       not-accessible
    STATUS           current
    DESCRIPTION
        "Entry for the cucsEquipmentInventoryStatusTable table."
    INDEX { cucsEquipmentInventoryStatusInstanceId }
    ::= { cucsEquipmentInventoryStatusTable 1 }

CucsEquipmentInventoryStatusEntry ::= SEQUENCE {
    cucsEquipmentInventoryStatusInstanceId                           CucsManagedObjectId,
    cucsEquipmentInventoryStatusDn                                   CucsManagedObjectDn,
    cucsEquipmentInventoryStatusRn                                   SnmpAdminString,
    cucsEquipmentInventoryStatusCleanupParentOnDiscovery             TruthValue,
    cucsEquipmentInventoryStatusHwInventoryStatus                    CucsComputeInventoryStatus,
    cucsEquipmentInventoryStatusId                                   Gauge32,
    cucsEquipmentInventoryStatusModel                                SnmpAdminString,
    cucsEquipmentInventoryStatusRevision                             SnmpAdminString,
    cucsEquipmentInventoryStatusSerial                               SnmpAdminString,
    cucsEquipmentInventoryStatusVendor                               SnmpAdminString
}

cucsEquipmentInventoryStatusInstanceId OBJECT-TYPE
    SYNTAX       CucsManagedObjectId
    MAX-ACCESS   not-accessible
    STATUS       current
    DESCRIPTION
        "Instance identifier of the managed object."
    ::= { cucsEquipmentInventoryStatusEntry 1 }

cucsEquipmentInventoryStatusDn OBJECT-TYPE
    SYNTAX       CucsManagedObjectDn
    MAX-ACCESS   read-only
    STATUS       current
    DESCRIPTION
        "Cisco UCS equipment:InventoryStatus:dn managed object property"
    ::= { cucsEquipmentInventoryStatusEntry 2 }

cucsEquipmentInventoryStatusRn OBJECT-TYPE
    SYNTAX       SnmpAdminString
    MAX-ACCESS   read-only
    STATUS       current
    DESCRIPTION
        "Cisco UCS equipment:InventoryStatus:rn managed object property"
    ::= { cucsEquipmentInventoryStatusEntry 3 }

cucsEquipmentInventoryStatusCleanupParentOnDiscovery OBJECT-TYPE
    SYNTAX       TruthValue
    MAX-ACCESS   read-only
    STATUS       current
    DESCRIPTION
        "Cisco UCS equipment:InventoryStatus:cleanupParentOnDiscovery
        managed object property"
    ::= { cucsEquipmentInventoryStatusEntry 4 }

cucsEquipmentInventoryStatusHwInventoryStatus OBJECT-TYPE
    SYNTAX       CucsComputeInventoryStatus
    MAX-ACCESS   read-only
    STATUS       current
    DESCRIPTION
        "Cisco UCS equipment:InventoryStatus:hwInventoryStatus
        managed object property"
    ::= { cucsEquipmentInventoryStatusEntry 5 }

cucsEquipmentInventoryStatusId OBJECT-TYPE
    SYNTAX       Gauge32
    MAX-ACCESS   read-only
    STATUS       current
    DESCRIPTION
        "Cisco UCS equipment:InventoryStatus:id managed object property"
    ::= { cucsEquipmentInventoryStatusEntry 6 }

cucsEquipmentInventoryStatusModel OBJECT-TYPE
    SYNTAX       SnmpAdminString
    MAX-ACCESS   read-only
    STATUS       current
    DESCRIPTION
        "Cisco UCS equipment:InventoryStatus:model managed
        object property"
    ::= { cucsEquipmentInventoryStatusEntry 7 }

cucsEquipmentInventoryStatusRevision OBJECT-TYPE
    SYNTAX       SnmpAdminString
    MAX-ACCESS   read-only
    STATUS       current
    DESCRIPTION
        "Cisco UCS equipment:InventoryStatus:revision managed
        object property"
    ::= { cucsEquipmentInventoryStatusEntry 8 }

cucsEquipmentInventoryStatusSerial OBJECT-TYPE
    SYNTAX       SnmpAdminString
    MAX-ACCESS   read-only
    STATUS       current
    DESCRIPTION
        "Cisco UCS equipment:InventoryStatus:serial managed
        object property"
    ::= { cucsEquipmentInventoryStatusEntry 9 }

cucsEquipmentInventoryStatusVendor OBJECT-TYPE
    SYNTAX       SnmpAdminString
    MAX-ACCESS   read-only
    STATUS       current
    DESCRIPTION
        "Cisco UCS equipment:InventoryStatus:vendor managed
        object property"
    ::= { cucsEquipmentInventoryStatusEntry 10 }

cucsEquipmentKvmMgmtCapTable OBJECT-TYPE
    SYNTAX           SEQUENCE OF CucsEquipmentKvmMgmtCapEntry
    MAX-ACCESS       not-accessible
    STATUS           current
    DESCRIPTION
        "Cisco UCS equipment:KvmMgmtCap managed object table"
    ::= { cucsEquipmentObjects 128 }

cucsEquipmentKvmMgmtCapEntry OBJECT-TYPE
    SYNTAX           CucsEquipmentKvmMgmtCapEntry
    MAX-ACCESS       not-accessible
    STATUS           current
    DESCRIPTION
        "Entry for the cucsEquipmentKvmMgmtCapTable table."
    INDEX { cucsEquipmentKvmMgmtCapInstanceId }
    ::= { cucsEquipmentKvmMgmtCapTable 1 }

CucsEquipmentKvmMgmtCapEntry ::= SEQUENCE {
    cucsEquipmentKvmMgmtCapInstanceId                                CucsManagedObjectId,
    cucsEquipmentKvmMgmtCapDn                                        CucsManagedObjectDn,
    cucsEquipmentKvmMgmtCapRn                                        SnmpAdminString,
    cucsEquipmentKvmMgmtCapIsSupported                               CucsEquipmentIsSupported,
    cucsEquipmentKvmMgmtCapMinCimcVersion                            SnmpAdminString,
    cucsEquipmentKvmMgmtCapMinWebUISupportedCimcVer                  SnmpAdminString
}

cucsEquipmentKvmMgmtCapInstanceId OBJECT-TYPE
    SYNTAX       CucsManagedObjectId
    MAX-ACCESS   not-accessible
    STATUS       current
    DESCRIPTION
        "Instance identifier of the managed object."
    ::= { cucsEquipmentKvmMgmtCapEntry 1 }

cucsEquipmentKvmMgmtCapDn OBJECT-TYPE
    SYNTAX       CucsManagedObjectDn
    MAX-ACCESS   read-only
    STATUS       current
    DESCRIPTION
        "Cisco UCS equipment:KvmMgmtCap:dn managed object property"
    ::= { cucsEquipmentKvmMgmtCapEntry 2 }

cucsEquipmentKvmMgmtCapRn OBJECT-TYPE
    SYNTAX       SnmpAdminString
    MAX-ACCESS   read-only
    STATUS       current
    DESCRIPTION
        "Cisco UCS equipment:KvmMgmtCap:rn managed object property"
    ::= { cucsEquipmentKvmMgmtCapEntry 3 }

cucsEquipmentKvmMgmtCapIsSupported OBJECT-TYPE
    SYNTAX       CucsEquipmentIsSupported
    MAX-ACCESS   read-only
    STATUS       current
    DESCRIPTION
        "Cisco UCS equipment:KvmMgmtCap:isSupported managed
        object property"
    ::= { cucsEquipmentKvmMgmtCapEntry 4 }

cucsEquipmentKvmMgmtCapMinCimcVersion OBJECT-TYPE
    SYNTAX       SnmpAdminString
    MAX-ACCESS   read-only
    STATUS       current
    DESCRIPTION
        "Cisco UCS equipment:KvmMgmtCap:minCimcVersion
        managed object property"
    ::= { cucsEquipmentKvmMgmtCapEntry 5 }

cucsEquipmentKvmMgmtCapMinWebUISupportedCimcVer OBJECT-TYPE
    SYNTAX       SnmpAdminString
    MAX-ACCESS   read-only
    STATUS       current
    DESCRIPTION
        "Cisco UCS equipment:KvmMgmtCap:minWebUISupportedCimcVer
        managed object property"
    ::= { cucsEquipmentKvmMgmtCapEntry 6 }

cucsEquipmentLocalDiskCapProviderTable OBJECT-TYPE
    SYNTAX           SEQUENCE OF CucsEquipmentLocalDiskCapProviderEntry
    MAX-ACCESS       not-accessible
    STATUS           current
    DESCRIPTION
        "Cisco UCS equipment:LocalDiskCapProvider managed object table"
    ::= { cucsEquipmentObjects 36 }

cucsEquipmentLocalDiskCapProviderEntry OBJECT-TYPE
    SYNTAX           CucsEquipmentLocalDiskCapProviderEntry
    MAX-ACCESS       not-accessible
    STATUS           current
    DESCRIPTION
        "Entry for the cucsEquipmentLocalDiskCapProviderTable table."
    INDEX { cucsEquipmentLocalDiskCapProviderInstanceId }
    ::= { cucsEquipmentLocalDiskCapProviderTable 1 }

CucsEquipmentLocalDiskCapProviderEntry ::= SEQUENCE {
    cucsEquipmentLocalDiskCapProviderInstanceId                      CucsManagedObjectId,
    cucsEquipmentLocalDiskCapProviderDn                              CucsManagedObjectDn,
    cucsEquipmentLocalDiskCapProviderRn                              SnmpAdminString,
    cucsEquipmentLocalDiskCapProviderDeprecated                      TruthValue,
    cucsEquipmentLocalDiskCapProviderGencount                        Gauge32,
    cucsEquipmentLocalDiskCapProviderMgmtPlaneVer                    SnmpAdminString,
    cucsEquipmentLocalDiskCapProviderModel                           SnmpAdminString,
    cucsEquipmentLocalDiskCapProviderRevision                        SnmpAdminString,
    cucsEquipmentLocalDiskCapProviderVendor                          SnmpAdminString,
    cucsEquipmentLocalDiskCapProviderPromCardType                    Gauge32,
    cucsEquipmentLocalDiskCapProviderDeleted                         TruthValue,
    cucsEquipmentLocalDiskCapProviderElementLoadFailures             Gauge32,
    cucsEquipmentLocalDiskCapProviderElementsLoaded                  Gauge32,
    cucsEquipmentLocalDiskCapProviderLoadErrors                      Gauge32,
    cucsEquipmentLocalDiskCapProviderLoadWarnings                    Gauge32
}

cucsEquipmentLocalDiskCapProviderInstanceId OBJECT-TYPE
    SYNTAX       CucsManagedObjectId
    MAX-ACCESS   not-accessible
    STATUS       current
    DESCRIPTION
        "Instance identifier of the managed object."
    ::= { cucsEquipmentLocalDiskCapProviderEntry 1 }

cucsEquipmentLocalDiskCapProviderDn OBJECT-TYPE
    SYNTAX       CucsManagedObjectDn
    MAX-ACCESS   read-only
    STATUS       current
    DESCRIPTION
        "Cisco UCS equipment:LocalDiskCapProvider:dn managed
        object property"
    ::= { cucsEquipmentLocalDiskCapProviderEntry 2 }

cucsEquipmentLocalDiskCapProviderRn OBJECT-TYPE
    SYNTAX       SnmpAdminString
    MAX-ACCESS   read-only
    STATUS       current
    DESCRIPTION
        "Cisco UCS equipment:LocalDiskCapProvider:rn managed
        object property"
    ::= { cucsEquipmentLocalDiskCapProviderEntry 3 }

cucsEquipmentLocalDiskCapProviderDeprecated OBJECT-TYPE
    SYNTAX       TruthValue
    MAX-ACCESS   read-only
    STATUS       current
    DESCRIPTION
        "Cisco UCS equipment:LocalDiskCapProvider:deprecated
        managed object property"
    ::= { cucsEquipmentLocalDiskCapProviderEntry 4 }

cucsEquipmentLocalDiskCapProviderGencount OBJECT-TYPE
    SYNTAX       Gauge32
    MAX-ACCESS   read-only
    STATUS       current
    DESCRIPTION
        "Cisco UCS equipment:LocalDiskCapProvider:gencount
        managed object property"
    ::= { cucsEquipmentLocalDiskCapProviderEntry 5 }

cucsEquipmentLocalDiskCapProviderMgmtPlaneVer OBJECT-TYPE
    SYNTAX       SnmpAdminString
    MAX-ACCESS   read-only
    STATUS       current
    DESCRIPTION
        "Cisco UCS equipment:LocalDiskCapProvider:mgmtPlaneVer
        managed object property"
    ::= { cucsEquipmentLocalDiskCapProviderEntry 6 }

cucsEquipmentLocalDiskCapProviderModel OBJECT-TYPE
    SYNTAX       SnmpAdminString
    MAX-ACCESS   read-only
    STATUS       current
    DESCRIPTION
        "Cisco UCS equipment:LocalDiskCapProvider:model
        managed object property"
    ::= { cucsEquipmentLocalDiskCapProviderEntry 7 }

cucsEquipmentLocalDiskCapProviderRevision OBJECT-TYPE
    SYNTAX       SnmpAdminString
    MAX-ACCESS   read-only
    STATUS       current
    DESCRIPTION
        "Cisco UCS equipment:LocalDiskCapProvider:revision
        managed object property"
    ::= { cucsEquipmentLocalDiskCapProviderEntry 8 }

cucsEquipmentLocalDiskCapProviderVendor OBJECT-TYPE
    SYNTAX       SnmpAdminString
    MAX-ACCESS   read-only
    STATUS       current
    DESCRIPTION
        "Cisco UCS equipment:LocalDiskCapProvider:vendor
        managed object property"
    ::= { cucsEquipmentLocalDiskCapProviderEntry 9 }

cucsEquipmentLocalDiskCapProviderPromCardType OBJECT-TYPE
    SYNTAX       Gauge32
    MAX-ACCESS   read-only
    STATUS       current
    DESCRIPTION
        "Cisco UCS equipment:LocalDiskCapProvider:promCardType
        managed object property"
    ::= { cucsEquipmentLocalDiskCapProviderEntry 10 }

cucsEquipmentLocalDiskCapProviderDeleted OBJECT-TYPE
    SYNTAX       TruthValue
    MAX-ACCESS   read-only
    STATUS       current
    DESCRIPTION
        "Cisco UCS equipment:LocalDiskCapProvider:deleted
        managed object property"
    ::= { cucsEquipmentLocalDiskCapProviderEntry 11 }

cucsEquipmentLocalDiskCapProviderElementLoadFailures OBJECT-TYPE
    SYNTAX       Gauge32
    MAX-ACCESS   read-only
    STATUS       current
    DESCRIPTION
        "Cisco UCS equipment:LocalDiskCapProvider:elementLoadFailures
        managed object property"
    ::= { cucsEquipmentLocalDiskCapProviderEntry 12 }

cucsEquipmentLocalDiskCapProviderElementsLoaded OBJECT-TYPE
    SYNTAX       Gauge32
    MAX-ACCESS   read-only
    STATUS       current
    DESCRIPTION
        "Cisco UCS equipment:LocalDiskCapProvider:elementsLoaded
        managed object property"
    ::= { cucsEquipmentLocalDiskCapProviderEntry 13 }

cucsEquipmentLocalDiskCapProviderLoadErrors OBJECT-TYPE
    SYNTAX       Gauge32
    MAX-ACCESS   read-only
    STATUS       current
    DESCRIPTION
        "Cisco UCS equipment:LocalDiskCapProvider:loadErrors
        managed object property"
    ::= { cucsEquipmentLocalDiskCapProviderEntry 14 }

cucsEquipmentLocalDiskCapProviderLoadWarnings OBJECT-TYPE
    SYNTAX       Gauge32
    MAX-ACCESS   read-only
    STATUS       current
    DESCRIPTION
        "Cisco UCS equipment:LocalDiskCapProvider:loadWarnings
        managed object property"
    ::= { cucsEquipmentLocalDiskCapProviderEntry 15 }

cucsEquipmentLocalDiskControllerCapProviderTable OBJECT-TYPE
    SYNTAX           SEQUENCE OF CucsEquipmentLocalDiskControllerCapProviderEntry
    MAX-ACCESS       not-accessible
    STATUS           current
    DESCRIPTION
        "Cisco UCS equipment:LocalDiskControllerCapProvider
        managed object table"
    ::= { cucsEquipmentObjects 37 }

cucsEquipmentLocalDiskControllerCapProviderEntry OBJECT-TYPE
    SYNTAX           CucsEquipmentLocalDiskControllerCapProviderEntry
    MAX-ACCESS       not-accessible
    STATUS           current
    DESCRIPTION
        "Entry for the cucsEquipmentLocalDiskControllerCapProviderTable table."
    INDEX { cucsEquipmentLocalDiskControllerCapProviderInstanceId }
    ::= { cucsEquipmentLocalDiskControllerCapProviderTable 1 }

CucsEquipmentLocalDiskControllerCapProviderEntry ::= SEQUENCE {
    cucsEquipmentLocalDiskControllerCapProviderInstanceId            CucsManagedObjectId,
    cucsEquipmentLocalDiskControllerCapProviderDn                    CucsManagedObjectDn,
    cucsEquipmentLocalDiskControllerCapProviderRn                    SnmpAdminString,
    cucsEquipmentLocalDiskControllerCapProviderDeprecated            TruthValue,
    cucsEquipmentLocalDiskControllerCapProviderGencount              Gauge32,
    cucsEquipmentLocalDiskControllerCapProviderMgmtPlaneVer          SnmpAdminString,
    cucsEquipmentLocalDiskControllerCapProviderModel                 SnmpAdminString,
    cucsEquipmentLocalDiskControllerCapProviderRevision              SnmpAdminString,
    cucsEquipmentLocalDiskControllerCapProviderVendor                SnmpAdminString,
    cucsEquipmentLocalDiskControllerCapProviderPromCardType          Gauge32,
    cucsEquipmentLocalDiskControllerCapProviderDeleted               TruthValue,
    cucsEquipmentLocalDiskControllerCapProviderForm                  CucsEquipmentControllerForm,
    cucsEquipmentLocalDiskControllerCapProviderElementLoadFailures   Gauge32,
    cucsEquipmentLocalDiskControllerCapProviderElementsLoaded        Gauge32,
    cucsEquipmentLocalDiskControllerCapProviderInternalports         Gauge32,
    cucsEquipmentLocalDiskControllerCapProviderLoadErrors            Gauge32,
    cucsEquipmentLocalDiskControllerCapProviderLoadWarnings          Gauge32,
    cucsEquipmentLocalDiskControllerCapProviderCardType              CucsEquipmentCType,
    cucsEquipmentLocalDiskControllerCapProviderContainmentMethod     CucsEquipmentStorageContainmentMethod,
    cucsEquipmentLocalDiskControllerCapProviderControllerType        CucsEquipmentContType,
    cucsEquipmentLocalDiskControllerCapProviderControllerMode        CucsStorageControllerMode,
    cucsEquipmentLocalDiskControllerCapProviderOnBoardMemorySize     Unsigned64,
    cucsEquipmentLocalDiskControllerCapProviderNumControllers        Gauge32
}

cucsEquipmentLocalDiskControllerCapProviderInstanceId OBJECT-TYPE
    SYNTAX       CucsManagedObjectId
    MAX-ACCESS   not-accessible
    STATUS       current
    DESCRIPTION
        "Instance identifier of the managed object."
    ::= { cucsEquipmentLocalDiskControllerCapProviderEntry 1 }

cucsEquipmentLocalDiskControllerCapProviderDn OBJECT-TYPE
    SYNTAX       CucsManagedObjectDn
    MAX-ACCESS   read-only
    STATUS       current
    DESCRIPTION
        "Cisco UCS equipment:LocalDiskControllerCapProvider:dn
        managed object property"
    ::= { cucsEquipmentLocalDiskControllerCapProviderEntry 2 }

cucsEquipmentLocalDiskControllerCapProviderRn OBJECT-TYPE
    SYNTAX       SnmpAdminString
    MAX-ACCESS   read-only
    STATUS       current
    DESCRIPTION
        "Cisco UCS equipment:LocalDiskControllerCapProvider:rn
        managed object property"
    ::= { cucsEquipmentLocalDiskControllerCapProviderEntry 3 }

cucsEquipmentLocalDiskControllerCapProviderDeprecated OBJECT-TYPE
    SYNTAX       TruthValue
    MAX-ACCESS   read-only
    STATUS       current
    DESCRIPTION
        "Cisco UCS equipment:LocalDiskControllerCapProvider:deprecated
        managed object property"
    ::= { cucsEquipmentLocalDiskControllerCapProviderEntry 4 }

cucsEquipmentLocalDiskControllerCapProviderGencount OBJECT-TYPE
    SYNTAX       Gauge32
    MAX-ACCESS   read-only
    STATUS       current
    DESCRIPTION
        "Cisco UCS equipment:LocalDiskControllerCapProvider:gencount
        managed object property"
    ::= { cucsEquipmentLocalDiskControllerCapProviderEntry 5 }

cucsEquipmentLocalDiskControllerCapProviderMgmtPlaneVer OBJECT-TYPE
    SYNTAX       SnmpAdminString
    MAX-ACCESS   read-only
    STATUS       current
    DESCRIPTION
        "Cisco UCS equipment:LocalDiskControllerCapProvider:mgmtPlaneVer
        managed object property"
    ::= { cucsEquipmentLocalDiskControllerCapProviderEntry 6 }

cucsEquipmentLocalDiskControllerCapProviderModel OBJECT-TYPE
    SYNTAX       SnmpAdminString
    MAX-ACCESS   read-only
    STATUS       current
    DESCRIPTION
        "Cisco UCS equipment:LocalDiskControllerCapProvider:model
        managed object property"
    ::= { cucsEquipmentLocalDiskControllerCapProviderEntry 7 }

cucsEquipmentLocalDiskControllerCapProviderRevision OBJECT-TYPE
    SYNTAX       SnmpAdminString
    MAX-ACCESS   read-only
    STATUS       current
    DESCRIPTION
        "Cisco UCS equipment:LocalDiskControllerCapProvider:revision
        managed object property"
    ::= { cucsEquipmentLocalDiskControllerCapProviderEntry 8 }

cucsEquipmentLocalDiskControllerCapProviderVendor OBJECT-TYPE
    SYNTAX       SnmpAdminString
    MAX-ACCESS   read-only
    STATUS       current
    DESCRIPTION
        "Cisco UCS equipment:LocalDiskControllerCapProvider:vendor
        managed object property"
    ::= { cucsEquipmentLocalDiskControllerCapProviderEntry 9 }

cucsEquipmentLocalDiskControllerCapProviderPromCardType OBJECT-TYPE
    SYNTAX       Gauge32
    MAX-ACCESS   read-only
    STATUS       current
    DESCRIPTION
        "Cisco UCS equipment:LocalDiskControllerCapProvider:promCardType
        managed object property"
    ::= { cucsEquipmentLocalDiskControllerCapProviderEntry 10 }

cucsEquipmentLocalDiskControllerCapProviderDeleted OBJECT-TYPE
    SYNTAX       TruthValue
    MAX-ACCESS   read-only
    STATUS       current
    DESCRIPTION
        "Cisco UCS equipment:LocalDiskControllerCapProvider:deleted
        managed object property"
    ::= { cucsEquipmentLocalDiskControllerCapProviderEntry 11 }

cucsEquipmentLocalDiskControllerCapProviderForm OBJECT-TYPE
    SYNTAX       CucsEquipmentControllerForm
    MAX-ACCESS   read-only
    STATUS       current
    DESCRIPTION
        "Cisco UCS equipment:LocalDiskControllerCapProvider:form
        managed object property"
    ::= { cucsEquipmentLocalDiskControllerCapProviderEntry 12 }

cucsEquipmentLocalDiskControllerCapProviderElementLoadFailures OBJECT-TYPE
    SYNTAX       Gauge32
    MAX-ACCESS   read-only
    STATUS       current
    DESCRIPTION
        "Cisco UCS equipment:LocalDiskControllerCapProvider:elementLoadFai
        lures managed object property"
    ::= { cucsEquipmentLocalDiskControllerCapProviderEntry 13 }

cucsEquipmentLocalDiskControllerCapProviderElementsLoaded OBJECT-TYPE
    SYNTAX       Gauge32
    MAX-ACCESS   read-only
    STATUS       current
    DESCRIPTION
        "Cisco UCS equipment:LocalDiskControllerCapProvider:elementsLoaded
         managed object property"
    ::= { cucsEquipmentLocalDiskControllerCapProviderEntry 14 }

cucsEquipmentLocalDiskControllerCapProviderInternalports OBJECT-TYPE
    SYNTAX       Gauge32
    MAX-ACCESS   read-only
    STATUS       current
    DESCRIPTION
        "Cisco UCS equipment:LocalDiskControllerCapProvider:internalports
        managed object property"
    ::= { cucsEquipmentLocalDiskControllerCapProviderEntry 15 }

cucsEquipmentLocalDiskControllerCapProviderLoadErrors OBJECT-TYPE
    SYNTAX       Gauge32
    MAX-ACCESS   read-only
    STATUS       current
    DESCRIPTION
        "Cisco UCS equipment:LocalDiskControllerCapProvider:loadErrors
        managed object property"
    ::= { cucsEquipmentLocalDiskControllerCapProviderEntry 16 }

cucsEquipmentLocalDiskControllerCapProviderLoadWarnings OBJECT-TYPE
    SYNTAX       Gauge32
    MAX-ACCESS   read-only
    STATUS       current
    DESCRIPTION
        "Cisco UCS equipment:LocalDiskControllerCapProvider:loadWarnings
        managed object property"
    ::= { cucsEquipmentLocalDiskControllerCapProviderEntry 17 }

cucsEquipmentLocalDiskControllerCapProviderCardType OBJECT-TYPE
    SYNTAX       CucsEquipmentCType
    MAX-ACCESS   read-only
    STATUS       current
    DESCRIPTION
        "Cisco UCS equipment:LocalDiskControllerCapProvider:cardType
        managed object property"
    ::= { cucsEquipmentLocalDiskControllerCapProviderEntry 18 }

cucsEquipmentLocalDiskControllerCapProviderContainmentMethod OBJECT-TYPE
    SYNTAX       CucsEquipmentStorageContainmentMethod
    MAX-ACCESS   read-only
    STATUS       current
    DESCRIPTION
        "Cisco UCS equipment:LocalDiskControllerCapProvider:containmentMet
        hod managed object property"
    ::= { cucsEquipmentLocalDiskControllerCapProviderEntry 19 }

cucsEquipmentLocalDiskControllerCapProviderControllerType OBJECT-TYPE
    SYNTAX       CucsEquipmentContType
    MAX-ACCESS   read-only
    STATUS       current
    DESCRIPTION
        "Cisco UCS equipment:LocalDiskControllerCapProvider:controllerType
         managed object property"
    ::= { cucsEquipmentLocalDiskControllerCapProviderEntry 20 }

cucsEquipmentLocalDiskControllerCapProviderControllerMode OBJECT-TYPE
    SYNTAX       CucsStorageControllerMode
    MAX-ACCESS   read-only
    STATUS       current
    DESCRIPTION
        "Cisco UCS equipment:LocalDiskControllerCapProvider:controllerMode
         managed object property"
    ::= { cucsEquipmentLocalDiskControllerCapProviderEntry 21 }

cucsEquipmentLocalDiskControllerCapProviderOnBoardMemorySize OBJECT-TYPE
    SYNTAX       Unsigned64
    MAX-ACCESS   read-only
    STATUS       current
    DESCRIPTION
        "Cisco UCS equipment:LocalDiskControllerCapProvider:onBoardMemoryS
        ize managed object property"
    ::= { cucsEquipmentLocalDiskControllerCapProviderEntry 22 }

cucsEquipmentLocalDiskControllerCapProviderNumControllers OBJECT-TYPE
    SYNTAX       Gauge32
    MAX-ACCESS   read-only
    STATUS       current
    DESCRIPTION
        "Cisco UCS equipment:LocalDiskControllerCapProvider:numControllers
         managed object property"
    ::= { cucsEquipmentLocalDiskControllerCapProviderEntry 23 }

cucsEquipmentLocalDiskControllerCapRefTable OBJECT-TYPE
    SYNTAX           SEQUENCE OF CucsEquipmentLocalDiskControllerCapRefEntry
    MAX-ACCESS       not-accessible
    STATUS           current
    DESCRIPTION
        "Cisco UCS equipment:LocalDiskControllerCapRef
        managed object table"
    ::= { cucsEquipmentObjects 80 }

cucsEquipmentLocalDiskControllerCapRefEntry OBJECT-TYPE
    SYNTAX           CucsEquipmentLocalDiskControllerCapRefEntry
    MAX-ACCESS       not-accessible
    STATUS           current
    DESCRIPTION
        "Entry for the cucsEquipmentLocalDiskControllerCapRefTable table."
    INDEX { cucsEquipmentLocalDiskControllerCapRefInstanceId }
    ::= { cucsEquipmentLocalDiskControllerCapRefTable 1 }

CucsEquipmentLocalDiskControllerCapRefEntry ::= SEQUENCE {
    cucsEquipmentLocalDiskControllerCapRefInstanceId                 CucsManagedObjectId,
    cucsEquipmentLocalDiskControllerCapRefDn                         CucsManagedObjectDn,
    cucsEquipmentLocalDiskControllerCapRefRn                         SnmpAdminString,
    cucsEquipmentLocalDiskControllerCapRefIsSupported                CucsEquipmentIsSupported,
    cucsEquipmentLocalDiskControllerCapRefModel                      SnmpAdminString,
    cucsEquipmentLocalDiskControllerCapRefRevision                   SnmpAdminString,
    cucsEquipmentLocalDiskControllerCapRefVendor                     SnmpAdminString
}

cucsEquipmentLocalDiskControllerCapRefInstanceId OBJECT-TYPE
    SYNTAX       CucsManagedObjectId
    MAX-ACCESS   not-accessible
    STATUS       current
    DESCRIPTION
        "Instance identifier of the managed object."
    ::= { cucsEquipmentLocalDiskControllerCapRefEntry 1 }

cucsEquipmentLocalDiskControllerCapRefDn OBJECT-TYPE
    SYNTAX       CucsManagedObjectDn
    MAX-ACCESS   read-only
    STATUS       current
    DESCRIPTION
        "Cisco UCS equipment:LocalDiskControllerCapRef:dn
        managed object property"
    ::= { cucsEquipmentLocalDiskControllerCapRefEntry 2 }

cucsEquipmentLocalDiskControllerCapRefRn OBJECT-TYPE
    SYNTAX       SnmpAdminString
    MAX-ACCESS   read-only
    STATUS       current
    DESCRIPTION
        "Cisco UCS equipment:LocalDiskControllerCapRef:rn
        managed object property"
    ::= { cucsEquipmentLocalDiskControllerCapRefEntry 3 }

cucsEquipmentLocalDiskControllerCapRefIsSupported OBJECT-TYPE
    SYNTAX       CucsEquipmentIsSupported
    MAX-ACCESS   read-only
    STATUS       current
    DESCRIPTION
        "Cisco UCS equipment:LocalDiskControllerCapRef:isSupported
        managed object property"
    ::= { cucsEquipmentLocalDiskControllerCapRefEntry 4 }

cucsEquipmentLocalDiskControllerCapRefModel OBJECT-TYPE
    SYNTAX       SnmpAdminString
    MAX-ACCESS   read-only
    STATUS       current
    DESCRIPTION
        "Cisco UCS equipment:LocalDiskControllerCapRef:model
        managed object property"
    ::= { cucsEquipmentLocalDiskControllerCapRefEntry 5 }

cucsEquipmentLocalDiskControllerCapRefRevision OBJECT-TYPE
    SYNTAX       SnmpAdminString
    MAX-ACCESS   read-only
    STATUS       current
    DESCRIPTION
        "Cisco UCS equipment:LocalDiskControllerCapRef:revision
        managed object property"
    ::= { cucsEquipmentLocalDiskControllerCapRefEntry 6 }

cucsEquipmentLocalDiskControllerCapRefVendor OBJECT-TYPE
    SYNTAX       SnmpAdminString
    MAX-ACCESS   read-only
    STATUS       current
    DESCRIPTION
        "Cisco UCS equipment:LocalDiskControllerCapRef:vendor
        managed object property"
    ::= { cucsEquipmentLocalDiskControllerCapRefEntry 7 }

cucsEquipmentLocalDiskControllerDefTable OBJECT-TYPE
    SYNTAX           SEQUENCE OF CucsEquipmentLocalDiskControllerDefEntry
    MAX-ACCESS       not-accessible
    STATUS           current
    DESCRIPTION
        "Cisco UCS equipment:LocalDiskControllerDef managed object table"
    ::= { cucsEquipmentObjects 38 }

cucsEquipmentLocalDiskControllerDefEntry OBJECT-TYPE
    SYNTAX           CucsEquipmentLocalDiskControllerDefEntry
    MAX-ACCESS       not-accessible
    STATUS           current
    DESCRIPTION
        "Entry for the cucsEquipmentLocalDiskControllerDefTable table."
    INDEX { cucsEquipmentLocalDiskControllerDefInstanceId }
    ::= { cucsEquipmentLocalDiskControllerDefTable 1 }

CucsEquipmentLocalDiskControllerDefEntry ::= SEQUENCE {
    cucsEquipmentLocalDiskControllerDefInstanceId                    CucsManagedObjectId,
    cucsEquipmentLocalDiskControllerDefDn                            CucsManagedObjectDn,
    cucsEquipmentLocalDiskControllerDefRn                            SnmpAdminString,
    cucsEquipmentLocalDiskControllerDefDescr                         SnmpAdminString,
    cucsEquipmentLocalDiskControllerDefForceUpdateVersion            TruthValue,
    cucsEquipmentLocalDiskControllerDefIntId                         SnmpAdminString,
    cucsEquipmentLocalDiskControllerDefName                          SnmpAdminString,
    cucsEquipmentLocalDiskControllerDefPolicyLevel                   Gauge32,
    cucsEquipmentLocalDiskControllerDefPolicyOwner                   CucsPolicyPolicyOwner,
    cucsEquipmentLocalDiskControllerDefConfigParmModSupported        TruthValue,
    cucsEquipmentLocalDiskControllerDefOobInterfaceSupported         TruthValue,
    cucsEquipmentLocalDiskControllerDefTfmSupported                  TruthValue,
    cucsEquipmentLocalDiskControllerDefControllerDefType             CucsEquipmentControllerDefType,
    cucsEquipmentLocalDiskControllerDefDiskSharingSupported          TruthValue,
    cucsEquipmentLocalDiskControllerDefJbodSharingSupported          TruthValue,
    cucsEquipmentLocalDiskControllerDefOnBoardMemoryCheckNeeded      TruthValue,
    cucsEquipmentLocalDiskControllerDefOobControllerClassIdentifier  CucsEquipmentLocalDiskControllerDefOobControllerClassIdentifier,
    cucsEquipmentLocalDiskControllerDefZoningSupported               TruthValue,
    cucsEquipmentLocalDiskControllerDefControllerSubType             CucsEquipmentControllerSubType,
    cucsEquipmentLocalDiskControllerDefHotPlugSupported              TruthValue
}

cucsEquipmentLocalDiskControllerDefInstanceId OBJECT-TYPE
    SYNTAX       CucsManagedObjectId
    MAX-ACCESS   not-accessible
    STATUS       current
    DESCRIPTION
        "Instance identifier of the managed object."
    ::= { cucsEquipmentLocalDiskControllerDefEntry 1 }

cucsEquipmentLocalDiskControllerDefDn OBJECT-TYPE
    SYNTAX       CucsManagedObjectDn
    MAX-ACCESS   read-only
    STATUS       current
    DESCRIPTION
        "Cisco UCS equipment:LocalDiskControllerDef:dn
        managed object property"
    ::= { cucsEquipmentLocalDiskControllerDefEntry 2 }

cucsEquipmentLocalDiskControllerDefRn OBJECT-TYPE
    SYNTAX       SnmpAdminString
    MAX-ACCESS   read-only
    STATUS       current
    DESCRIPTION
        "Cisco UCS equipment:LocalDiskControllerDef:rn
        managed object property"
    ::= { cucsEquipmentLocalDiskControllerDefEntry 3 }

cucsEquipmentLocalDiskControllerDefDescr OBJECT-TYPE
    SYNTAX       SnmpAdminString
    MAX-ACCESS   read-only
    STATUS       current
    DESCRIPTION
        "Cisco UCS equipment:LocalDiskControllerDef:descr
        managed object property"
    ::= { cucsEquipmentLocalDiskControllerDefEntry 4 }

cucsEquipmentLocalDiskControllerDefForceUpdateVersion OBJECT-TYPE
    SYNTAX       TruthValue
    MAX-ACCESS   read-only
    STATUS       current
    DESCRIPTION
        "Cisco UCS equipment:LocalDiskControllerDef:forceUpdateVersion
        managed object property"
    ::= { cucsEquipmentLocalDiskControllerDefEntry 5 }

cucsEquipmentLocalDiskControllerDefIntId OBJECT-TYPE
    SYNTAX       SnmpAdminString
    MAX-ACCESS   read-only
    STATUS       current
    DESCRIPTION
        "Cisco UCS equipment:LocalDiskControllerDef:intId
        managed object property"
    ::= { cucsEquipmentLocalDiskControllerDefEntry 6 }

cucsEquipmentLocalDiskControllerDefName OBJECT-TYPE
    SYNTAX       SnmpAdminString
    MAX-ACCESS   read-only
    STATUS       current
    DESCRIPTION
        "Cisco UCS equipment:LocalDiskControllerDef:name
        managed object property"
    ::= { cucsEquipmentLocalDiskControllerDefEntry 7 }

cucsEquipmentLocalDiskControllerDefPolicyLevel OBJECT-TYPE
    SYNTAX       Gauge32
    MAX-ACCESS   read-only
    STATUS       current
    DESCRIPTION
        "Cisco UCS equipment:LocalDiskControllerDef:policyLevel
        managed object property"
    ::= { cucsEquipmentLocalDiskControllerDefEntry 8 }

cucsEquipmentLocalDiskControllerDefPolicyOwner OBJECT-TYPE
    SYNTAX       CucsPolicyPolicyOwner
    MAX-ACCESS   read-only
    STATUS       current
    DESCRIPTION
        "Cisco UCS equipment:LocalDiskControllerDef:policyOwner
        managed object property"
    ::= { cucsEquipmentLocalDiskControllerDefEntry 9 }

cucsEquipmentLocalDiskControllerDefConfigParmModSupported OBJECT-TYPE
    SYNTAX       TruthValue
    MAX-ACCESS   read-only
    STATUS       current
    DESCRIPTION
        "Cisco UCS equipment:LocalDiskControllerDef:configParmModSupported
         managed object property"
    ::= { cucsEquipmentLocalDiskControllerDefEntry 10 }

cucsEquipmentLocalDiskControllerDefOobInterfaceSupported OBJECT-TYPE
    SYNTAX       TruthValue
    MAX-ACCESS   read-only
    STATUS       current
    DESCRIPTION
        "Cisco UCS equipment:LocalDiskControllerDef:oobInterfaceSupported
        managed object property"
    ::= { cucsEquipmentLocalDiskControllerDefEntry 11 }

cucsEquipmentLocalDiskControllerDefTfmSupported OBJECT-TYPE
    SYNTAX       TruthValue
    MAX-ACCESS   read-only
    STATUS       current
    DESCRIPTION
        "Cisco UCS equipment:LocalDiskControllerDef:tfmSupported
        managed object property"
    ::= { cucsEquipmentLocalDiskControllerDefEntry 12 }

cucsEquipmentLocalDiskControllerDefControllerDefType OBJECT-TYPE
    SYNTAX       CucsEquipmentControllerDefType
    MAX-ACCESS   read-only
    STATUS       current
    DESCRIPTION
        "Cisco UCS equipment:LocalDiskControllerDef:controllerDefType
        managed object property"
    ::= { cucsEquipmentLocalDiskControllerDefEntry 13 }

cucsEquipmentLocalDiskControllerDefDiskSharingSupported OBJECT-TYPE
    SYNTAX       TruthValue
    MAX-ACCESS   read-only
    STATUS       current
    DESCRIPTION
        "Cisco UCS equipment:LocalDiskControllerDef:diskSharingSupported
        managed object property"
    ::= { cucsEquipmentLocalDiskControllerDefEntry 14 }

cucsEquipmentLocalDiskControllerDefJbodSharingSupported OBJECT-TYPE
    SYNTAX       TruthValue
    MAX-ACCESS   read-only
    STATUS       current
    DESCRIPTION
        "Cisco UCS equipment:LocalDiskControllerDef:jbodSharingSupported
        managed object property"
    ::= { cucsEquipmentLocalDiskControllerDefEntry 15 }

cucsEquipmentLocalDiskControllerDefOnBoardMemoryCheckNeeded OBJECT-TYPE
    SYNTAX       TruthValue
    MAX-ACCESS   read-only
    STATUS       current
    DESCRIPTION
        "Cisco UCS equipment:LocalDiskControllerDef:onBoardMemoryCheckNeed
        ed managed object property"
    ::= { cucsEquipmentLocalDiskControllerDefEntry 16 }

cucsEquipmentLocalDiskControllerDefOobControllerClassIdentifier OBJECT-TYPE
    SYNTAX       CucsEquipmentLocalDiskControllerDefOobControllerClassIdentifier
    MAX-ACCESS   read-only
    STATUS       current
    DESCRIPTION
        "Cisco UCS equipment:LocalDiskControllerDef:oobControllerClassIden
        tifier managed object property"
    ::= { cucsEquipmentLocalDiskControllerDefEntry 17 }

cucsEquipmentLocalDiskControllerDefZoningSupported OBJECT-TYPE
    SYNTAX       TruthValue
    MAX-ACCESS   read-only
    STATUS       current
    DESCRIPTION
        "Cisco UCS equipment:LocalDiskControllerDef:zoningSupported
        managed object property"
    ::= { cucsEquipmentLocalDiskControllerDefEntry 18 }

cucsEquipmentLocalDiskControllerDefControllerSubType OBJECT-TYPE
    SYNTAX       CucsEquipmentControllerSubType
    MAX-ACCESS   read-only
    STATUS       current
    DESCRIPTION
        "Cisco UCS equipment:LocalDiskControllerDef:controllerSubType
        managed object property"
    ::= { cucsEquipmentLocalDiskControllerDefEntry 19 }

cucsEquipmentLocalDiskControllerDefHotPlugSupported OBJECT-TYPE
    SYNTAX       TruthValue
    MAX-ACCESS   read-only
    STATUS       current
    DESCRIPTION
        "Cisco UCS equipment:LocalDiskControllerDef:hotPlugSupported
        managed object property"
    ::= { cucsEquipmentLocalDiskControllerDefEntry 20 }

cucsEquipmentLocalDiskControllerTypeDefTable OBJECT-TYPE
    SYNTAX           SEQUENCE OF CucsEquipmentLocalDiskControllerTypeDefEntry
    MAX-ACCESS       not-accessible
    STATUS           current
    DESCRIPTION
        "Cisco UCS equipment:LocalDiskControllerTypeDef
        managed object table"
    ::= { cucsEquipmentObjects 155 }

cucsEquipmentLocalDiskControllerTypeDefEntry OBJECT-TYPE
    SYNTAX           CucsEquipmentLocalDiskControllerTypeDefEntry
    MAX-ACCESS       not-accessible
    STATUS           current
    DESCRIPTION
        "Entry for the cucsEquipmentLocalDiskControllerTypeDefTable table."
    INDEX { cucsEquipmentLocalDiskControllerTypeDefInstanceId }
    ::= { cucsEquipmentLocalDiskControllerTypeDefTable 1 }

CucsEquipmentLocalDiskControllerTypeDefEntry ::= SEQUENCE {
    cucsEquipmentLocalDiskControllerTypeDefInstanceId                CucsManagedObjectId,
    cucsEquipmentLocalDiskControllerTypeDefDn                        CucsManagedObjectDn,
    cucsEquipmentLocalDiskControllerTypeDefRn                        SnmpAdminString,
    cucsEquipmentLocalDiskControllerTypeDefIsFlashLifeLeftSupported  TruthValue
}

cucsEquipmentLocalDiskControllerTypeDefInstanceId OBJECT-TYPE
    SYNTAX       CucsManagedObjectId
    MAX-ACCESS   not-accessible
    STATUS       current
    DESCRIPTION
        "Instance identifier of the managed object."
    ::= { cucsEquipmentLocalDiskControllerTypeDefEntry 1 }

cucsEquipmentLocalDiskControllerTypeDefDn OBJECT-TYPE
    SYNTAX       CucsManagedObjectDn
    MAX-ACCESS   read-only
    STATUS       current
    DESCRIPTION
        "Cisco UCS equipment:LocalDiskControllerTypeDef:dn
        managed object property"
    ::= { cucsEquipmentLocalDiskControllerTypeDefEntry 2 }

cucsEquipmentLocalDiskControllerTypeDefRn OBJECT-TYPE
    SYNTAX       SnmpAdminString
    MAX-ACCESS   read-only
    STATUS       current
    DESCRIPTION
        "Cisco UCS equipment:LocalDiskControllerTypeDef:rn
        managed object property"
    ::= { cucsEquipmentLocalDiskControllerTypeDefEntry 3 }

cucsEquipmentLocalDiskControllerTypeDefIsFlashLifeLeftSupported OBJECT-TYPE
    SYNTAX       TruthValue
    MAX-ACCESS   read-only
    STATUS       current
    DESCRIPTION
        "Cisco UCS equipment:LocalDiskControllerTypeDef:isFlashLifeLeftSup
        ported managed object property"
    ::= { cucsEquipmentLocalDiskControllerTypeDefEntry 4 }

cucsEquipmentLocalDiskDefTable OBJECT-TYPE
    SYNTAX           SEQUENCE OF CucsEquipmentLocalDiskDefEntry
    MAX-ACCESS       not-accessible
    STATUS           current
    DESCRIPTION
        "Cisco UCS equipment:LocalDiskDef managed object table"
    ::= { cucsEquipmentObjects 39 }

cucsEquipmentLocalDiskDefEntry OBJECT-TYPE
    SYNTAX           CucsEquipmentLocalDiskDefEntry
    MAX-ACCESS       not-accessible
    STATUS           current
    DESCRIPTION
        "Entry for the cucsEquipmentLocalDiskDefTable table."
    INDEX { cucsEquipmentLocalDiskDefInstanceId }
    ::= { cucsEquipmentLocalDiskDefTable 1 }

CucsEquipmentLocalDiskDefEntry ::= SEQUENCE {
    cucsEquipmentLocalDiskDefInstanceId                              CucsManagedObjectId,
    cucsEquipmentLocalDiskDefDn                                      CucsManagedObjectDn,
    cucsEquipmentLocalDiskDefRn                                      SnmpAdminString,
    cucsEquipmentLocalDiskDefBlockSize                               Gauge32,
    cucsEquipmentLocalDiskDefDescr                                   SnmpAdminString,
    cucsEquipmentLocalDiskDefIntId                                   SnmpAdminString,
    cucsEquipmentLocalDiskDefName                                    SnmpAdminString,
    cucsEquipmentLocalDiskDefNumberOfBlocks                          Unsigned64,
    cucsEquipmentLocalDiskDefRotationalSpeed                         INTEGER,
    cucsEquipmentLocalDiskDefCacheSize                               SnmpAdminString,
    cucsEquipmentLocalDiskDefSeekAverageReadWrite                    SnmpAdminString,
    cucsEquipmentLocalDiskDefSeekTrackToTrackReadWrite               SnmpAdminString,
    cucsEquipmentLocalDiskDefTechnology                              CucsStorageTechnology,
    cucsEquipmentLocalDiskDefPolicyLevel                             Gauge32,
    cucsEquipmentLocalDiskDefPolicyOwner                             CucsPolicyPolicyOwner,
    cucsEquipmentLocalDiskDefForceUpdateVersion                      TruthValue,
    cucsEquipmentLocalDiskDefCapacity                                SnmpAdminString,
    cucsEquipmentLocalDiskDefLinkSpeed                               SnmpAdminString,
    cucsEquipmentLocalDiskDefMe4308Supported                         TruthValue,
    cucsEquipmentLocalDiskDefSelfEncryptingDrive                     TruthValue
}

cucsEquipmentLocalDiskDefInstanceId OBJECT-TYPE
    SYNTAX       CucsManagedObjectId
    MAX-ACCESS   not-accessible
    STATUS       current
    DESCRIPTION
        "Instance identifier of the managed object."
    ::= { cucsEquipmentLocalDiskDefEntry 1 }

cucsEquipmentLocalDiskDefDn OBJECT-TYPE
    SYNTAX       CucsManagedObjectDn
    MAX-ACCESS   read-only
    STATUS       current
    DESCRIPTION
        "Cisco UCS equipment:LocalDiskDef:dn managed object property"
    ::= { cucsEquipmentLocalDiskDefEntry 2 }

cucsEquipmentLocalDiskDefRn OBJECT-TYPE
    SYNTAX       SnmpAdminString
    MAX-ACCESS   read-only
    STATUS       current
    DESCRIPTION
        "Cisco UCS equipment:LocalDiskDef:rn managed object property"
    ::= { cucsEquipmentLocalDiskDefEntry 3 }

cucsEquipmentLocalDiskDefBlockSize OBJECT-TYPE
    SYNTAX       Gauge32
    MAX-ACCESS   read-only
    STATUS       current
    DESCRIPTION
        "Cisco UCS equipment:LocalDiskDef:blockSize managed
        object property"
    ::= { cucsEquipmentLocalDiskDefEntry 4 }

cucsEquipmentLocalDiskDefDescr OBJECT-TYPE
    SYNTAX       SnmpAdminString
    MAX-ACCESS   read-only
    STATUS       current
    DESCRIPTION
        "Cisco UCS equipment:LocalDiskDef:descr managed object property"
    ::= { cucsEquipmentLocalDiskDefEntry 5 }

cucsEquipmentLocalDiskDefIntId OBJECT-TYPE
    SYNTAX       SnmpAdminString
    MAX-ACCESS   read-only
    STATUS       current
    DESCRIPTION
        "Cisco UCS equipment:LocalDiskDef:intId managed object property"
    ::= { cucsEquipmentLocalDiskDefEntry 6 }

cucsEquipmentLocalDiskDefName OBJECT-TYPE
    SYNTAX       SnmpAdminString
    MAX-ACCESS   read-only
    STATUS       current
    DESCRIPTION
        "Cisco UCS equipment:LocalDiskDef:name managed object property"
    ::= { cucsEquipmentLocalDiskDefEntry 7 }

cucsEquipmentLocalDiskDefNumberOfBlocks OBJECT-TYPE
    SYNTAX       Unsigned64
    MAX-ACCESS   read-only
    STATUS       current
    DESCRIPTION
        "Cisco UCS equipment:LocalDiskDef:numberOfBlocks
        managed object property"
    ::= { cucsEquipmentLocalDiskDefEntry 8 }

cucsEquipmentLocalDiskDefRotationalSpeed OBJECT-TYPE
    SYNTAX       INTEGER
    MAX-ACCESS   read-only
    STATUS       current
    DESCRIPTION
        "Cisco UCS equipment:LocalDiskDef:rotationalSpeed
        managed object property"
    ::= { cucsEquipmentLocalDiskDefEntry 9 }

cucsEquipmentLocalDiskDefCacheSize OBJECT-TYPE
    SYNTAX       SnmpAdminString
    MAX-ACCESS   read-only
    STATUS       current
    DESCRIPTION
        "Cisco UCS equipment:LocalDiskDef:cacheSize managed
        object property"
    ::= { cucsEquipmentLocalDiskDefEntry 10 }

cucsEquipmentLocalDiskDefSeekAverageReadWrite OBJECT-TYPE
    SYNTAX       SnmpAdminString
    MAX-ACCESS   read-only
    STATUS       current
    DESCRIPTION
        "Cisco UCS equipment:LocalDiskDef:seekAverageReadWrite
        managed object property"
    ::= { cucsEquipmentLocalDiskDefEntry 11 }

cucsEquipmentLocalDiskDefSeekTrackToTrackReadWrite OBJECT-TYPE
    SYNTAX       SnmpAdminString
    MAX-ACCESS   read-only
    STATUS       current
    DESCRIPTION
        "Cisco UCS equipment:LocalDiskDef:seekTrackToTrackReadWrite
        managed object property"
    ::= { cucsEquipmentLocalDiskDefEntry 12 }

cucsEquipmentLocalDiskDefTechnology OBJECT-TYPE
    SYNTAX       CucsStorageTechnology
    MAX-ACCESS   read-only
    STATUS       current
    DESCRIPTION
        "Cisco UCS equipment:LocalDiskDef:technology managed
        object property"
    ::= { cucsEquipmentLocalDiskDefEntry 13 }

cucsEquipmentLocalDiskDefPolicyLevel OBJECT-TYPE
    SYNTAX       Gauge32
    MAX-ACCESS   read-only
    STATUS       current
    DESCRIPTION
        "Cisco UCS equipment:LocalDiskDef:policyLevel managed
        object property"
    ::= { cucsEquipmentLocalDiskDefEntry 14 }

cucsEquipmentLocalDiskDefPolicyOwner OBJECT-TYPE
    SYNTAX       CucsPolicyPolicyOwner
    MAX-ACCESS   read-only
    STATUS       current
    DESCRIPTION
        "Cisco UCS equipment:LocalDiskDef:policyOwner managed
        object property"
    ::= { cucsEquipmentLocalDiskDefEntry 15 }

cucsEquipmentLocalDiskDefForceUpdateVersion OBJECT-TYPE
    SYNTAX       TruthValue
    MAX-ACCESS   read-only
    STATUS       current
    DESCRIPTION
        "Cisco UCS equipment:LocalDiskDef:forceUpdateVersion
        managed object property"
    ::= { cucsEquipmentLocalDiskDefEntry 16 }

cucsEquipmentLocalDiskDefCapacity OBJECT-TYPE
    SYNTAX       SnmpAdminString
    MAX-ACCESS   read-only
    STATUS       current
    DESCRIPTION
        "Cisco UCS equipment:LocalDiskDef:capacity managed
        object property"
    ::= { cucsEquipmentLocalDiskDefEntry 17 }

cucsEquipmentLocalDiskDefLinkSpeed OBJECT-TYPE
    SYNTAX       SnmpAdminString
    MAX-ACCESS   read-only
    STATUS       current
    DESCRIPTION
        "Cisco UCS equipment:LocalDiskDef:linkSpeed managed
        object property"
    ::= { cucsEquipmentLocalDiskDefEntry 18 }

cucsEquipmentLocalDiskDefMe4308Supported OBJECT-TYPE
    SYNTAX       TruthValue
    MAX-ACCESS   read-only
    STATUS       current
    DESCRIPTION
        "Cisco UCS equipment:LocalDiskDef:me4308Supported
        managed object property"
    ::= { cucsEquipmentLocalDiskDefEntry 19 }

cucsEquipmentLocalDiskDefSelfEncryptingDrive OBJECT-TYPE
    SYNTAX       TruthValue
    MAX-ACCESS   read-only
    STATUS       current
    DESCRIPTION
        "Cisco UCS equipment:LocalDiskDef:selfEncryptingDrive
        managed object property"
    ::= { cucsEquipmentLocalDiskDefEntry 20 }

cucsEquipmentLocatorLedTable OBJECT-TYPE
    SYNTAX           SEQUENCE OF CucsEquipmentLocatorLedEntry
    MAX-ACCESS       not-accessible
    STATUS           current
    DESCRIPTION
        "Cisco UCS equipment:LocatorLed managed object table"
    ::= { cucsEquipmentObjects 40 }

cucsEquipmentLocatorLedEntry OBJECT-TYPE
    SYNTAX           CucsEquipmentLocatorLedEntry
    MAX-ACCESS       not-accessible
    STATUS           current
    DESCRIPTION
        "Entry for the cucsEquipmentLocatorLedTable table."
    INDEX { cucsEquipmentLocatorLedInstanceId }
    ::= { cucsEquipmentLocatorLedTable 1 }

CucsEquipmentLocatorLedEntry ::= SEQUENCE {
    cucsEquipmentLocatorLedInstanceId                                CucsManagedObjectId,
    cucsEquipmentLocatorLedDn                                        CucsManagedObjectDn,
    cucsEquipmentLocatorLedRn                                        SnmpAdminString,
    cucsEquipmentLocatorLedAdminState                                CucsEquipmentLedLocatorState,
    cucsEquipmentLocatorLedColor                                     CucsEquipmentLedColor,
    cucsEquipmentLocatorLedFsmDescr                                  SnmpAdminString,
    cucsEquipmentLocatorLedFsmPrev                                   SnmpAdminString,
    cucsEquipmentLocatorLedFsmProgr                                  Gauge32,
    cucsEquipmentLocatorLedFsmRmtInvErrCode                          Gauge32,
    cucsEquipmentLocatorLedFsmRmtInvErrDescr                         SnmpAdminString,
    cucsEquipmentLocatorLedFsmRmtInvRslt                             CucsConditionRemoteInvRslt,
    cucsEquipmentLocatorLedFsmStageDescr                             SnmpAdminString,
    cucsEquipmentLocatorLedFsmStamp                                  DateAndTime,
    cucsEquipmentLocatorLedFsmStatus                                 SnmpAdminString,
    cucsEquipmentLocatorLedFsmTry                                    Gauge32,
    cucsEquipmentLocatorLedId                                        Gauge32,
    cucsEquipmentLocatorLedName                                      SnmpAdminString,
    cucsEquipmentLocatorLedOperState                                 CucsEquipmentLedOperState,
    cucsEquipmentLocatorLedBoardType                                 CucsEquipmentBoardAggregationRole
}

cucsEquipmentLocatorLedInstanceId OBJECT-TYPE
    SYNTAX       CucsManagedObjectId
    MAX-ACCESS   not-accessible
    STATUS       current
    DESCRIPTION
        "Instance identifier of the managed object."
    ::= { cucsEquipmentLocatorLedEntry 1 }

cucsEquipmentLocatorLedDn OBJECT-TYPE
    SYNTAX       CucsManagedObjectDn
    MAX-ACCESS   read-only
    STATUS       current
    DESCRIPTION
        "Cisco UCS equipment:LocatorLed:dn managed object property"
    ::= { cucsEquipmentLocatorLedEntry 2 }

cucsEquipmentLocatorLedRn OBJECT-TYPE
    SYNTAX       SnmpAdminString
    MAX-ACCESS   read-only
    STATUS       current
    DESCRIPTION
        "Cisco UCS equipment:LocatorLed:rn managed object property"
    ::= { cucsEquipmentLocatorLedEntry 3 }

cucsEquipmentLocatorLedAdminState OBJECT-TYPE
    SYNTAX       CucsEquipmentLedLocatorState
    MAX-ACCESS   read-only
    STATUS       current
    DESCRIPTION
        "Cisco UCS equipment:LocatorLed:adminState managed
        object property"
    ::= { cucsEquipmentLocatorLedEntry 4 }

cucsEquipmentLocatorLedColor OBJECT-TYPE
    SYNTAX       CucsEquipmentLedColor
    MAX-ACCESS   read-only
    STATUS       current
    DESCRIPTION
        "Cisco UCS equipment:LocatorLed:color managed object property"
    ::= { cucsEquipmentLocatorLedEntry 5 }

cucsEquipmentLocatorLedFsmDescr OBJECT-TYPE
    SYNTAX       SnmpAdminString
    MAX-ACCESS   read-only
    STATUS       current
    DESCRIPTION
        "Cisco UCS equipment:LocatorLed:fsmDescr managed object property"
    ::= { cucsEquipmentLocatorLedEntry 6 }

cucsEquipmentLocatorLedFsmPrev OBJECT-TYPE
    SYNTAX       SnmpAdminString
    MAX-ACCESS   read-only
    STATUS       current
    DESCRIPTION
        "Cisco UCS equipment:LocatorLed:fsmPrev managed object property"
    ::= { cucsEquipmentLocatorLedEntry 7 }

cucsEquipmentLocatorLedFsmProgr OBJECT-TYPE
    SYNTAX       Gauge32
    MAX-ACCESS   read-only
    STATUS       current
    DESCRIPTION
        "Cisco UCS equipment:LocatorLed:fsmProgr managed object property"
    ::= { cucsEquipmentLocatorLedEntry 8 }

cucsEquipmentLocatorLedFsmRmtInvErrCode OBJECT-TYPE
    SYNTAX       Gauge32
    MAX-ACCESS   read-only
    STATUS       current
    DESCRIPTION
        "Cisco UCS equipment:LocatorLed:fsmRmtInvErrCode
        managed object property"
    ::= { cucsEquipmentLocatorLedEntry 9 }

cucsEquipmentLocatorLedFsmRmtInvErrDescr OBJECT-TYPE
    SYNTAX       SnmpAdminString
    MAX-ACCESS   read-only
    STATUS       current
    DESCRIPTION
        "Cisco UCS equipment:LocatorLed:fsmRmtInvErrDescr
        managed object property"
    ::= { cucsEquipmentLocatorLedEntry 10 }

cucsEquipmentLocatorLedFsmRmtInvRslt OBJECT-TYPE
    SYNTAX       CucsConditionRemoteInvRslt
    MAX-ACCESS   read-only
    STATUS       current
    DESCRIPTION
        "Cisco UCS equipment:LocatorLed:fsmRmtInvRslt managed
        object property"
    ::= { cucsEquipmentLocatorLedEntry 11 }

cucsEquipmentLocatorLedFsmStageDescr OBJECT-TYPE
    SYNTAX       SnmpAdminString
    MAX-ACCESS   read-only
    STATUS       current
    DESCRIPTION
        "Cisco UCS equipment:LocatorLed:fsmStageDescr managed
        object property"
    ::= { cucsEquipmentLocatorLedEntry 12 }

cucsEquipmentLocatorLedFsmStamp OBJECT-TYPE
    SYNTAX       DateAndTime
    MAX-ACCESS   read-only
    STATUS       current
    DESCRIPTION
        "Cisco UCS equipment:LocatorLed:fsmStamp managed object property"
    ::= { cucsEquipmentLocatorLedEntry 13 }

cucsEquipmentLocatorLedFsmStatus OBJECT-TYPE
    SYNTAX       SnmpAdminString
    MAX-ACCESS   read-only
    STATUS       current
    DESCRIPTION
        "Cisco UCS equipment:LocatorLed:fsmStatus managed object property"
    ::= { cucsEquipmentLocatorLedEntry 14 }

cucsEquipmentLocatorLedFsmTry OBJECT-TYPE
    SYNTAX       Gauge32
    MAX-ACCESS   read-only
    STATUS       current
    DESCRIPTION
        "Cisco UCS equipment:LocatorLed:fsmTry managed object property"
    ::= { cucsEquipmentLocatorLedEntry 15 }

cucsEquipmentLocatorLedId OBJECT-TYPE
    SYNTAX       Gauge32
    MAX-ACCESS   read-only
    STATUS       current
    DESCRIPTION
        "Cisco UCS equipment:LocatorLed:id managed object property"
    ::= { cucsEquipmentLocatorLedEntry 16 }

cucsEquipmentLocatorLedName OBJECT-TYPE
    SYNTAX       SnmpAdminString
    MAX-ACCESS   read-only
    STATUS       current
    DESCRIPTION
        "Cisco UCS equipment:LocatorLed:name managed object property"
    ::= { cucsEquipmentLocatorLedEntry 17 }

cucsEquipmentLocatorLedOperState OBJECT-TYPE
    SYNTAX       CucsEquipmentLedOperState
    MAX-ACCESS   read-only
    STATUS       current
    DESCRIPTION
        "Cisco UCS equipment:LocatorLed:operState managed object property"
    ::= { cucsEquipmentLocatorLedEntry 18 }

cucsEquipmentLocatorLedBoardType OBJECT-TYPE
    SYNTAX       CucsEquipmentBoardAggregationRole
    MAX-ACCESS   read-only
    STATUS       current
    DESCRIPTION
        "Cisco UCS equipment:LocatorLed:boardType managed object property"
    ::= { cucsEquipmentLocatorLedEntry 19 }

cucsEquipmentLocatorLedFsmTable OBJECT-TYPE
    SYNTAX           SEQUENCE OF CucsEquipmentLocatorLedFsmEntry
    MAX-ACCESS       not-accessible
    STATUS           current
    DESCRIPTION
        "Cisco UCS equipment:LocatorLedFsm managed object table"
    ::= { cucsEquipmentObjects 111 }

cucsEquipmentLocatorLedFsmEntry OBJECT-TYPE
    SYNTAX           CucsEquipmentLocatorLedFsmEntry
    MAX-ACCESS       not-accessible
    STATUS           current
    DESCRIPTION
        "Entry for the cucsEquipmentLocatorLedFsmTable table."
    INDEX { cucsEquipmentLocatorLedFsmInstanceId }
    ::= { cucsEquipmentLocatorLedFsmTable 1 }

CucsEquipmentLocatorLedFsmEntry ::= SEQUENCE {
    cucsEquipmentLocatorLedFsmInstanceId                             CucsManagedObjectId,
    cucsEquipmentLocatorLedFsmDn                                     CucsManagedObjectDn,
    cucsEquipmentLocatorLedFsmRn                                     SnmpAdminString,
    cucsEquipmentLocatorLedFsmCompletionTime                         DateAndTime,
    cucsEquipmentLocatorLedFsmCurrentFsm                             CucsEquipmentLocatorLedFsmCurrentFsm,
    cucsEquipmentLocatorLedFsmDescrData                              SnmpAdminString,
    cucsEquipmentLocatorLedFsmFsmStatus                              CucsFsmFsmStageStatus,
    cucsEquipmentLocatorLedFsmProgress                               Gauge32,
    cucsEquipmentLocatorLedFsmRmtErrCode                             Gauge32,
    cucsEquipmentLocatorLedFsmRmtErrDescr                            SnmpAdminString,
    cucsEquipmentLocatorLedFsmRmtRslt                                CucsConditionRemoteInvRslt
}

cucsEquipmentLocatorLedFsmInstanceId OBJECT-TYPE
    SYNTAX       CucsManagedObjectId
    MAX-ACCESS   not-accessible
    STATUS       current
    DESCRIPTION
        "Instance identifier of the managed object."
    ::= { cucsEquipmentLocatorLedFsmEntry 1 }

cucsEquipmentLocatorLedFsmDn OBJECT-TYPE
    SYNTAX       CucsManagedObjectDn
    MAX-ACCESS   read-only
    STATUS       current
    DESCRIPTION
        "Cisco UCS equipment:LocatorLedFsm:dn managed object property"
    ::= { cucsEquipmentLocatorLedFsmEntry 2 }

cucsEquipmentLocatorLedFsmRn OBJECT-TYPE
    SYNTAX       SnmpAdminString
    MAX-ACCESS   read-only
    STATUS       current
    DESCRIPTION
        "Cisco UCS equipment:LocatorLedFsm:rn managed object property"
    ::= { cucsEquipmentLocatorLedFsmEntry 3 }

cucsEquipmentLocatorLedFsmCompletionTime OBJECT-TYPE
    SYNTAX       DateAndTime
    MAX-ACCESS   read-only
    STATUS       current
    DESCRIPTION
        "Cisco UCS equipment:LocatorLedFsm:completionTime
        managed object property"
    ::= { cucsEquipmentLocatorLedFsmEntry 4 }

cucsEquipmentLocatorLedFsmCurrentFsm OBJECT-TYPE
    SYNTAX       CucsEquipmentLocatorLedFsmCurrentFsm
    MAX-ACCESS   read-only
    STATUS       current
    DESCRIPTION
        "Cisco UCS equipment:LocatorLedFsm:currentFsm managed
        object property"
    ::= { cucsEquipmentLocatorLedFsmEntry 5 }

cucsEquipmentLocatorLedFsmDescrData OBJECT-TYPE
    SYNTAX       SnmpAdminString
    MAX-ACCESS   read-only
    STATUS       current
    DESCRIPTION
        "Cisco UCS equipment:LocatorLedFsm:descr managed object property"
    ::= { cucsEquipmentLocatorLedFsmEntry 6 }

cucsEquipmentLocatorLedFsmFsmStatus OBJECT-TYPE
    SYNTAX       CucsFsmFsmStageStatus
    MAX-ACCESS   read-only
    STATUS       current
    DESCRIPTION
        "Cisco UCS equipment:LocatorLedFsm:fsmStatus managed
        object property"
    ::= { cucsEquipmentLocatorLedFsmEntry 7 }

cucsEquipmentLocatorLedFsmProgress OBJECT-TYPE
    SYNTAX       Gauge32
    MAX-ACCESS   read-only
    STATUS       current
    DESCRIPTION
        "Cisco UCS equipment:LocatorLedFsm:progress managed
        object property"
    ::= { cucsEquipmentLocatorLedFsmEntry 8 }

cucsEquipmentLocatorLedFsmRmtErrCode OBJECT-TYPE
    SYNTAX       Gauge32
    MAX-ACCESS   read-only
    STATUS       current
    DESCRIPTION
        "Cisco UCS equipment:LocatorLedFsm:rmtErrCode managed
        object property"
    ::= { cucsEquipmentLocatorLedFsmEntry 9 }

cucsEquipmentLocatorLedFsmRmtErrDescr OBJECT-TYPE
    SYNTAX       SnmpAdminString
    MAX-ACCESS   read-only
    STATUS       current
    DESCRIPTION
        "Cisco UCS equipment:LocatorLedFsm:rmtErrDescr
        managed object property"
    ::= { cucsEquipmentLocatorLedFsmEntry 10 }

cucsEquipmentLocatorLedFsmRmtRslt OBJECT-TYPE
    SYNTAX       CucsConditionRemoteInvRslt
    MAX-ACCESS   read-only
    STATUS       current
    DESCRIPTION
        "Cisco UCS equipment:LocatorLedFsm:rmtRslt managed
        object property"
    ::= { cucsEquipmentLocatorLedFsmEntry 11 }

cucsEquipmentLocatorLedFsmStageTable OBJECT-TYPE
    SYNTAX           SEQUENCE OF CucsEquipmentLocatorLedFsmStageEntry
    MAX-ACCESS       not-accessible
    STATUS           current
    DESCRIPTION
        "Cisco UCS equipment:LocatorLedFsmStage managed object table"
    ::= { cucsEquipmentObjects 112 }

cucsEquipmentLocatorLedFsmStageEntry OBJECT-TYPE
    SYNTAX           CucsEquipmentLocatorLedFsmStageEntry
    MAX-ACCESS       not-accessible
    STATUS           current
    DESCRIPTION
        "Entry for the cucsEquipmentLocatorLedFsmStageTable table."
    INDEX { cucsEquipmentLocatorLedFsmStageInstanceId }
    ::= { cucsEquipmentLocatorLedFsmStageTable 1 }

CucsEquipmentLocatorLedFsmStageEntry ::= SEQUENCE {
    cucsEquipmentLocatorLedFsmStageInstanceId                        CucsManagedObjectId,
    cucsEquipmentLocatorLedFsmStageDn                                CucsManagedObjectDn,
    cucsEquipmentLocatorLedFsmStageRn                                SnmpAdminString,
    cucsEquipmentLocatorLedFsmStageDescrData                         SnmpAdminString,
    cucsEquipmentLocatorLedFsmStageLastUpdateTime                    DateAndTime,
    cucsEquipmentLocatorLedFsmStageName                              CucsEquipmentLocatorLedFsmStageName,
    cucsEquipmentLocatorLedFsmStageOrder                             Gauge32,
    cucsEquipmentLocatorLedFsmStageRetry                             Gauge32,
    cucsEquipmentLocatorLedFsmStageStageStatus                       CucsFsmFsmStageStatus
}

cucsEquipmentLocatorLedFsmStageInstanceId OBJECT-TYPE
    SYNTAX       CucsManagedObjectId
    MAX-ACCESS   not-accessible
    STATUS       current
    DESCRIPTION
        "Instance identifier of the managed object."
    ::= { cucsEquipmentLocatorLedFsmStageEntry 1 }

cucsEquipmentLocatorLedFsmStageDn OBJECT-TYPE
    SYNTAX       CucsManagedObjectDn
    MAX-ACCESS   read-only
    STATUS       current
    DESCRIPTION
        "Cisco UCS equipment:LocatorLedFsmStage:dn managed
        object property"
    ::= { cucsEquipmentLocatorLedFsmStageEntry 2 }

cucsEquipmentLocatorLedFsmStageRn OBJECT-TYPE
    SYNTAX       SnmpAdminString
    MAX-ACCESS   read-only
    STATUS       current
    DESCRIPTION
        "Cisco UCS equipment:LocatorLedFsmStage:rn managed
        object property"
    ::= { cucsEquipmentLocatorLedFsmStageEntry 3 }

cucsEquipmentLocatorLedFsmStageDescrData OBJECT-TYPE
    SYNTAX       SnmpAdminString
    MAX-ACCESS   read-only
    STATUS       current
    DESCRIPTION
        "Cisco UCS equipment:LocatorLedFsmStage:descr managed
        object property"
    ::= { cucsEquipmentLocatorLedFsmStageEntry 4 }

cucsEquipmentLocatorLedFsmStageLastUpdateTime OBJECT-TYPE
    SYNTAX       DateAndTime
    MAX-ACCESS   read-only
    STATUS       current
    DESCRIPTION
        "Cisco UCS equipment:LocatorLedFsmStage:lastUpdateTime
        managed object property"
    ::= { cucsEquipmentLocatorLedFsmStageEntry 5 }

cucsEquipmentLocatorLedFsmStageName OBJECT-TYPE
    SYNTAX       CucsEquipmentLocatorLedFsmStageName
    MAX-ACCESS   read-only
    STATUS       current
    DESCRIPTION
        "Cisco UCS equipment:LocatorLedFsmStage:name managed
        object property"
    ::= { cucsEquipmentLocatorLedFsmStageEntry 6 }

cucsEquipmentLocatorLedFsmStageOrder OBJECT-TYPE
    SYNTAX       Gauge32
    MAX-ACCESS   read-only
    STATUS       current
    DESCRIPTION
        "Cisco UCS equipment:LocatorLedFsmStage:order managed
        object property"
    ::= { cucsEquipmentLocatorLedFsmStageEntry 7 }

cucsEquipmentLocatorLedFsmStageRetry OBJECT-TYPE
    SYNTAX       Gauge32
    MAX-ACCESS   read-only
    STATUS       current
    DESCRIPTION
        "Cisco UCS equipment:LocatorLedFsmStage:retry managed
        object property"
    ::= { cucsEquipmentLocatorLedFsmStageEntry 8 }

cucsEquipmentLocatorLedFsmStageStageStatus OBJECT-TYPE
    SYNTAX       CucsFsmFsmStageStatus
    MAX-ACCESS   read-only
    STATUS       current
    DESCRIPTION
        "Cisco UCS equipment:LocatorLedFsmStage:stageStatus
        managed object property"
    ::= { cucsEquipmentLocatorLedFsmStageEntry 9 }

cucsEquipmentLocatorLedFsmTaskTable OBJECT-TYPE
    SYNTAX           SEQUENCE OF CucsEquipmentLocatorLedFsmTaskEntry
    MAX-ACCESS       not-accessible
    STATUS           current
    DESCRIPTION
        "Cisco UCS equipment:LocatorLedFsmTask managed object table"
    ::= { cucsEquipmentObjects 41 }

cucsEquipmentLocatorLedFsmTaskEntry OBJECT-TYPE
    SYNTAX           CucsEquipmentLocatorLedFsmTaskEntry
    MAX-ACCESS       not-accessible
    STATUS           current
    DESCRIPTION
        "Entry for the cucsEquipmentLocatorLedFsmTaskTable table."
    INDEX { cucsEquipmentLocatorLedFsmTaskInstanceId }
    ::= { cucsEquipmentLocatorLedFsmTaskTable 1 }

CucsEquipmentLocatorLedFsmTaskEntry ::= SEQUENCE {
    cucsEquipmentLocatorLedFsmTaskInstanceId                         CucsManagedObjectId,
    cucsEquipmentLocatorLedFsmTaskDn                                 CucsManagedObjectDn,
    cucsEquipmentLocatorLedFsmTaskRn                                 SnmpAdminString,
    cucsEquipmentLocatorLedFsmTaskCompletion                         CucsFsmCompletion,
    cucsEquipmentLocatorLedFsmTaskFlags                              CucsFsmFlags,
    cucsEquipmentLocatorLedFsmTaskItem                               CucsEquipmentLocatorLedFsmTaskItem,
    cucsEquipmentLocatorLedFsmTaskSeqId                              Gauge32
}

cucsEquipmentLocatorLedFsmTaskInstanceId OBJECT-TYPE
    SYNTAX       CucsManagedObjectId
    MAX-ACCESS   not-accessible
    STATUS       current
    DESCRIPTION
        "Instance identifier of the managed object."
    ::= { cucsEquipmentLocatorLedFsmTaskEntry 1 }

cucsEquipmentLocatorLedFsmTaskDn OBJECT-TYPE
    SYNTAX       CucsManagedObjectDn
    MAX-ACCESS   read-only
    STATUS       current
    DESCRIPTION
        "Cisco UCS equipment:LocatorLedFsmTask:dn managed object property"
    ::= { cucsEquipmentLocatorLedFsmTaskEntry 2 }

cucsEquipmentLocatorLedFsmTaskRn OBJECT-TYPE
    SYNTAX       SnmpAdminString
    MAX-ACCESS   read-only
    STATUS       current
    DESCRIPTION
        "Cisco UCS equipment:LocatorLedFsmTask:rn managed object property"
    ::= { cucsEquipmentLocatorLedFsmTaskEntry 3 }

cucsEquipmentLocatorLedFsmTaskCompletion OBJECT-TYPE
    SYNTAX       CucsFsmCompletion
    MAX-ACCESS   read-only
    STATUS       current
    DESCRIPTION
        "Cisco UCS equipment:LocatorLedFsmTask:completion
        managed object property"
    ::= { cucsEquipmentLocatorLedFsmTaskEntry 4 }

cucsEquipmentLocatorLedFsmTaskFlags OBJECT-TYPE
    SYNTAX       CucsFsmFlags
    MAX-ACCESS   read-only
    STATUS       current
    DESCRIPTION
        "Cisco UCS equipment:LocatorLedFsmTask:flags managed
        object property"
    ::= { cucsEquipmentLocatorLedFsmTaskEntry 5 }

cucsEquipmentLocatorLedFsmTaskItem OBJECT-TYPE
    SYNTAX       CucsEquipmentLocatorLedFsmTaskItem
    MAX-ACCESS   read-only
    STATUS       current
    DESCRIPTION
        "Cisco UCS equipment:LocatorLedFsmTask:item managed
        object property"
    ::= { cucsEquipmentLocatorLedFsmTaskEntry 6 }

cucsEquipmentLocatorLedFsmTaskSeqId OBJECT-TYPE
    SYNTAX       Gauge32
    MAX-ACCESS   read-only
    STATUS       current
    DESCRIPTION
        "Cisco UCS equipment:LocatorLedFsmTask:seqId managed
        object property"
    ::= { cucsEquipmentLocatorLedFsmTaskEntry 7 }

cucsEquipmentManufacturingDefTable OBJECT-TYPE
    SYNTAX           SEQUENCE OF CucsEquipmentManufacturingDefEntry
    MAX-ACCESS       not-accessible
    STATUS           current
    DESCRIPTION
        "Cisco UCS equipment:ManufacturingDef managed object table"
    ::= { cucsEquipmentObjects 42 }

cucsEquipmentManufacturingDefEntry OBJECT-TYPE
    SYNTAX           CucsEquipmentManufacturingDefEntry
    MAX-ACCESS       not-accessible
    STATUS           current
    DESCRIPTION
        "Entry for the cucsEquipmentManufacturingDefTable table."
    INDEX { cucsEquipmentManufacturingDefInstanceId }
    ::= { cucsEquipmentManufacturingDefTable 1 }

CucsEquipmentManufacturingDefEntry ::= SEQUENCE {
    cucsEquipmentManufacturingDefInstanceId                          CucsManagedObjectId,
    cucsEquipmentManufacturingDefDn                                  CucsManagedObjectDn,
    cucsEquipmentManufacturingDefRn                                  SnmpAdminString,
    cucsEquipmentManufacturingDefCaption                             SnmpAdminString,
    cucsEquipmentManufacturingDefClei                                SnmpAdminString,
    cucsEquipmentManufacturingDefDescr                               SnmpAdminString,
    cucsEquipmentManufacturingDefDescription                         SnmpAdminString,
    cucsEquipmentManufacturingDefFruMajorType                        SnmpAdminString,
    cucsEquipmentManufacturingDefFruMinorType                        SnmpAdminString,
    cucsEquipmentManufacturingDefIntId                               SnmpAdminString,
    cucsEquipmentManufacturingDefName                                SnmpAdminString,
    cucsEquipmentManufacturingDefOemName                             SnmpAdminString,
    cucsEquipmentManufacturingDefOemPartNumber                       SnmpAdminString,
    cucsEquipmentManufacturingDefPartNumber                          SnmpAdminString,
    cucsEquipmentManufacturingDefPid                                 SnmpAdminString,
    cucsEquipmentManufacturingDefSeries                              SnmpAdminString,
    cucsEquipmentManufacturingDefSku                                 SnmpAdminString,
    cucsEquipmentManufacturingDefVendorEquipmentType                 SnmpAdminString,
    cucsEquipmentManufacturingDefVid                                 SnmpAdminString,
    cucsEquipmentManufacturingDefPolicyLevel                         Gauge32,
    cucsEquipmentManufacturingDefPolicyOwner                         CucsPolicyPolicyOwner,
    cucsEquipmentManufacturingDefIsSecFwUpdate                       TruthValue
}

cucsEquipmentManufacturingDefInstanceId OBJECT-TYPE
    SYNTAX       CucsManagedObjectId
    MAX-ACCESS   not-accessible
    STATUS       current
    DESCRIPTION
        "Instance identifier of the managed object."
    ::= { cucsEquipmentManufacturingDefEntry 1 }

cucsEquipmentManufacturingDefDn OBJECT-TYPE
    SYNTAX       CucsManagedObjectDn
    MAX-ACCESS   read-only
    STATUS       current
    DESCRIPTION
        "Cisco UCS equipment:ManufacturingDef:dn managed object property"
    ::= { cucsEquipmentManufacturingDefEntry 2 }

cucsEquipmentManufacturingDefRn OBJECT-TYPE
    SYNTAX       SnmpAdminString
    MAX-ACCESS   read-only
    STATUS       current
    DESCRIPTION
        "Cisco UCS equipment:ManufacturingDef:rn managed object property"
    ::= { cucsEquipmentManufacturingDefEntry 3 }

cucsEquipmentManufacturingDefCaption OBJECT-TYPE
    SYNTAX       SnmpAdminString
    MAX-ACCESS   read-only
    STATUS       current
    DESCRIPTION
        "Cisco UCS equipment:ManufacturingDef:caption managed
        object property"
    ::= { cucsEquipmentManufacturingDefEntry 4 }

cucsEquipmentManufacturingDefClei OBJECT-TYPE
    SYNTAX       SnmpAdminString
    MAX-ACCESS   read-only
    STATUS       current
    DESCRIPTION
        "Cisco UCS equipment:ManufacturingDef:clei managed
        object property"
    ::= { cucsEquipmentManufacturingDefEntry 5 }

cucsEquipmentManufacturingDefDescr OBJECT-TYPE
    SYNTAX       SnmpAdminString
    MAX-ACCESS   read-only
    STATUS       current
    DESCRIPTION
        "Cisco UCS equipment:ManufacturingDef:descr managed
        object property"
    ::= { cucsEquipmentManufacturingDefEntry 6 }

cucsEquipmentManufacturingDefDescription OBJECT-TYPE
    SYNTAX       SnmpAdminString
    MAX-ACCESS   read-only
    STATUS       current
    DESCRIPTION
        "Cisco UCS equipment:ManufacturingDef:description
        managed object property"
    ::= { cucsEquipmentManufacturingDefEntry 7 }

cucsEquipmentManufacturingDefFruMajorType OBJECT-TYPE
    SYNTAX       SnmpAdminString
    MAX-ACCESS   read-only
    STATUS       current
    DESCRIPTION
        "Cisco UCS equipment:ManufacturingDef:fruMajorType
        managed object property"
    ::= { cucsEquipmentManufacturingDefEntry 8 }

cucsEquipmentManufacturingDefFruMinorType OBJECT-TYPE
    SYNTAX       SnmpAdminString
    MAX-ACCESS   read-only
    STATUS       current
    DESCRIPTION
        "Cisco UCS equipment:ManufacturingDef:fruMinorType
        managed object property"
    ::= { cucsEquipmentManufacturingDefEntry 9 }

cucsEquipmentManufacturingDefIntId OBJECT-TYPE
    SYNTAX       SnmpAdminString
    MAX-ACCESS   read-only
    STATUS       current
    DESCRIPTION
        "Cisco UCS equipment:ManufacturingDef:intId managed
        object property"
    ::= { cucsEquipmentManufacturingDefEntry 10 }

cucsEquipmentManufacturingDefName OBJECT-TYPE
    SYNTAX       SnmpAdminString
    MAX-ACCESS   read-only
    STATUS       current
    DESCRIPTION
        "Cisco UCS equipment:ManufacturingDef:name managed
        object property"
    ::= { cucsEquipmentManufacturingDefEntry 11 }

cucsEquipmentManufacturingDefOemName OBJECT-TYPE
    SYNTAX       SnmpAdminString
    MAX-ACCESS   read-only
    STATUS       current
    DESCRIPTION
        "Cisco UCS equipment:ManufacturingDef:oemName managed
        object property"
    ::= { cucsEquipmentManufacturingDefEntry 12 }

cucsEquipmentManufacturingDefOemPartNumber OBJECT-TYPE
    SYNTAX       SnmpAdminString
    MAX-ACCESS   read-only
    STATUS       current
    DESCRIPTION
        "Cisco UCS equipment:ManufacturingDef:oemPartNumber
        managed object property"
    ::= { cucsEquipmentManufacturingDefEntry 13 }

cucsEquipmentManufacturingDefPartNumber OBJECT-TYPE
    SYNTAX       SnmpAdminString
    MAX-ACCESS   read-only
    STATUS       current
    DESCRIPTION
        "Cisco UCS equipment:ManufacturingDef:partNumber
        managed object property"
    ::= { cucsEquipmentManufacturingDefEntry 14 }

cucsEquipmentManufacturingDefPid OBJECT-TYPE
    SYNTAX       SnmpAdminString
    MAX-ACCESS   read-only
    STATUS       current
    DESCRIPTION
        "Cisco UCS equipment:ManufacturingDef:pid managed object property"
    ::= { cucsEquipmentManufacturingDefEntry 15 }

cucsEquipmentManufacturingDefSeries OBJECT-TYPE
    SYNTAX       SnmpAdminString
    MAX-ACCESS   read-only
    STATUS       current
    DESCRIPTION
        "Cisco UCS equipment:ManufacturingDef:series managed
        object property"
    ::= { cucsEquipmentManufacturingDefEntry 16 }

cucsEquipmentManufacturingDefSku OBJECT-TYPE
    SYNTAX       SnmpAdminString
    MAX-ACCESS   read-only
    STATUS       current
    DESCRIPTION
        "Cisco UCS equipment:ManufacturingDef:sku managed object property"
    ::= { cucsEquipmentManufacturingDefEntry 17 }

cucsEquipmentManufacturingDefVendorEquipmentType OBJECT-TYPE
    SYNTAX       SnmpAdminString
    MAX-ACCESS   read-only
    STATUS       current
    DESCRIPTION
        "Cisco UCS equipment:ManufacturingDef:vendorEquipmentType
        managed object property"
    ::= { cucsEquipmentManufacturingDefEntry 18 }

cucsEquipmentManufacturingDefVid OBJECT-TYPE
    SYNTAX       SnmpAdminString
    MAX-ACCESS   read-only
    STATUS       current
    DESCRIPTION
        "Cisco UCS equipment:ManufacturingDef:vid managed object property"
    ::= { cucsEquipmentManufacturingDefEntry 19 }

cucsEquipmentManufacturingDefPolicyLevel OBJECT-TYPE
    SYNTAX       Gauge32
    MAX-ACCESS   read-only
    STATUS       current
    DESCRIPTION
        "Cisco UCS equipment:ManufacturingDef:policyLevel
        managed object property"
    ::= { cucsEquipmentManufacturingDefEntry 20 }

cucsEquipmentManufacturingDefPolicyOwner OBJECT-TYPE
    SYNTAX       CucsPolicyPolicyOwner
    MAX-ACCESS   read-only
    STATUS       current
    DESCRIPTION
        "Cisco UCS equipment:ManufacturingDef:policyOwner
        managed object property"
    ::= { cucsEquipmentManufacturingDefEntry 21 }

cucsEquipmentManufacturingDefIsSecFwUpdate OBJECT-TYPE
    SYNTAX       TruthValue
    MAX-ACCESS   read-only
    STATUS       current
    DESCRIPTION
        "Cisco UCS equipment:ManufacturingDef:isSecFwUpdate
        managed object property"
    ::= { cucsEquipmentManufacturingDefEntry 22 }

cucsEquipmentMemoryUnitCapProviderTable OBJECT-TYPE
    SYNTAX           SEQUENCE OF CucsEquipmentMemoryUnitCapProviderEntry
    MAX-ACCESS       not-accessible
    STATUS           current
    DESCRIPTION
        "Cisco UCS equipment:MemoryUnitCapProvider managed object table"
    ::= { cucsEquipmentObjects 43 }

cucsEquipmentMemoryUnitCapProviderEntry OBJECT-TYPE
    SYNTAX           CucsEquipmentMemoryUnitCapProviderEntry
    MAX-ACCESS       not-accessible
    STATUS           current
    DESCRIPTION
        "Entry for the cucsEquipmentMemoryUnitCapProviderTable table."
    INDEX { cucsEquipmentMemoryUnitCapProviderInstanceId }
    ::= { cucsEquipmentMemoryUnitCapProviderTable 1 }

CucsEquipmentMemoryUnitCapProviderEntry ::= SEQUENCE {
    cucsEquipmentMemoryUnitCapProviderInstanceId                     CucsManagedObjectId,
    cucsEquipmentMemoryUnitCapProviderDn                             CucsManagedObjectDn,
    cucsEquipmentMemoryUnitCapProviderRn                             SnmpAdminString,
    cucsEquipmentMemoryUnitCapProviderDeprecated                     TruthValue,
    cucsEquipmentMemoryUnitCapProviderGencount                       Gauge32,
    cucsEquipmentMemoryUnitCapProviderMgmtPlaneVer                   SnmpAdminString,
    cucsEquipmentMemoryUnitCapProviderModel                          SnmpAdminString,
    cucsEquipmentMemoryUnitCapProviderRevision                       SnmpAdminString,
    cucsEquipmentMemoryUnitCapProviderVendor                         SnmpAdminString,
    cucsEquipmentMemoryUnitCapProviderPromCardType                   Gauge32,
    cucsEquipmentMemoryUnitCapProviderDeleted                        TruthValue,
    cucsEquipmentMemoryUnitCapProviderElementLoadFailures            Gauge32,
    cucsEquipmentMemoryUnitCapProviderElementsLoaded                 Gauge32,
    cucsEquipmentMemoryUnitCapProviderLoadErrors                     Gauge32,
    cucsEquipmentMemoryUnitCapProviderLoadWarnings                   Gauge32
}

cucsEquipmentMemoryUnitCapProviderInstanceId OBJECT-TYPE
    SYNTAX       CucsManagedObjectId
    MAX-ACCESS   not-accessible
    STATUS       current
    DESCRIPTION
        "Instance identifier of the managed object."
    ::= { cucsEquipmentMemoryUnitCapProviderEntry 1 }

cucsEquipmentMemoryUnitCapProviderDn OBJECT-TYPE
    SYNTAX       CucsManagedObjectDn
    MAX-ACCESS   read-only
    STATUS       current
    DESCRIPTION
        "Cisco UCS equipment:MemoryUnitCapProvider:dn managed
        object property"
    ::= { cucsEquipmentMemoryUnitCapProviderEntry 2 }

cucsEquipmentMemoryUnitCapProviderRn OBJECT-TYPE
    SYNTAX       SnmpAdminString
    MAX-ACCESS   read-only
    STATUS       current
    DESCRIPTION
        "Cisco UCS equipment:MemoryUnitCapProvider:rn managed
        object property"
    ::= { cucsEquipmentMemoryUnitCapProviderEntry 3 }

cucsEquipmentMemoryUnitCapProviderDeprecated OBJECT-TYPE
    SYNTAX       TruthValue
    MAX-ACCESS   read-only
    STATUS       current
    DESCRIPTION
        "Cisco UCS equipment:MemoryUnitCapProvider:deprecated
        managed object property"
    ::= { cucsEquipmentMemoryUnitCapProviderEntry 4 }

cucsEquipmentMemoryUnitCapProviderGencount OBJECT-TYPE
    SYNTAX       Gauge32
    MAX-ACCESS   read-only
    STATUS       current
    DESCRIPTION
        "Cisco UCS equipment:MemoryUnitCapProvider:gencount
        managed object property"
    ::= { cucsEquipmentMemoryUnitCapProviderEntry 5 }

cucsEquipmentMemoryUnitCapProviderMgmtPlaneVer OBJECT-TYPE
    SYNTAX       SnmpAdminString
    MAX-ACCESS   read-only
    STATUS       current
    DESCRIPTION
        "Cisco UCS equipment:MemoryUnitCapProvider:mgmtPlaneVer
        managed object property"
    ::= { cucsEquipmentMemoryUnitCapProviderEntry 6 }

cucsEquipmentMemoryUnitCapProviderModel OBJECT-TYPE
    SYNTAX       SnmpAdminString
    MAX-ACCESS   read-only
    STATUS       current
    DESCRIPTION
        "Cisco UCS equipment:MemoryUnitCapProvider:model
        managed object property"
    ::= { cucsEquipmentMemoryUnitCapProviderEntry 7 }

cucsEquipmentMemoryUnitCapProviderRevision OBJECT-TYPE
    SYNTAX       SnmpAdminString
    MAX-ACCESS   read-only
    STATUS       current
    DESCRIPTION
        "Cisco UCS equipment:MemoryUnitCapProvider:revision
        managed object property"
    ::= { cucsEquipmentMemoryUnitCapProviderEntry 8 }

cucsEquipmentMemoryUnitCapProviderVendor OBJECT-TYPE
    SYNTAX       SnmpAdminString
    MAX-ACCESS   read-only
    STATUS       current
    DESCRIPTION
        "Cisco UCS equipment:MemoryUnitCapProvider:vendor
        managed object property"
    ::= { cucsEquipmentMemoryUnitCapProviderEntry 9 }

cucsEquipmentMemoryUnitCapProviderPromCardType OBJECT-TYPE
    SYNTAX       Gauge32
    MAX-ACCESS   read-only
    STATUS       current
    DESCRIPTION
        "Cisco UCS equipment:MemoryUnitCapProvider:promCardType
        managed object property"
    ::= { cucsEquipmentMemoryUnitCapProviderEntry 10 }

cucsEquipmentMemoryUnitCapProviderDeleted OBJECT-TYPE
    SYNTAX       TruthValue
    MAX-ACCESS   read-only
    STATUS       current
    DESCRIPTION
        "Cisco UCS equipment:MemoryUnitCapProvider:deleted
        managed object property"
    ::= { cucsEquipmentMemoryUnitCapProviderEntry 11 }

cucsEquipmentMemoryUnitCapProviderElementLoadFailures OBJECT-TYPE
    SYNTAX       Gauge32
    MAX-ACCESS   read-only
    STATUS       current
    DESCRIPTION
        "Cisco UCS equipment:MemoryUnitCapProvider:elementLoadFailures
        managed object property"
    ::= { cucsEquipmentMemoryUnitCapProviderEntry 12 }

cucsEquipmentMemoryUnitCapProviderElementsLoaded OBJECT-TYPE
    SYNTAX       Gauge32
    MAX-ACCESS   read-only
    STATUS       current
    DESCRIPTION
        "Cisco UCS equipment:MemoryUnitCapProvider:elementsLoaded
        managed object property"
    ::= { cucsEquipmentMemoryUnitCapProviderEntry 13 }

cucsEquipmentMemoryUnitCapProviderLoadErrors OBJECT-TYPE
    SYNTAX       Gauge32
    MAX-ACCESS   read-only
    STATUS       current
    DESCRIPTION
        "Cisco UCS equipment:MemoryUnitCapProvider:loadErrors
        managed object property"
    ::= { cucsEquipmentMemoryUnitCapProviderEntry 14 }

cucsEquipmentMemoryUnitCapProviderLoadWarnings OBJECT-TYPE
    SYNTAX       Gauge32
    MAX-ACCESS   read-only
    STATUS       current
    DESCRIPTION
        "Cisco UCS equipment:MemoryUnitCapProvider:loadWarnings
        managed object property"
    ::= { cucsEquipmentMemoryUnitCapProviderEntry 15 }

cucsEquipmentMemoryUnitDiscoveryModifierDefTable OBJECT-TYPE
    SYNTAX           SEQUENCE OF CucsEquipmentMemoryUnitDiscoveryModifierDefEntry
    MAX-ACCESS       not-accessible
    STATUS           current
    DESCRIPTION
        "Cisco UCS equipment:MemoryUnitDiscoveryModifierDef
        managed object table"
    ::= { cucsEquipmentObjects 44 }

cucsEquipmentMemoryUnitDiscoveryModifierDefEntry OBJECT-TYPE
    SYNTAX           CucsEquipmentMemoryUnitDiscoveryModifierDefEntry
    MAX-ACCESS       not-accessible
    STATUS           current
    DESCRIPTION
        "Entry for the cucsEquipmentMemoryUnitDiscoveryModifierDefTable table."
    INDEX { cucsEquipmentMemoryUnitDiscoveryModifierDefInstanceId }
    ::= { cucsEquipmentMemoryUnitDiscoveryModifierDefTable 1 }

CucsEquipmentMemoryUnitDiscoveryModifierDefEntry ::= SEQUENCE {
    cucsEquipmentMemoryUnitDiscoveryModifierDefInstanceId            CucsManagedObjectId,
    cucsEquipmentMemoryUnitDiscoveryModifierDefDn                    CucsManagedObjectDn,
    cucsEquipmentMemoryUnitDiscoveryModifierDefRn                    SnmpAdminString,
    cucsEquipmentMemoryUnitDiscoveryModifierDefAction                CucsEquipmentMemoryUnitDiscoveryModifierAction,
    cucsEquipmentMemoryUnitDiscoveryModifierDefConstraintType        CucsComputeMemoryUnitConstraintType,
    cucsEquipmentMemoryUnitDiscoveryModifierDefDescr                 SnmpAdminString,
    cucsEquipmentMemoryUnitDiscoveryModifierDefIntId                 SnmpAdminString,
    cucsEquipmentMemoryUnitDiscoveryModifierDefName                  SnmpAdminString,
    cucsEquipmentMemoryUnitDiscoveryModifierDefPolicyLevel           Gauge32,
    cucsEquipmentMemoryUnitDiscoveryModifierDefPolicyOwner           CucsPolicyPolicyOwner
}

cucsEquipmentMemoryUnitDiscoveryModifierDefInstanceId OBJECT-TYPE
    SYNTAX       CucsManagedObjectId
    MAX-ACCESS   not-accessible
    STATUS       current
    DESCRIPTION
        "Instance identifier of the managed object."
    ::= { cucsEquipmentMemoryUnitDiscoveryModifierDefEntry 1 }

cucsEquipmentMemoryUnitDiscoveryModifierDefDn OBJECT-TYPE
    SYNTAX       CucsManagedObjectDn
    MAX-ACCESS   read-only
    STATUS       current
    DESCRIPTION
        "Cisco UCS equipment:MemoryUnitDiscoveryModifierDef:dn
        managed object property"
    ::= { cucsEquipmentMemoryUnitDiscoveryModifierDefEntry 2 }

cucsEquipmentMemoryUnitDiscoveryModifierDefRn OBJECT-TYPE
    SYNTAX       SnmpAdminString
    MAX-ACCESS   read-only
    STATUS       current
    DESCRIPTION
        "Cisco UCS equipment:MemoryUnitDiscoveryModifierDef:rn
        managed object property"
    ::= { cucsEquipmentMemoryUnitDiscoveryModifierDefEntry 3 }

cucsEquipmentMemoryUnitDiscoveryModifierDefAction OBJECT-TYPE
    SYNTAX       CucsEquipmentMemoryUnitDiscoveryModifierAction
    MAX-ACCESS   read-only
    STATUS       current
    DESCRIPTION
        "Cisco UCS equipment:MemoryUnitDiscoveryModifierDef:action
        managed object property"
    ::= { cucsEquipmentMemoryUnitDiscoveryModifierDefEntry 4 }

cucsEquipmentMemoryUnitDiscoveryModifierDefConstraintType OBJECT-TYPE
    SYNTAX       CucsComputeMemoryUnitConstraintType
    MAX-ACCESS   read-only
    STATUS       current
    DESCRIPTION
        "Cisco UCS equipment:MemoryUnitDiscoveryModifierDef:constraintType
         managed object property"
    ::= { cucsEquipmentMemoryUnitDiscoveryModifierDefEntry 5 }

cucsEquipmentMemoryUnitDiscoveryModifierDefDescr OBJECT-TYPE
    SYNTAX       SnmpAdminString
    MAX-ACCESS   read-only
    STATUS       current
    DESCRIPTION
        "Cisco UCS equipment:MemoryUnitDiscoveryModifierDef:descr
        managed object property"
    ::= { cucsEquipmentMemoryUnitDiscoveryModifierDefEntry 6 }

cucsEquipmentMemoryUnitDiscoveryModifierDefIntId OBJECT-TYPE
    SYNTAX       SnmpAdminString
    MAX-ACCESS   read-only
    STATUS       current
    DESCRIPTION
        "Cisco UCS equipment:MemoryUnitDiscoveryModifierDef:intId
        managed object property"
    ::= { cucsEquipmentMemoryUnitDiscoveryModifierDefEntry 7 }

cucsEquipmentMemoryUnitDiscoveryModifierDefName OBJECT-TYPE
    SYNTAX       SnmpAdminString
    MAX-ACCESS   read-only
    STATUS       current
    DESCRIPTION
        "Cisco UCS equipment:MemoryUnitDiscoveryModifierDef:name
        managed object property"
    ::= { cucsEquipmentMemoryUnitDiscoveryModifierDefEntry 8 }

cucsEquipmentMemoryUnitDiscoveryModifierDefPolicyLevel OBJECT-TYPE
    SYNTAX       Gauge32
    MAX-ACCESS   read-only
    STATUS       current
    DESCRIPTION
        "Cisco UCS equipment:MemoryUnitDiscoveryModifierDef:policyLevel
        managed object property"
    ::= { cucsEquipmentMemoryUnitDiscoveryModifierDefEntry 9 }

cucsEquipmentMemoryUnitDiscoveryModifierDefPolicyOwner OBJECT-TYPE
    SYNTAX       CucsPolicyPolicyOwner
    MAX-ACCESS   read-only
    STATUS       current
    DESCRIPTION
        "Cisco UCS equipment:MemoryUnitDiscoveryModifierDef:policyOwner
        managed object property"
    ::= { cucsEquipmentMemoryUnitDiscoveryModifierDefEntry 10 }

cucsEquipmentMgmtCapProviderTable OBJECT-TYPE
    SYNTAX           SEQUENCE OF CucsEquipmentMgmtCapProviderEntry
    MAX-ACCESS       not-accessible
    STATUS           current
    DESCRIPTION
        "Cisco UCS equipment:MgmtCapProvider managed object table"
    ::= { cucsEquipmentObjects 45 }

cucsEquipmentMgmtCapProviderEntry OBJECT-TYPE
    SYNTAX           CucsEquipmentMgmtCapProviderEntry
    MAX-ACCESS       not-accessible
    STATUS           current
    DESCRIPTION
        "Entry for the cucsEquipmentMgmtCapProviderTable table."
    INDEX { cucsEquipmentMgmtCapProviderInstanceId }
    ::= { cucsEquipmentMgmtCapProviderTable 1 }

CucsEquipmentMgmtCapProviderEntry ::= SEQUENCE {
    cucsEquipmentMgmtCapProviderInstanceId                           CucsManagedObjectId,
    cucsEquipmentMgmtCapProviderDn                                   CucsManagedObjectDn,
    cucsEquipmentMgmtCapProviderRn                                   SnmpAdminString,
    cucsEquipmentMgmtCapProviderDeprecated                           TruthValue,
    cucsEquipmentMgmtCapProviderGencount                             Gauge32,
    cucsEquipmentMgmtCapProviderMgmtPlaneVer                         SnmpAdminString,
    cucsEquipmentMgmtCapProviderModel                                SnmpAdminString,
    cucsEquipmentMgmtCapProviderRevision                             SnmpAdminString,
    cucsEquipmentMgmtCapProviderVendor                               SnmpAdminString,
    cucsEquipmentMgmtCapProviderPromCardType                         Gauge32,
    cucsEquipmentMgmtCapProviderDeleted                              TruthValue,
    cucsEquipmentMgmtCapProviderElementLoadFailures                  Gauge32,
    cucsEquipmentMgmtCapProviderElementsLoaded                       Gauge32,
    cucsEquipmentMgmtCapProviderLoadErrors                           Gauge32,
    cucsEquipmentMgmtCapProviderLoadWarnings                         Gauge32
}

cucsEquipmentMgmtCapProviderInstanceId OBJECT-TYPE
    SYNTAX       CucsManagedObjectId
    MAX-ACCESS   not-accessible
    STATUS       current
    DESCRIPTION
        "Instance identifier of the managed object."
    ::= { cucsEquipmentMgmtCapProviderEntry 1 }

cucsEquipmentMgmtCapProviderDn OBJECT-TYPE
    SYNTAX       CucsManagedObjectDn
    MAX-ACCESS   read-only
    STATUS       current
    DESCRIPTION
        "Cisco UCS equipment:MgmtCapProvider:dn managed object property"
    ::= { cucsEquipmentMgmtCapProviderEntry 2 }

cucsEquipmentMgmtCapProviderRn OBJECT-TYPE
    SYNTAX       SnmpAdminString
    MAX-ACCESS   read-only
    STATUS       current
    DESCRIPTION
        "Cisco UCS equipment:MgmtCapProvider:rn managed object property"
    ::= { cucsEquipmentMgmtCapProviderEntry 3 }

cucsEquipmentMgmtCapProviderDeprecated OBJECT-TYPE
    SYNTAX       TruthValue
    MAX-ACCESS   read-only
    STATUS       current
    DESCRIPTION
        "Cisco UCS equipment:MgmtCapProvider:deprecated
        managed object property"
    ::= { cucsEquipmentMgmtCapProviderEntry 4 }

cucsEquipmentMgmtCapProviderGencount OBJECT-TYPE
    SYNTAX       Gauge32
    MAX-ACCESS   read-only
    STATUS       current
    DESCRIPTION
        "Cisco UCS equipment:MgmtCapProvider:gencount managed
        object property"
    ::= { cucsEquipmentMgmtCapProviderEntry 5 }

cucsEquipmentMgmtCapProviderMgmtPlaneVer OBJECT-TYPE
    SYNTAX       SnmpAdminString
    MAX-ACCESS   read-only
    STATUS       current
    DESCRIPTION
        "Cisco UCS equipment:MgmtCapProvider:mgmtPlaneVer
        managed object property"
    ::= { cucsEquipmentMgmtCapProviderEntry 6 }

cucsEquipmentMgmtCapProviderModel OBJECT-TYPE
    SYNTAX       SnmpAdminString
    MAX-ACCESS   read-only
    STATUS       current
    DESCRIPTION
        "Cisco UCS equipment:MgmtCapProvider:model managed
        object property"
    ::= { cucsEquipmentMgmtCapProviderEntry 7 }

cucsEquipmentMgmtCapProviderRevision OBJECT-TYPE
    SYNTAX       SnmpAdminString
    MAX-ACCESS   read-only
    STATUS       current
    DESCRIPTION
        "Cisco UCS equipment:MgmtCapProvider:revision managed
        object property"
    ::= { cucsEquipmentMgmtCapProviderEntry 8 }

cucsEquipmentMgmtCapProviderVendor OBJECT-TYPE
    SYNTAX       SnmpAdminString
    MAX-ACCESS   read-only
    STATUS       current
    DESCRIPTION
        "Cisco UCS equipment:MgmtCapProvider:vendor managed
        object property"
    ::= { cucsEquipmentMgmtCapProviderEntry 9 }

cucsEquipmentMgmtCapProviderPromCardType OBJECT-TYPE
    SYNTAX       Gauge32
    MAX-ACCESS   read-only
    STATUS       current
    DESCRIPTION
        "Cisco UCS equipment:MgmtCapProvider:promCardType
        managed object property"
    ::= { cucsEquipmentMgmtCapProviderEntry 10 }

cucsEquipmentMgmtCapProviderDeleted OBJECT-TYPE
    SYNTAX       TruthValue
    MAX-ACCESS   read-only
    STATUS       current
    DESCRIPTION
        "Cisco UCS equipment:MgmtCapProvider:deleted managed
        object property"
    ::= { cucsEquipmentMgmtCapProviderEntry 11 }

cucsEquipmentMgmtCapProviderElementLoadFailures OBJECT-TYPE
    SYNTAX       Gauge32
    MAX-ACCESS   read-only
    STATUS       current
    DESCRIPTION
        "Cisco UCS equipment:MgmtCapProvider:elementLoadFailures
        managed object property"
    ::= { cucsEquipmentMgmtCapProviderEntry 12 }

cucsEquipmentMgmtCapProviderElementsLoaded OBJECT-TYPE
    SYNTAX       Gauge32
    MAX-ACCESS   read-only
    STATUS       current
    DESCRIPTION
        "Cisco UCS equipment:MgmtCapProvider:elementsLoaded
        managed object property"
    ::= { cucsEquipmentMgmtCapProviderEntry 13 }

cucsEquipmentMgmtCapProviderLoadErrors OBJECT-TYPE
    SYNTAX       Gauge32
    MAX-ACCESS   read-only
    STATUS       current
    DESCRIPTION
        "Cisco UCS equipment:MgmtCapProvider:loadErrors
        managed object property"
    ::= { cucsEquipmentMgmtCapProviderEntry 14 }

cucsEquipmentMgmtCapProviderLoadWarnings OBJECT-TYPE
    SYNTAX       Gauge32
    MAX-ACCESS   read-only
    STATUS       current
    DESCRIPTION
        "Cisco UCS equipment:MgmtCapProvider:loadWarnings
        managed object property"
    ::= { cucsEquipmentMgmtCapProviderEntry 15 }

cucsEquipmentMgmtExtCapProviderTable OBJECT-TYPE
    SYNTAX           SEQUENCE OF CucsEquipmentMgmtExtCapProviderEntry
    MAX-ACCESS       not-accessible
    STATUS           current
    DESCRIPTION
        "Cisco UCS equipment:MgmtExtCapProvider managed object table"
    ::= { cucsEquipmentObjects 46 }

cucsEquipmentMgmtExtCapProviderEntry OBJECT-TYPE
    SYNTAX           CucsEquipmentMgmtExtCapProviderEntry
    MAX-ACCESS       not-accessible
    STATUS           current
    DESCRIPTION
        "Entry for the cucsEquipmentMgmtExtCapProviderTable table."
    INDEX { cucsEquipmentMgmtExtCapProviderInstanceId }
    ::= { cucsEquipmentMgmtExtCapProviderTable 1 }

CucsEquipmentMgmtExtCapProviderEntry ::= SEQUENCE {
    cucsEquipmentMgmtExtCapProviderInstanceId                        CucsManagedObjectId,
    cucsEquipmentMgmtExtCapProviderDn                                CucsManagedObjectDn,
    cucsEquipmentMgmtExtCapProviderRn                                SnmpAdminString,
    cucsEquipmentMgmtExtCapProviderDeprecated                        TruthValue,
    cucsEquipmentMgmtExtCapProviderGencount                          Gauge32,
    cucsEquipmentMgmtExtCapProviderMgmtPlaneVer                      SnmpAdminString,
    cucsEquipmentMgmtExtCapProviderModel                             SnmpAdminString,
    cucsEquipmentMgmtExtCapProviderRevision                          SnmpAdminString,
    cucsEquipmentMgmtExtCapProviderVendor                            SnmpAdminString,
    cucsEquipmentMgmtExtCapProviderPromCardType                      Gauge32,
    cucsEquipmentMgmtExtCapProviderDeleted                           TruthValue,
    cucsEquipmentMgmtExtCapProviderElementLoadFailures               Gauge32,
    cucsEquipmentMgmtExtCapProviderElementsLoaded                    Gauge32,
    cucsEquipmentMgmtExtCapProviderLoadErrors                        Gauge32,
    cucsEquipmentMgmtExtCapProviderLoadWarnings                      Gauge32
}

cucsEquipmentMgmtExtCapProviderInstanceId OBJECT-TYPE
    SYNTAX       CucsManagedObjectId
    MAX-ACCESS   not-accessible
    STATUS       current
    DESCRIPTION
        "Instance identifier of the managed object."
    ::= { cucsEquipmentMgmtExtCapProviderEntry 1 }

cucsEquipmentMgmtExtCapProviderDn OBJECT-TYPE
    SYNTAX       CucsManagedObjectDn
    MAX-ACCESS   read-only
    STATUS       current
    DESCRIPTION
        "Cisco UCS equipment:MgmtExtCapProvider:dn managed
        object property"
    ::= { cucsEquipmentMgmtExtCapProviderEntry 2 }

cucsEquipmentMgmtExtCapProviderRn OBJECT-TYPE
    SYNTAX       SnmpAdminString
    MAX-ACCESS   read-only
    STATUS       current
    DESCRIPTION
        "Cisco UCS equipment:MgmtExtCapProvider:rn managed
        object property"
    ::= { cucsEquipmentMgmtExtCapProviderEntry 3 }

cucsEquipmentMgmtExtCapProviderDeprecated OBJECT-TYPE
    SYNTAX       TruthValue
    MAX-ACCESS   read-only
    STATUS       current
    DESCRIPTION
        "Cisco UCS equipment:MgmtExtCapProvider:deprecated
        managed object property"
    ::= { cucsEquipmentMgmtExtCapProviderEntry 4 }

cucsEquipmentMgmtExtCapProviderGencount OBJECT-TYPE
    SYNTAX       Gauge32
    MAX-ACCESS   read-only
    STATUS       current
    DESCRIPTION
        "Cisco UCS equipment:MgmtExtCapProvider:gencount
        managed object property"
    ::= { cucsEquipmentMgmtExtCapProviderEntry 5 }

cucsEquipmentMgmtExtCapProviderMgmtPlaneVer OBJECT-TYPE
    SYNTAX       SnmpAdminString
    MAX-ACCESS   read-only
    STATUS       current
    DESCRIPTION
        "Cisco UCS equipment:MgmtExtCapProvider:mgmtPlaneVer
        managed object property"
    ::= { cucsEquipmentMgmtExtCapProviderEntry 6 }

cucsEquipmentMgmtExtCapProviderModel OBJECT-TYPE
    SYNTAX       SnmpAdminString
    MAX-ACCESS   read-only
    STATUS       current
    DESCRIPTION
        "Cisco UCS equipment:MgmtExtCapProvider:model managed
        object property"
    ::= { cucsEquipmentMgmtExtCapProviderEntry 7 }

cucsEquipmentMgmtExtCapProviderRevision OBJECT-TYPE
    SYNTAX       SnmpAdminString
    MAX-ACCESS   read-only
    STATUS       current
    DESCRIPTION
        "Cisco UCS equipment:MgmtExtCapProvider:revision
        managed object property"
    ::= { cucsEquipmentMgmtExtCapProviderEntry 8 }

cucsEquipmentMgmtExtCapProviderVendor OBJECT-TYPE
    SYNTAX       SnmpAdminString
    MAX-ACCESS   read-only
    STATUS       current
    DESCRIPTION
        "Cisco UCS equipment:MgmtExtCapProvider:vendor
        managed object property"
    ::= { cucsEquipmentMgmtExtCapProviderEntry 9 }

cucsEquipmentMgmtExtCapProviderPromCardType OBJECT-TYPE
    SYNTAX       Gauge32
    MAX-ACCESS   read-only
    STATUS       current
    DESCRIPTION
        "Cisco UCS equipment:MgmtExtCapProvider:promCardType
        managed object property"
    ::= { cucsEquipmentMgmtExtCapProviderEntry 10 }

cucsEquipmentMgmtExtCapProviderDeleted OBJECT-TYPE
    SYNTAX       TruthValue
    MAX-ACCESS   read-only
    STATUS       current
    DESCRIPTION
        "Cisco UCS equipment:MgmtExtCapProvider:deleted
        managed object property"
    ::= { cucsEquipmentMgmtExtCapProviderEntry 11 }

cucsEquipmentMgmtExtCapProviderElementLoadFailures OBJECT-TYPE
    SYNTAX       Gauge32
    MAX-ACCESS   read-only
    STATUS       current
    DESCRIPTION
        "Cisco UCS equipment:MgmtExtCapProvider:elementLoadFailures
        managed object property"
    ::= { cucsEquipmentMgmtExtCapProviderEntry 12 }

cucsEquipmentMgmtExtCapProviderElementsLoaded OBJECT-TYPE
    SYNTAX       Gauge32
    MAX-ACCESS   read-only
    STATUS       current
    DESCRIPTION
        "Cisco UCS equipment:MgmtExtCapProvider:elementsLoaded
        managed object property"
    ::= { cucsEquipmentMgmtExtCapProviderEntry 13 }

cucsEquipmentMgmtExtCapProviderLoadErrors OBJECT-TYPE
    SYNTAX       Gauge32
    MAX-ACCESS   read-only
    STATUS       current
    DESCRIPTION
        "Cisco UCS equipment:MgmtExtCapProvider:loadErrors
        managed object property"
    ::= { cucsEquipmentMgmtExtCapProviderEntry 14 }

cucsEquipmentMgmtExtCapProviderLoadWarnings OBJECT-TYPE
    SYNTAX       Gauge32
    MAX-ACCESS   read-only
    STATUS       current
    DESCRIPTION
        "Cisco UCS equipment:MgmtExtCapProvider:loadWarnings
        managed object property"
    ::= { cucsEquipmentMgmtExtCapProviderEntry 15 }

cucsEquipmentMiniStorageCapProviderTable OBJECT-TYPE
    SYNTAX           SEQUENCE OF CucsEquipmentMiniStorageCapProviderEntry
    MAX-ACCESS       not-accessible
    STATUS           current
    DESCRIPTION
        "Cisco UCS equipment:MiniStorageCapProvider managed object table"
    ::= { cucsEquipmentObjects 229 }

cucsEquipmentMiniStorageCapProviderEntry OBJECT-TYPE
    SYNTAX           CucsEquipmentMiniStorageCapProviderEntry
    MAX-ACCESS       not-accessible
    STATUS           current
    DESCRIPTION
        "Entry for the cucsEquipmentMiniStorageCapProviderTable table."
    INDEX { cucsEquipmentMiniStorageCapProviderInstanceId }
    ::= { cucsEquipmentMiniStorageCapProviderTable 1 }

CucsEquipmentMiniStorageCapProviderEntry ::= SEQUENCE {
    cucsEquipmentMiniStorageCapProviderInstanceId                    CucsManagedObjectId,
    cucsEquipmentMiniStorageCapProviderDn                            CucsManagedObjectDn,
    cucsEquipmentMiniStorageCapProviderRn                            SnmpAdminString,
    cucsEquipmentMiniStorageCapProviderCardType                      CucsEquipmentCType,
    cucsEquipmentMiniStorageCapProviderDeleted                       TruthValue,
    cucsEquipmentMiniStorageCapProviderDeprecated                    TruthValue,
    cucsEquipmentMiniStorageCapProviderElementLoadFailures           Gauge32,
    cucsEquipmentMiniStorageCapProviderElementsLoaded                Gauge32,
    cucsEquipmentMiniStorageCapProviderGencount                      Gauge32,
    cucsEquipmentMiniStorageCapProviderLoadErrors                    Gauge32,
    cucsEquipmentMiniStorageCapProviderLoadWarnings                  Gauge32,
    cucsEquipmentMiniStorageCapProviderMgmtPlaneVer                  SnmpAdminString,
    cucsEquipmentMiniStorageCapProviderModel                         SnmpAdminString,
    cucsEquipmentMiniStorageCapProviderPromCardType                  Gauge32,
    cucsEquipmentMiniStorageCapProviderRevision                      SnmpAdminString,
    cucsEquipmentMiniStorageCapProviderVendor                        SnmpAdminString
}

cucsEquipmentMiniStorageCapProviderInstanceId OBJECT-TYPE
    SYNTAX       CucsManagedObjectId
    MAX-ACCESS   not-accessible
    STATUS       current
    DESCRIPTION
        "Instance identifier of the managed object."
    ::= { cucsEquipmentMiniStorageCapProviderEntry 1 }

cucsEquipmentMiniStorageCapProviderDn OBJECT-TYPE
    SYNTAX       CucsManagedObjectDn
    MAX-ACCESS   read-only
    STATUS       current
    DESCRIPTION
        "Cisco UCS equipment:MiniStorageCapProvider:dn
        managed object property"
    ::= { cucsEquipmentMiniStorageCapProviderEntry 2 }

cucsEquipmentMiniStorageCapProviderRn OBJECT-TYPE
    SYNTAX       SnmpAdminString
    MAX-ACCESS   read-only
    STATUS       current
    DESCRIPTION
        "Cisco UCS equipment:MiniStorageCapProvider:rn
        managed object property"
    ::= { cucsEquipmentMiniStorageCapProviderEntry 3 }

cucsEquipmentMiniStorageCapProviderCardType OBJECT-TYPE
    SYNTAX       CucsEquipmentCType
    MAX-ACCESS   read-only
    STATUS       current
    DESCRIPTION
        "Cisco UCS equipment:MiniStorageCapProvider:cardType
        managed object property"
    ::= { cucsEquipmentMiniStorageCapProviderEntry 4 }

cucsEquipmentMiniStorageCapProviderDeleted OBJECT-TYPE
    SYNTAX       TruthValue
    MAX-ACCESS   read-only
    STATUS       current
    DESCRIPTION
        "Cisco UCS equipment:MiniStorageCapProvider:deleted
        managed object property"
    ::= { cucsEquipmentMiniStorageCapProviderEntry 5 }

cucsEquipmentMiniStorageCapProviderDeprecated OBJECT-TYPE
    SYNTAX       TruthValue
    MAX-ACCESS   read-only
    STATUS       current
    DESCRIPTION
        "Cisco UCS equipment:MiniStorageCapProvider:deprecated
        managed object property"
    ::= { cucsEquipmentMiniStorageCapProviderEntry 6 }

cucsEquipmentMiniStorageCapProviderElementLoadFailures OBJECT-TYPE
    SYNTAX       Gauge32
    MAX-ACCESS   read-only
    STATUS       current
    DESCRIPTION
        "Cisco UCS equipment:MiniStorageCapProvider:elementLoadFailures
        managed object property"
    ::= { cucsEquipmentMiniStorageCapProviderEntry 7 }

cucsEquipmentMiniStorageCapProviderElementsLoaded OBJECT-TYPE
    SYNTAX       Gauge32
    MAX-ACCESS   read-only
    STATUS       current
    DESCRIPTION
        "Cisco UCS equipment:MiniStorageCapProvider:elementsLoaded
        managed object property"
    ::= { cucsEquipmentMiniStorageCapProviderEntry 8 }

cucsEquipmentMiniStorageCapProviderGencount OBJECT-TYPE
    SYNTAX       Gauge32
    MAX-ACCESS   read-only
    STATUS       current
    DESCRIPTION
        "Cisco UCS equipment:MiniStorageCapProvider:gencount
        managed object property"
    ::= { cucsEquipmentMiniStorageCapProviderEntry 9 }

cucsEquipmentMiniStorageCapProviderLoadErrors OBJECT-TYPE
    SYNTAX       Gauge32
    MAX-ACCESS   read-only
    STATUS       current
    DESCRIPTION
        "Cisco UCS equipment:MiniStorageCapProvider:loadErrors
        managed object property"
    ::= { cucsEquipmentMiniStorageCapProviderEntry 10 }

cucsEquipmentMiniStorageCapProviderLoadWarnings OBJECT-TYPE
    SYNTAX       Gauge32
    MAX-ACCESS   read-only
    STATUS       current
    DESCRIPTION
        "Cisco UCS equipment:MiniStorageCapProvider:loadWarnings
        managed object property"
    ::= { cucsEquipmentMiniStorageCapProviderEntry 11 }

cucsEquipmentMiniStorageCapProviderMgmtPlaneVer OBJECT-TYPE
    SYNTAX       SnmpAdminString
    MAX-ACCESS   read-only
    STATUS       current
    DESCRIPTION
        "Cisco UCS equipment:MiniStorageCapProvider:mgmtPlaneVer
        managed object property"
    ::= { cucsEquipmentMiniStorageCapProviderEntry 12 }

cucsEquipmentMiniStorageCapProviderModel OBJECT-TYPE
    SYNTAX       SnmpAdminString
    MAX-ACCESS   read-only
    STATUS       current
    DESCRIPTION
        "Cisco UCS equipment:MiniStorageCapProvider:model
        managed object property"
    ::= { cucsEquipmentMiniStorageCapProviderEntry 13 }

cucsEquipmentMiniStorageCapProviderPromCardType OBJECT-TYPE
    SYNTAX       Gauge32
    MAX-ACCESS   read-only
    STATUS       current
    DESCRIPTION
        "Cisco UCS equipment:MiniStorageCapProvider:promCardType
        managed object property"
    ::= { cucsEquipmentMiniStorageCapProviderEntry 14 }

cucsEquipmentMiniStorageCapProviderRevision OBJECT-TYPE
    SYNTAX       SnmpAdminString
    MAX-ACCESS   read-only
    STATUS       current
    DESCRIPTION
        "Cisco UCS equipment:MiniStorageCapProvider:revision
        managed object property"
    ::= { cucsEquipmentMiniStorageCapProviderEntry 15 }

cucsEquipmentMiniStorageCapProviderVendor OBJECT-TYPE
    SYNTAX       SnmpAdminString
    MAX-ACCESS   read-only
    STATUS       current
    DESCRIPTION
        "Cisco UCS equipment:MiniStorageCapProvider:vendor
        managed object property"
    ::= { cucsEquipmentMiniStorageCapProviderEntry 16 }

cucsEquipmentNetworkElementFanStatsTable OBJECT-TYPE
    SYNTAX           SEQUENCE OF CucsEquipmentNetworkElementFanStatsEntry
    MAX-ACCESS       not-accessible
    STATUS           current
    DESCRIPTION
        "Cisco UCS equipment:NetworkElementFanStats managed object table"
    ::= { cucsEquipmentObjects 86 }

cucsEquipmentNetworkElementFanStatsEntry OBJECT-TYPE
    SYNTAX           CucsEquipmentNetworkElementFanStatsEntry
    MAX-ACCESS       not-accessible
    STATUS           current
    DESCRIPTION
        "Entry for the cucsEquipmentNetworkElementFanStatsTable table."
    INDEX { cucsEquipmentNetworkElementFanStatsInstanceId }
    ::= { cucsEquipmentNetworkElementFanStatsTable 1 }

CucsEquipmentNetworkElementFanStatsEntry ::= SEQUENCE {
    cucsEquipmentNetworkElementFanStatsInstanceId                    CucsManagedObjectId,
    cucsEquipmentNetworkElementFanStatsDn                            CucsManagedObjectDn,
    cucsEquipmentNetworkElementFanStatsRn                            SnmpAdminString,
    cucsEquipmentNetworkElementFanStatsAirflowDirection              CucsEquipmentAirflowDirection,
    cucsEquipmentNetworkElementFanStatsDrivePercentage               Gauge32,
    cucsEquipmentNetworkElementFanStatsDrivePercentageAvg            Gauge32,
    cucsEquipmentNetworkElementFanStatsDrivePercentageMax            Gauge32,
    cucsEquipmentNetworkElementFanStatsDrivePercentageMin            Gauge32,
    cucsEquipmentNetworkElementFanStatsIntervals                     Gauge32,
    cucsEquipmentNetworkElementFanStatsSpeed                         Gauge32,
    cucsEquipmentNetworkElementFanStatsSpeedAvg                      Gauge32,
    cucsEquipmentNetworkElementFanStatsSpeedMax                      Gauge32,
    cucsEquipmentNetworkElementFanStatsSpeedMin                      Gauge32,
    cucsEquipmentNetworkElementFanStatsSuspect                       TruthValue,
    cucsEquipmentNetworkElementFanStatsThresholded                   CucsEquipmentNetworkElementFanStatsThresholded,
    cucsEquipmentNetworkElementFanStatsTimeCollected                 DateAndTime,
    cucsEquipmentNetworkElementFanStatsUpdate                        Gauge32
}

cucsEquipmentNetworkElementFanStatsInstanceId OBJECT-TYPE
    SYNTAX       CucsManagedObjectId
    MAX-ACCESS   not-accessible
    STATUS       current
    DESCRIPTION
        "Instance identifier of the managed object."
    ::= { cucsEquipmentNetworkElementFanStatsEntry 1 }

cucsEquipmentNetworkElementFanStatsDn OBJECT-TYPE
    SYNTAX       CucsManagedObjectDn
    MAX-ACCESS   read-only
    STATUS       current
    DESCRIPTION
        "Cisco UCS equipment:NetworkElementFanStats:dn
        managed object property"
    ::= { cucsEquipmentNetworkElementFanStatsEntry 2 }

cucsEquipmentNetworkElementFanStatsRn OBJECT-TYPE
    SYNTAX       SnmpAdminString
    MAX-ACCESS   read-only
    STATUS       current
    DESCRIPTION
        "Cisco UCS equipment:NetworkElementFanStats:rn
        managed object property"
    ::= { cucsEquipmentNetworkElementFanStatsEntry 3 }

cucsEquipmentNetworkElementFanStatsAirflowDirection OBJECT-TYPE
    SYNTAX       CucsEquipmentAirflowDirection
    MAX-ACCESS   read-only
    STATUS       current
    DESCRIPTION
        "Cisco UCS equipment:NetworkElementFanStats:airflowDirection
        managed object property"
    ::= { cucsEquipmentNetworkElementFanStatsEntry 4 }

cucsEquipmentNetworkElementFanStatsDrivePercentage OBJECT-TYPE
    SYNTAX       Gauge32
    MAX-ACCESS   read-only
    STATUS       current
    DESCRIPTION
        "Cisco UCS equipment:NetworkElementFanStats:drivePercentage
        managed object property"
    ::= { cucsEquipmentNetworkElementFanStatsEntry 5 }

cucsEquipmentNetworkElementFanStatsDrivePercentageAvg OBJECT-TYPE
    SYNTAX       Gauge32
    MAX-ACCESS   read-only
    STATUS       current
    DESCRIPTION
        "Cisco UCS equipment:NetworkElementFanStats:drivePercentageAvg
        managed object property"
    ::= { cucsEquipmentNetworkElementFanStatsEntry 6 }

cucsEquipmentNetworkElementFanStatsDrivePercentageMax OBJECT-TYPE
    SYNTAX       Gauge32
    MAX-ACCESS   read-only
    STATUS       current
    DESCRIPTION
        "Cisco UCS equipment:NetworkElementFanStats:drivePercentageMax
        managed object property"
    ::= { cucsEquipmentNetworkElementFanStatsEntry 7 }

cucsEquipmentNetworkElementFanStatsDrivePercentageMin OBJECT-TYPE
    SYNTAX       Gauge32
    MAX-ACCESS   read-only
    STATUS       current
    DESCRIPTION
        "Cisco UCS equipment:NetworkElementFanStats:drivePercentageMin
        managed object property"
    ::= { cucsEquipmentNetworkElementFanStatsEntry 8 }

cucsEquipmentNetworkElementFanStatsIntervals OBJECT-TYPE
    SYNTAX       Gauge32
    MAX-ACCESS   read-only
    STATUS       current
    DESCRIPTION
        "Cisco UCS equipment:NetworkElementFanStats:intervals
        managed object property"
    ::= { cucsEquipmentNetworkElementFanStatsEntry 9 }

cucsEquipmentNetworkElementFanStatsSpeed OBJECT-TYPE
    SYNTAX       Gauge32
    MAX-ACCESS   read-only
    STATUS       current
    DESCRIPTION
        "Cisco UCS equipment:NetworkElementFanStats:speed
        managed object property"
    ::= { cucsEquipmentNetworkElementFanStatsEntry 10 }

cucsEquipmentNetworkElementFanStatsSpeedAvg OBJECT-TYPE
    SYNTAX       Gauge32
    MAX-ACCESS   read-only
    STATUS       current
    DESCRIPTION
        "Cisco UCS equipment:NetworkElementFanStats:speedAvg
        managed object property"
    ::= { cucsEquipmentNetworkElementFanStatsEntry 11 }

cucsEquipmentNetworkElementFanStatsSpeedMax OBJECT-TYPE
    SYNTAX       Gauge32
    MAX-ACCESS   read-only
    STATUS       current
    DESCRIPTION
        "Cisco UCS equipment:NetworkElementFanStats:speedMax
        managed object property"
    ::= { cucsEquipmentNetworkElementFanStatsEntry 12 }

cucsEquipmentNetworkElementFanStatsSpeedMin OBJECT-TYPE
    SYNTAX       Gauge32
    MAX-ACCESS   read-only
    STATUS       current
    DESCRIPTION
        "Cisco UCS equipment:NetworkElementFanStats:speedMin
        managed object property"
    ::= { cucsEquipmentNetworkElementFanStatsEntry 13 }

cucsEquipmentNetworkElementFanStatsSuspect OBJECT-TYPE
    SYNTAX       TruthValue
    MAX-ACCESS   read-only
    STATUS       current
    DESCRIPTION
        "Cisco UCS equipment:NetworkElementFanStats:suspect
        managed object property"
    ::= { cucsEquipmentNetworkElementFanStatsEntry 14 }

cucsEquipmentNetworkElementFanStatsThresholded OBJECT-TYPE
    SYNTAX       CucsEquipmentNetworkElementFanStatsThresholded
    MAX-ACCESS   read-only
    STATUS       current
    DESCRIPTION
        "Cisco UCS equipment:NetworkElementFanStats:thresholded
        managed object property"
    ::= { cucsEquipmentNetworkElementFanStatsEntry 15 }

cucsEquipmentNetworkElementFanStatsTimeCollected OBJECT-TYPE
    SYNTAX       DateAndTime
    MAX-ACCESS   read-only
    STATUS       current
    DESCRIPTION
        "Cisco UCS equipment:NetworkElementFanStats:timeCollected
        managed object property"
    ::= { cucsEquipmentNetworkElementFanStatsEntry 16 }

cucsEquipmentNetworkElementFanStatsUpdate OBJECT-TYPE
    SYNTAX       Gauge32
    MAX-ACCESS   read-only
    STATUS       current
    DESCRIPTION
        "Cisco UCS equipment:NetworkElementFanStats:update
        managed object property"
    ::= { cucsEquipmentNetworkElementFanStatsEntry 17 }

cucsEquipmentNetworkElementFanStatsHistTable OBJECT-TYPE
    SYNTAX           SEQUENCE OF CucsEquipmentNetworkElementFanStatsHistEntry
    MAX-ACCESS       not-accessible
    STATUS           current
    DESCRIPTION
        "Cisco UCS equipment:NetworkElementFanStatsHist
        managed object table"
    ::= { cucsEquipmentObjects 87 }

cucsEquipmentNetworkElementFanStatsHistEntry OBJECT-TYPE
    SYNTAX           CucsEquipmentNetworkElementFanStatsHistEntry
    MAX-ACCESS       not-accessible
    STATUS           current
    DESCRIPTION
        "Entry for the cucsEquipmentNetworkElementFanStatsHistTable table."
    INDEX { cucsEquipmentNetworkElementFanStatsHistInstanceId }
    ::= { cucsEquipmentNetworkElementFanStatsHistTable 1 }

CucsEquipmentNetworkElementFanStatsHistEntry ::= SEQUENCE {
    cucsEquipmentNetworkElementFanStatsHistInstanceId                CucsManagedObjectId,
    cucsEquipmentNetworkElementFanStatsHistDn                        CucsManagedObjectDn,
    cucsEquipmentNetworkElementFanStatsHistRn                        SnmpAdminString,
    cucsEquipmentNetworkElementFanStatsHistDrivePercentage           Gauge32,
    cucsEquipmentNetworkElementFanStatsHistDrivePercentageAvg        Gauge32,
    cucsEquipmentNetworkElementFanStatsHistDrivePercentageMax        Gauge32,
    cucsEquipmentNetworkElementFanStatsHistDrivePercentageMin        Gauge32,
    cucsEquipmentNetworkElementFanStatsHistId                        Unsigned64,
    cucsEquipmentNetworkElementFanStatsHistMostRecent                TruthValue,
    cucsEquipmentNetworkElementFanStatsHistSpeed                     Gauge32,
    cucsEquipmentNetworkElementFanStatsHistSpeedAvg                  Gauge32,
    cucsEquipmentNetworkElementFanStatsHistSpeedMax                  Gauge32,
    cucsEquipmentNetworkElementFanStatsHistSpeedMin                  Gauge32,
    cucsEquipmentNetworkElementFanStatsHistSuspect                   TruthValue,
    cucsEquipmentNetworkElementFanStatsHistThresholded               CucsEquipmentNetworkElementFanStatsHistThresholded,
    cucsEquipmentNetworkElementFanStatsHistTimeCollected             DateAndTime
}

cucsEquipmentNetworkElementFanStatsHistInstanceId OBJECT-TYPE
    SYNTAX       CucsManagedObjectId
    MAX-ACCESS   not-accessible
    STATUS       current
    DESCRIPTION
        "Instance identifier of the managed object."
    ::= { cucsEquipmentNetworkElementFanStatsHistEntry 1 }

cucsEquipmentNetworkElementFanStatsHistDn OBJECT-TYPE
    SYNTAX       CucsManagedObjectDn
    MAX-ACCESS   read-only
    STATUS       current
    DESCRIPTION
        "Cisco UCS equipment:NetworkElementFanStatsHist:dn
        managed object property"
    ::= { cucsEquipmentNetworkElementFanStatsHistEntry 2 }

cucsEquipmentNetworkElementFanStatsHistRn OBJECT-TYPE
    SYNTAX       SnmpAdminString
    MAX-ACCESS   read-only
    STATUS       current
    DESCRIPTION
        "Cisco UCS equipment:NetworkElementFanStatsHist:rn
        managed object property"
    ::= { cucsEquipmentNetworkElementFanStatsHistEntry 3 }

cucsEquipmentNetworkElementFanStatsHistDrivePercentage OBJECT-TYPE
    SYNTAX       Gauge32
    MAX-ACCESS   read-only
    STATUS       current
    DESCRIPTION
        "Cisco UCS equipment:NetworkElementFanStatsHist:drivePercentage
        managed object property"
    ::= { cucsEquipmentNetworkElementFanStatsHistEntry 4 }

cucsEquipmentNetworkElementFanStatsHistDrivePercentageAvg OBJECT-TYPE
    SYNTAX       Gauge32
    MAX-ACCESS   read-only
    STATUS       current
    DESCRIPTION
        "Cisco UCS equipment:NetworkElementFanStatsHist:drivePercentageAvg
         managed object property"
    ::= { cucsEquipmentNetworkElementFanStatsHistEntry 5 }

cucsEquipmentNetworkElementFanStatsHistDrivePercentageMax OBJECT-TYPE
    SYNTAX       Gauge32
    MAX-ACCESS   read-only
    STATUS       current
    DESCRIPTION
        "Cisco UCS equipment:NetworkElementFanStatsHist:drivePercentageMax
         managed object property"
    ::= { cucsEquipmentNetworkElementFanStatsHistEntry 6 }

cucsEquipmentNetworkElementFanStatsHistDrivePercentageMin OBJECT-TYPE
    SYNTAX       Gauge32
    MAX-ACCESS   read-only
    STATUS       current
    DESCRIPTION
        "Cisco UCS equipment:NetworkElementFanStatsHist:drivePercentageMin
         managed object property"
    ::= { cucsEquipmentNetworkElementFanStatsHistEntry 7 }

cucsEquipmentNetworkElementFanStatsHistId OBJECT-TYPE
    SYNTAX       Unsigned64
    MAX-ACCESS   read-only
    STATUS       current
    DESCRIPTION
        "Cisco UCS equipment:NetworkElementFanStatsHist:id
        managed object property"
    ::= { cucsEquipmentNetworkElementFanStatsHistEntry 8 }

cucsEquipmentNetworkElementFanStatsHistMostRecent OBJECT-TYPE
    SYNTAX       TruthValue
    MAX-ACCESS   read-only
    STATUS       current
    DESCRIPTION
        "Cisco UCS equipment:NetworkElementFanStatsHist:mostRecent
        managed object property"
    ::= { cucsEquipmentNetworkElementFanStatsHistEntry 9 }

cucsEquipmentNetworkElementFanStatsHistSpeed OBJECT-TYPE
    SYNTAX       Gauge32
    MAX-ACCESS   read-only
    STATUS       current
    DESCRIPTION
        "Cisco UCS equipment:NetworkElementFanStatsHist:speed
        managed object property"
    ::= { cucsEquipmentNetworkElementFanStatsHistEntry 10 }

cucsEquipmentNetworkElementFanStatsHistSpeedAvg OBJECT-TYPE
    SYNTAX       Gauge32
    MAX-ACCESS   read-only
    STATUS       current
    DESCRIPTION
        "Cisco UCS equipment:NetworkElementFanStatsHist:speedAvg
        managed object property"
    ::= { cucsEquipmentNetworkElementFanStatsHistEntry 11 }

cucsEquipmentNetworkElementFanStatsHistSpeedMax OBJECT-TYPE
    SYNTAX       Gauge32
    MAX-ACCESS   read-only
    STATUS       current
    DESCRIPTION
        "Cisco UCS equipment:NetworkElementFanStatsHist:speedMax
        managed object property"
    ::= { cucsEquipmentNetworkElementFanStatsHistEntry 12 }

cucsEquipmentNetworkElementFanStatsHistSpeedMin OBJECT-TYPE
    SYNTAX       Gauge32
    MAX-ACCESS   read-only
    STATUS       current
    DESCRIPTION
        "Cisco UCS equipment:NetworkElementFanStatsHist:speedMin
        managed object property"
    ::= { cucsEquipmentNetworkElementFanStatsHistEntry 13 }

cucsEquipmentNetworkElementFanStatsHistSuspect OBJECT-TYPE
    SYNTAX       TruthValue
    MAX-ACCESS   read-only
    STATUS       current
    DESCRIPTION
        "Cisco UCS equipment:NetworkElementFanStatsHist:suspect
        managed object property"
    ::= { cucsEquipmentNetworkElementFanStatsHistEntry 14 }

cucsEquipmentNetworkElementFanStatsHistThresholded OBJECT-TYPE
    SYNTAX       CucsEquipmentNetworkElementFanStatsHistThresholded
    MAX-ACCESS   read-only
    STATUS       current
    DESCRIPTION
        "Cisco UCS equipment:NetworkElementFanStatsHist:thresholded
        managed object property"
    ::= { cucsEquipmentNetworkElementFanStatsHistEntry 15 }

cucsEquipmentNetworkElementFanStatsHistTimeCollected OBJECT-TYPE
    SYNTAX       DateAndTime
    MAX-ACCESS   read-only
    STATUS       current
    DESCRIPTION
        "Cisco UCS equipment:NetworkElementFanStatsHist:timeCollected
        managed object property"
    ::= { cucsEquipmentNetworkElementFanStatsHistEntry 16 }

cucsEquipmentNonCopperPassiveCapTable OBJECT-TYPE
    SYNTAX           SEQUENCE OF CucsEquipmentNonCopperPassiveCapEntry
    MAX-ACCESS       not-accessible
    STATUS           current
    DESCRIPTION
        "Cisco UCS equipment:NonCopperPassiveCap managed object table"
    ::= { cucsEquipmentObjects 166 }

cucsEquipmentNonCopperPassiveCapEntry OBJECT-TYPE
    SYNTAX           CucsEquipmentNonCopperPassiveCapEntry
    MAX-ACCESS       not-accessible
    STATUS           current
    DESCRIPTION
        "Entry for the cucsEquipmentNonCopperPassiveCapTable table."
    INDEX { cucsEquipmentNonCopperPassiveCapInstanceId }
    ::= { cucsEquipmentNonCopperPassiveCapTable 1 }

CucsEquipmentNonCopperPassiveCapEntry ::= SEQUENCE {
    cucsEquipmentNonCopperPassiveCapInstanceId                       CucsManagedObjectId,
    cucsEquipmentNonCopperPassiveCapDn                               CucsManagedObjectDn,
    cucsEquipmentNonCopperPassiveCapRn                               SnmpAdminString,
    cucsEquipmentNonCopperPassiveCapDescr                            SnmpAdminString,
    cucsEquipmentNonCopperPassiveCapIntId                            SnmpAdminString,
    cucsEquipmentNonCopperPassiveCapName                             SnmpAdminString,
    cucsEquipmentNonCopperPassiveCapPhyPortBitmask                   CucsEquipmentPortBitmask,
    cucsEquipmentNonCopperPassiveCapPolicyLevel                      Gauge32,
    cucsEquipmentNonCopperPassiveCapPolicyOwner                      CucsPolicyPolicyOwner
}

cucsEquipmentNonCopperPassiveCapInstanceId OBJECT-TYPE
    SYNTAX       CucsManagedObjectId
    MAX-ACCESS   not-accessible
    STATUS       current
    DESCRIPTION
        "Instance identifier of the managed object."
    ::= { cucsEquipmentNonCopperPassiveCapEntry 1 }

cucsEquipmentNonCopperPassiveCapDn OBJECT-TYPE
    SYNTAX       CucsManagedObjectDn
    MAX-ACCESS   read-only
    STATUS       current
    DESCRIPTION
        "Cisco UCS equipment:NonCopperPassiveCap:dn managed
        object property"
    ::= { cucsEquipmentNonCopperPassiveCapEntry 2 }

cucsEquipmentNonCopperPassiveCapRn OBJECT-TYPE
    SYNTAX       SnmpAdminString
    MAX-ACCESS   read-only
    STATUS       current
    DESCRIPTION
        "Cisco UCS equipment:NonCopperPassiveCap:rn managed
        object property"
    ::= { cucsEquipmentNonCopperPassiveCapEntry 3 }

cucsEquipmentNonCopperPassiveCapDescr OBJECT-TYPE
    SYNTAX       SnmpAdminString
    MAX-ACCESS   read-only
    STATUS       current
    DESCRIPTION
        "Cisco UCS equipment:NonCopperPassiveCap:descr
        managed object property"
    ::= { cucsEquipmentNonCopperPassiveCapEntry 4 }

cucsEquipmentNonCopperPassiveCapIntId OBJECT-TYPE
    SYNTAX       SnmpAdminString
    MAX-ACCESS   read-only
    STATUS       current
    DESCRIPTION
        "Cisco UCS equipment:NonCopperPassiveCap:intId
        managed object property"
    ::= { cucsEquipmentNonCopperPassiveCapEntry 5 }

cucsEquipmentNonCopperPassiveCapName OBJECT-TYPE
    SYNTAX       SnmpAdminString
    MAX-ACCESS   read-only
    STATUS       current
    DESCRIPTION
        "Cisco UCS equipment:NonCopperPassiveCap:name managed
        object property"
    ::= { cucsEquipmentNonCopperPassiveCapEntry 6 }

cucsEquipmentNonCopperPassiveCapPhyPortBitmask OBJECT-TYPE
    SYNTAX       CucsEquipmentPortBitmask
    MAX-ACCESS   read-only
    STATUS       current
    DESCRIPTION
        "Cisco UCS equipment:NonCopperPassiveCap:phyPortBitmask
        managed object property"
    ::= { cucsEquipmentNonCopperPassiveCapEntry 7 }

cucsEquipmentNonCopperPassiveCapPolicyLevel OBJECT-TYPE
    SYNTAX       Gauge32
    MAX-ACCESS   read-only
    STATUS       current
    DESCRIPTION
        "Cisco UCS equipment:NonCopperPassiveCap:policyLevel
        managed object property"
    ::= { cucsEquipmentNonCopperPassiveCapEntry 8 }

cucsEquipmentNonCopperPassiveCapPolicyOwner OBJECT-TYPE
    SYNTAX       CucsPolicyPolicyOwner
    MAX-ACCESS   read-only
    STATUS       current
    DESCRIPTION
        "Cisco UCS equipment:NonCopperPassiveCap:policyOwner
        managed object property"
    ::= { cucsEquipmentNonCopperPassiveCapEntry 9 }

cucsEquipmentNvmeDefTable OBJECT-TYPE
    SYNTAX           SEQUENCE OF CucsEquipmentNvmeDefEntry
    MAX-ACCESS       not-accessible
    STATUS           current
    DESCRIPTION
        "Cisco UCS equipment:NvmeDef managed object table"
    ::= { cucsEquipmentObjects 230 }

cucsEquipmentNvmeDefEntry OBJECT-TYPE
    SYNTAX           CucsEquipmentNvmeDefEntry
    MAX-ACCESS       not-accessible
    STATUS           current
    DESCRIPTION
        "Entry for the cucsEquipmentNvmeDefTable table."
    INDEX { cucsEquipmentNvmeDefInstanceId }
    ::= { cucsEquipmentNvmeDefTable 1 }

CucsEquipmentNvmeDefEntry ::= SEQUENCE {
    cucsEquipmentNvmeDefInstanceId                                   CucsManagedObjectId,
    cucsEquipmentNvmeDefDn                                           CucsManagedObjectDn,
    cucsEquipmentNvmeDefRn                                           SnmpAdminString,
    cucsEquipmentNvmeDefDescr                                        SnmpAdminString,
    cucsEquipmentNvmeDefFrontDiskSlots                               Gauge32,
    cucsEquipmentNvmeDefIntId                                        SnmpAdminString,
    cucsEquipmentNvmeDefName                                         SnmpAdminString,
    cucsEquipmentNvmeDefPciSlots                                     Gauge32,
    cucsEquipmentNvmeDefPolicyLevel                                  Gauge32,
    cucsEquipmentNvmeDefPolicyOwner                                  CucsPolicyPolicyOwner,
    cucsEquipmentNvmeDefRearDiskSlots                                Gauge32
}

cucsEquipmentNvmeDefInstanceId OBJECT-TYPE
    SYNTAX       CucsManagedObjectId
    MAX-ACCESS   not-accessible
    STATUS       current
    DESCRIPTION
        "Instance identifier of the managed object."
    ::= { cucsEquipmentNvmeDefEntry 1 }

cucsEquipmentNvmeDefDn OBJECT-TYPE
    SYNTAX       CucsManagedObjectDn
    MAX-ACCESS   read-only
    STATUS       current
    DESCRIPTION
        "Cisco UCS equipment:NvmeDef:dn managed object property"
    ::= { cucsEquipmentNvmeDefEntry 2 }

cucsEquipmentNvmeDefRn OBJECT-TYPE
    SYNTAX       SnmpAdminString
    MAX-ACCESS   read-only
    STATUS       current
    DESCRIPTION
        "Cisco UCS equipment:NvmeDef:rn managed object property"
    ::= { cucsEquipmentNvmeDefEntry 3 }

cucsEquipmentNvmeDefDescr OBJECT-TYPE
    SYNTAX       SnmpAdminString
    MAX-ACCESS   read-only
    STATUS       current
    DESCRIPTION
        "Cisco UCS equipment:NvmeDef:descr managed object property"
    ::= { cucsEquipmentNvmeDefEntry 4 }

cucsEquipmentNvmeDefFrontDiskSlots OBJECT-TYPE
    SYNTAX       Gauge32
    MAX-ACCESS   read-only
    STATUS       current
    DESCRIPTION
        "Cisco UCS equipment:NvmeDef:frontDiskSlots managed
        object property"
    ::= { cucsEquipmentNvmeDefEntry 5 }

cucsEquipmentNvmeDefIntId OBJECT-TYPE
    SYNTAX       SnmpAdminString
    MAX-ACCESS   read-only
    STATUS       current
    DESCRIPTION
        "Cisco UCS equipment:NvmeDef:intId managed object property"
    ::= { cucsEquipmentNvmeDefEntry 6 }

cucsEquipmentNvmeDefName OBJECT-TYPE
    SYNTAX       SnmpAdminString
    MAX-ACCESS   read-only
    STATUS       current
    DESCRIPTION
        "Cisco UCS equipment:NvmeDef:name managed object property"
    ::= { cucsEquipmentNvmeDefEntry 7 }

cucsEquipmentNvmeDefPciSlots OBJECT-TYPE
    SYNTAX       Gauge32
    MAX-ACCESS   read-only
    STATUS       current
    DESCRIPTION
        "Cisco UCS equipment:NvmeDef:pciSlots managed object property"
    ::= { cucsEquipmentNvmeDefEntry 8 }

cucsEquipmentNvmeDefPolicyLevel OBJECT-TYPE
    SYNTAX       Gauge32
    MAX-ACCESS   read-only
    STATUS       current
    DESCRIPTION
        "Cisco UCS equipment:NvmeDef:policyLevel managed object property"
    ::= { cucsEquipmentNvmeDefEntry 9 }

cucsEquipmentNvmeDefPolicyOwner OBJECT-TYPE
    SYNTAX       CucsPolicyPolicyOwner
    MAX-ACCESS   read-only
    STATUS       current
    DESCRIPTION
        "Cisco UCS equipment:NvmeDef:policyOwner managed object property"
    ::= { cucsEquipmentNvmeDefEntry 10 }

cucsEquipmentNvmeDefRearDiskSlots OBJECT-TYPE
    SYNTAX       Gauge32
    MAX-ACCESS   read-only
    STATUS       current
    DESCRIPTION
        "Cisco UCS equipment:NvmeDef:rearDiskSlots managed
        object property"
    ::= { cucsEquipmentNvmeDefEntry 11 }

cucsEquipmentOnboardDeviceDefTable OBJECT-TYPE
    SYNTAX           SEQUENCE OF CucsEquipmentOnboardDeviceDefEntry
    MAX-ACCESS       not-accessible
    STATUS           current
    DESCRIPTION
        "Cisco UCS equipment:OnboardDeviceDef managed object table"
    ::= { cucsEquipmentObjects 175 }

cucsEquipmentOnboardDeviceDefEntry OBJECT-TYPE
    SYNTAX           CucsEquipmentOnboardDeviceDefEntry
    MAX-ACCESS       not-accessible
    STATUS           current
    DESCRIPTION
        "Entry for the cucsEquipmentOnboardDeviceDefTable table."
    INDEX { cucsEquipmentOnboardDeviceDefInstanceId }
    ::= { cucsEquipmentOnboardDeviceDefTable 1 }

CucsEquipmentOnboardDeviceDefEntry ::= SEQUENCE {
    cucsEquipmentOnboardDeviceDefInstanceId                          CucsManagedObjectId,
    cucsEquipmentOnboardDeviceDefDn                                  CucsManagedObjectDn,
    cucsEquipmentOnboardDeviceDefRn                                  SnmpAdminString,
    cucsEquipmentOnboardDeviceDefDescr                               SnmpAdminString,
    cucsEquipmentOnboardDeviceDefDevice                              SnmpAdminString,
    cucsEquipmentOnboardDeviceDefIntId                               SnmpAdminString,
    cucsEquipmentOnboardDeviceDefName                                SnmpAdminString,
    cucsEquipmentOnboardDeviceDefPolicyLevel                         Gauge32,
    cucsEquipmentOnboardDeviceDefPolicyOwner                         CucsPolicyPolicyOwner
}

cucsEquipmentOnboardDeviceDefInstanceId OBJECT-TYPE
    SYNTAX       CucsManagedObjectId
    MAX-ACCESS   not-accessible
    STATUS       current
    DESCRIPTION
        "Instance identifier of the managed object."
    ::= { cucsEquipmentOnboardDeviceDefEntry 1 }

cucsEquipmentOnboardDeviceDefDn OBJECT-TYPE
    SYNTAX       CucsManagedObjectDn
    MAX-ACCESS   read-only
    STATUS       current
    DESCRIPTION
        "Cisco UCS equipment:OnboardDeviceDef:dn managed object property"
    ::= { cucsEquipmentOnboardDeviceDefEntry 2 }

cucsEquipmentOnboardDeviceDefRn OBJECT-TYPE
    SYNTAX       SnmpAdminString
    MAX-ACCESS   read-only
    STATUS       current
    DESCRIPTION
        "Cisco UCS equipment:OnboardDeviceDef:rn managed object property"
    ::= { cucsEquipmentOnboardDeviceDefEntry 3 }

cucsEquipmentOnboardDeviceDefDescr OBJECT-TYPE
    SYNTAX       SnmpAdminString
    MAX-ACCESS   read-only
    STATUS       current
    DESCRIPTION
        "Cisco UCS equipment:OnboardDeviceDef:descr managed
        object property"
    ::= { cucsEquipmentOnboardDeviceDefEntry 4 }

cucsEquipmentOnboardDeviceDefDevice OBJECT-TYPE
    SYNTAX       SnmpAdminString
    MAX-ACCESS   read-only
    STATUS       current
    DESCRIPTION
        "Cisco UCS equipment:OnboardDeviceDef:device managed
        object property"
    ::= { cucsEquipmentOnboardDeviceDefEntry 5 }

cucsEquipmentOnboardDeviceDefIntId OBJECT-TYPE
    SYNTAX       SnmpAdminString
    MAX-ACCESS   read-only
    STATUS       current
    DESCRIPTION
        "Cisco UCS equipment:OnboardDeviceDef:intId managed
        object property"
    ::= { cucsEquipmentOnboardDeviceDefEntry 6 }

cucsEquipmentOnboardDeviceDefName OBJECT-TYPE
    SYNTAX       SnmpAdminString
    MAX-ACCESS   read-only
    STATUS       current
    DESCRIPTION
        "Cisco UCS equipment:OnboardDeviceDef:name managed
        object property"
    ::= { cucsEquipmentOnboardDeviceDefEntry 7 }

cucsEquipmentOnboardDeviceDefPolicyLevel OBJECT-TYPE
    SYNTAX       Gauge32
    MAX-ACCESS   read-only
    STATUS       current
    DESCRIPTION
        "Cisco UCS equipment:OnboardDeviceDef:policyLevel
        managed object property"
    ::= { cucsEquipmentOnboardDeviceDefEntry 8 }

cucsEquipmentOnboardDeviceDefPolicyOwner OBJECT-TYPE
    SYNTAX       CucsPolicyPolicyOwner
    MAX-ACCESS   read-only
    STATUS       current
    DESCRIPTION
        "Cisco UCS equipment:OnboardDeviceDef:policyOwner
        managed object property"
    ::= { cucsEquipmentOnboardDeviceDefEntry 9 }

cucsEquipmentPOSTTable OBJECT-TYPE
    SYNTAX           SEQUENCE OF CucsEquipmentPOSTEntry
    MAX-ACCESS       not-accessible
    STATUS           current
    DESCRIPTION
        "Cisco UCS equipment:POST managed object table"
    ::= { cucsEquipmentObjects 47 }

cucsEquipmentPOSTEntry OBJECT-TYPE
    SYNTAX           CucsEquipmentPOSTEntry
    MAX-ACCESS       not-accessible
    STATUS           current
    DESCRIPTION
        "Entry for the cucsEquipmentPOSTTable table."
    INDEX { cucsEquipmentPOSTInstanceId }
    ::= { cucsEquipmentPOSTTable 1 }

CucsEquipmentPOSTEntry ::= SEQUENCE {
    cucsEquipmentPOSTInstanceId                                      CucsManagedObjectId,
    cucsEquipmentPOSTDn                                              CucsManagedObjectDn,
    cucsEquipmentPOSTRn                                              SnmpAdminString,
    cucsEquipmentPOSTCode                                            SnmpAdminString,
    cucsEquipmentPOSTCreated                                         DateAndTime,
    cucsEquipmentPOSTDescr                                           SnmpAdminString,
    cucsEquipmentPOSTGlobalId                                        SnmpAdminString,
    cucsEquipmentPOSTLocalId                                         SnmpAdminString,
    cucsEquipmentPOSTMethod                                          CucsEquipmentMethod,
    cucsEquipmentPOSTName                                            SnmpAdminString,
    cucsEquipmentPOSTRecoverable                                     CucsEquipmentPOSTRecoverability,
    cucsEquipmentPOSTRecoveryAction                                  SnmpAdminString,
    cucsEquipmentPOSTSeverity                                        CucsConditionSeverity,
    cucsEquipmentPOSTType                                            SnmpAdminString,
    cucsEquipmentPOSTValue                                           Gauge32
}

cucsEquipmentPOSTInstanceId OBJECT-TYPE
    SYNTAX       CucsManagedObjectId
    MAX-ACCESS   not-accessible
    STATUS       current
    DESCRIPTION
        "Instance identifier of the managed object."
    ::= { cucsEquipmentPOSTEntry 1 }

cucsEquipmentPOSTDn OBJECT-TYPE
    SYNTAX       CucsManagedObjectDn
    MAX-ACCESS   read-only
    STATUS       current
    DESCRIPTION
        "Cisco UCS equipment:POST:dn managed object property"
    ::= { cucsEquipmentPOSTEntry 2 }

cucsEquipmentPOSTRn OBJECT-TYPE
    SYNTAX       SnmpAdminString
    MAX-ACCESS   read-only
    STATUS       current
    DESCRIPTION
        "Cisco UCS equipment:POST:rn managed object property"
    ::= { cucsEquipmentPOSTEntry 3 }

cucsEquipmentPOSTCode OBJECT-TYPE
    SYNTAX       SnmpAdminString
    MAX-ACCESS   read-only
    STATUS       current
    DESCRIPTION
        "Cisco UCS equipment:POST:code managed object property"
    ::= { cucsEquipmentPOSTEntry 4 }

cucsEquipmentPOSTCreated OBJECT-TYPE
    SYNTAX       DateAndTime
    MAX-ACCESS   read-only
    STATUS       current
    DESCRIPTION
        "Cisco UCS equipment:POST:created managed object property"
    ::= { cucsEquipmentPOSTEntry 5 }

cucsEquipmentPOSTDescr OBJECT-TYPE
    SYNTAX       SnmpAdminString
    MAX-ACCESS   read-only
    STATUS       current
    DESCRIPTION
        "Cisco UCS equipment:POST:descr managed object property"
    ::= { cucsEquipmentPOSTEntry 6 }

cucsEquipmentPOSTGlobalId OBJECT-TYPE
    SYNTAX       SnmpAdminString
    MAX-ACCESS   read-only
    STATUS       current
    DESCRIPTION
        "Cisco UCS equipment:POST:globalId managed object property"
    ::= { cucsEquipmentPOSTEntry 7 }

cucsEquipmentPOSTLocalId OBJECT-TYPE
    SYNTAX       SnmpAdminString
    MAX-ACCESS   read-only
    STATUS       current
    DESCRIPTION
        "Cisco UCS equipment:POST:localId managed object property"
    ::= { cucsEquipmentPOSTEntry 8 }

cucsEquipmentPOSTMethod OBJECT-TYPE
    SYNTAX       CucsEquipmentMethod
    MAX-ACCESS   read-only
    STATUS       current
    DESCRIPTION
        "Cisco UCS equipment:POST:method managed object property"
    ::= { cucsEquipmentPOSTEntry 9 }

cucsEquipmentPOSTName OBJECT-TYPE
    SYNTAX       SnmpAdminString
    MAX-ACCESS   read-only
    STATUS       current
    DESCRIPTION
        "Cisco UCS equipment:POST:name managed object property"
    ::= { cucsEquipmentPOSTEntry 10 }

cucsEquipmentPOSTRecoverable OBJECT-TYPE
    SYNTAX       CucsEquipmentPOSTRecoverability
    MAX-ACCESS   read-only
    STATUS       current
    DESCRIPTION
        "Cisco UCS equipment:POST:recoverable managed object property"
    ::= { cucsEquipmentPOSTEntry 11 }

cucsEquipmentPOSTRecoveryAction OBJECT-TYPE
    SYNTAX       SnmpAdminString
    MAX-ACCESS   read-only
    STATUS       current
    DESCRIPTION
        "Cisco UCS equipment:POST:recoveryAction managed object property"
    ::= { cucsEquipmentPOSTEntry 12 }

cucsEquipmentPOSTSeverity OBJECT-TYPE
    SYNTAX       CucsConditionSeverity
    MAX-ACCESS   read-only
    STATUS       current
    DESCRIPTION
        "Cisco UCS equipment:POST:severity managed object property"
    ::= { cucsEquipmentPOSTEntry 13 }

cucsEquipmentPOSTType OBJECT-TYPE
    SYNTAX       SnmpAdminString
    MAX-ACCESS   read-only
    STATUS       current
    DESCRIPTION
        "Cisco UCS equipment:POST:type managed object property"
    ::= { cucsEquipmentPOSTEntry 14 }

cucsEquipmentPOSTValue OBJECT-TYPE
    SYNTAX       Gauge32
    MAX-ACCESS   read-only
    STATUS       current
    DESCRIPTION
        "Cisco UCS equipment:POST:value managed object property"
    ::= { cucsEquipmentPOSTEntry 15 }

cucsEquipmentPOSTCodeTable OBJECT-TYPE
    SYNTAX           SEQUENCE OF CucsEquipmentPOSTCodeEntry
    MAX-ACCESS       not-accessible
    STATUS           current
    DESCRIPTION
        "Cisco UCS equipment:POSTCode managed object table"
    ::= { cucsEquipmentObjects 48 }

cucsEquipmentPOSTCodeEntry OBJECT-TYPE
    SYNTAX           CucsEquipmentPOSTCodeEntry
    MAX-ACCESS       not-accessible
    STATUS           current
    DESCRIPTION
        "Entry for the cucsEquipmentPOSTCodeTable table."
    INDEX { cucsEquipmentPOSTCodeInstanceId }
    ::= { cucsEquipmentPOSTCodeTable 1 }

CucsEquipmentPOSTCodeEntry ::= SEQUENCE {
    cucsEquipmentPOSTCodeInstanceId                                  CucsManagedObjectId,
    cucsEquipmentPOSTCodeDn                                          CucsManagedObjectDn,
    cucsEquipmentPOSTCodeRn                                          SnmpAdminString,
    cucsEquipmentPOSTCodeCode                                        SnmpAdminString,
    cucsEquipmentPOSTCodeDescr                                       SnmpAdminString,
    cucsEquipmentPOSTCodeGlobalId                                    SnmpAdminString,
    cucsEquipmentPOSTCodeLocalId                                     SnmpAdminString,
    cucsEquipmentPOSTCodeMethod                                      CucsEquipmentMethod,
    cucsEquipmentPOSTCodeName                                        SnmpAdminString,
    cucsEquipmentPOSTCodeRecoverable                                 CucsEquipmentPOSTRecoverability,
    cucsEquipmentPOSTCodeRecoveryAction                              SnmpAdminString,
    cucsEquipmentPOSTCodeSeverity                                    CucsConditionSeverity
}

cucsEquipmentPOSTCodeInstanceId OBJECT-TYPE
    SYNTAX       CucsManagedObjectId
    MAX-ACCESS   not-accessible
    STATUS       current
    DESCRIPTION
        "Instance identifier of the managed object."
    ::= { cucsEquipmentPOSTCodeEntry 1 }

cucsEquipmentPOSTCodeDn OBJECT-TYPE
    SYNTAX       CucsManagedObjectDn
    MAX-ACCESS   read-only
    STATUS       current
    DESCRIPTION
        "Cisco UCS equipment:POSTCode:dn managed object property"
    ::= { cucsEquipmentPOSTCodeEntry 2 }

cucsEquipmentPOSTCodeRn OBJECT-TYPE
    SYNTAX       SnmpAdminString
    MAX-ACCESS   read-only
    STATUS       current
    DESCRIPTION
        "Cisco UCS equipment:POSTCode:rn managed object property"
    ::= { cucsEquipmentPOSTCodeEntry 3 }

cucsEquipmentPOSTCodeCode OBJECT-TYPE
    SYNTAX       SnmpAdminString
    MAX-ACCESS   read-only
    STATUS       current
    DESCRIPTION
        "Cisco UCS equipment:POSTCode:code managed object property"
    ::= { cucsEquipmentPOSTCodeEntry 4 }

cucsEquipmentPOSTCodeDescr OBJECT-TYPE
    SYNTAX       SnmpAdminString
    MAX-ACCESS   read-only
    STATUS       current
    DESCRIPTION
        "Cisco UCS equipment:POSTCode:descr managed object property"
    ::= { cucsEquipmentPOSTCodeEntry 5 }

cucsEquipmentPOSTCodeGlobalId OBJECT-TYPE
    SYNTAX       SnmpAdminString
    MAX-ACCESS   read-only
    STATUS       current
    DESCRIPTION
        "Cisco UCS equipment:POSTCode:globalId managed object property"
    ::= { cucsEquipmentPOSTCodeEntry 6 }

cucsEquipmentPOSTCodeLocalId OBJECT-TYPE
    SYNTAX       SnmpAdminString
    MAX-ACCESS   read-only
    STATUS       current
    DESCRIPTION
        "Cisco UCS equipment:POSTCode:localId managed object property"
    ::= { cucsEquipmentPOSTCodeEntry 7 }

cucsEquipmentPOSTCodeMethod OBJECT-TYPE
    SYNTAX       CucsEquipmentMethod
    MAX-ACCESS   read-only
    STATUS       current
    DESCRIPTION
        "Cisco UCS equipment:POSTCode:method managed object property"
    ::= { cucsEquipmentPOSTCodeEntry 8 }

cucsEquipmentPOSTCodeName OBJECT-TYPE
    SYNTAX       SnmpAdminString
    MAX-ACCESS   read-only
    STATUS       current
    DESCRIPTION
        "Cisco UCS equipment:POSTCode:name managed object property"
    ::= { cucsEquipmentPOSTCodeEntry 9 }

cucsEquipmentPOSTCodeRecoverable OBJECT-TYPE
    SYNTAX       CucsEquipmentPOSTRecoverability
    MAX-ACCESS   read-only
    STATUS       current
    DESCRIPTION
        "Cisco UCS equipment:POSTCode:recoverable managed object property"
    ::= { cucsEquipmentPOSTCodeEntry 10 }

cucsEquipmentPOSTCodeRecoveryAction OBJECT-TYPE
    SYNTAX       SnmpAdminString
    MAX-ACCESS   read-only
    STATUS       current
    DESCRIPTION
        "Cisco UCS equipment:POSTCode:recoveryAction managed
        object property"
    ::= { cucsEquipmentPOSTCodeEntry 11 }

cucsEquipmentPOSTCodeSeverity OBJECT-TYPE
    SYNTAX       CucsConditionSeverity
    MAX-ACCESS   read-only
    STATUS       current
    DESCRIPTION
        "Cisco UCS equipment:POSTCode:severity managed object property"
    ::= { cucsEquipmentPOSTCodeEntry 12 }

cucsEquipmentPOSTCodeReporterTable OBJECT-TYPE
    SYNTAX           SEQUENCE OF CucsEquipmentPOSTCodeReporterEntry
    MAX-ACCESS       not-accessible
    STATUS           current
    DESCRIPTION
        "Cisco UCS equipment:POSTCodeReporter managed object table"
    ::= { cucsEquipmentObjects 49 }

cucsEquipmentPOSTCodeReporterEntry OBJECT-TYPE
    SYNTAX           CucsEquipmentPOSTCodeReporterEntry
    MAX-ACCESS       not-accessible
    STATUS           current
    DESCRIPTION
        "Entry for the cucsEquipmentPOSTCodeReporterTable table."
    INDEX { cucsEquipmentPOSTCodeReporterInstanceId }
    ::= { cucsEquipmentPOSTCodeReporterTable 1 }

CucsEquipmentPOSTCodeReporterEntry ::= SEQUENCE {
    cucsEquipmentPOSTCodeReporterInstanceId                          CucsManagedObjectId,
    cucsEquipmentPOSTCodeReporterDn                                  CucsManagedObjectDn,
    cucsEquipmentPOSTCodeReporterRn                                  SnmpAdminString,
    cucsEquipmentPOSTCodeReporterModel                               SnmpAdminString,
    cucsEquipmentPOSTCodeReporterRevision                            SnmpAdminString,
    cucsEquipmentPOSTCodeReporterSerial                              SnmpAdminString,
    cucsEquipmentPOSTCodeReporterType                                SnmpAdminString,
    cucsEquipmentPOSTCodeReporterVendor                              SnmpAdminString,
    cucsEquipmentPOSTCodeReporterBaseContainer                       SnmpAdminString,
    cucsEquipmentPOSTCodeReporterName                                SnmpAdminString
}

cucsEquipmentPOSTCodeReporterInstanceId OBJECT-TYPE
    SYNTAX       CucsManagedObjectId
    MAX-ACCESS   not-accessible
    STATUS       current
    DESCRIPTION
        "Instance identifier of the managed object."
    ::= { cucsEquipmentPOSTCodeReporterEntry 1 }

cucsEquipmentPOSTCodeReporterDn OBJECT-TYPE
    SYNTAX       CucsManagedObjectDn
    MAX-ACCESS   read-only
    STATUS       current
    DESCRIPTION
        "Cisco UCS equipment:POSTCodeReporter:dn managed object property"
    ::= { cucsEquipmentPOSTCodeReporterEntry 2 }

cucsEquipmentPOSTCodeReporterRn OBJECT-TYPE
    SYNTAX       SnmpAdminString
    MAX-ACCESS   read-only
    STATUS       current
    DESCRIPTION
        "Cisco UCS equipment:POSTCodeReporter:rn managed object property"
    ::= { cucsEquipmentPOSTCodeReporterEntry 3 }

cucsEquipmentPOSTCodeReporterModel OBJECT-TYPE
    SYNTAX       SnmpAdminString
    MAX-ACCESS   read-only
    STATUS       current
    DESCRIPTION
        "Cisco UCS equipment:POSTCodeReporter:model managed
        object property"
    ::= { cucsEquipmentPOSTCodeReporterEntry 4 }

cucsEquipmentPOSTCodeReporterRevision OBJECT-TYPE
    SYNTAX       SnmpAdminString
    MAX-ACCESS   read-only
    STATUS       current
    DESCRIPTION
        "Cisco UCS equipment:POSTCodeReporter:revision
        managed object property"
    ::= { cucsEquipmentPOSTCodeReporterEntry 5 }

cucsEquipmentPOSTCodeReporterSerial OBJECT-TYPE
    SYNTAX       SnmpAdminString
    MAX-ACCESS   read-only
    STATUS       current
    DESCRIPTION
        "Cisco UCS equipment:POSTCodeReporter:serial managed
        object property"
    ::= { cucsEquipmentPOSTCodeReporterEntry 6 }

cucsEquipmentPOSTCodeReporterType OBJECT-TYPE
    SYNTAX       SnmpAdminString
    MAX-ACCESS   read-only
    STATUS       current
    DESCRIPTION
        "Cisco UCS equipment:POSTCodeReporter:type managed
        object property"
    ::= { cucsEquipmentPOSTCodeReporterEntry 7 }

cucsEquipmentPOSTCodeReporterVendor OBJECT-TYPE
    SYNTAX       SnmpAdminString
    MAX-ACCESS   read-only
    STATUS       current
    DESCRIPTION
        "Cisco UCS equipment:POSTCodeReporter:vendor managed
        object property"
    ::= { cucsEquipmentPOSTCodeReporterEntry 8 }

cucsEquipmentPOSTCodeReporterBaseContainer OBJECT-TYPE
    SYNTAX       SnmpAdminString
    MAX-ACCESS   read-only
    STATUS       current
    DESCRIPTION
        "Cisco UCS equipment:POSTCodeReporter:baseContainer
        managed object property"
    ::= { cucsEquipmentPOSTCodeReporterEntry 9 }

cucsEquipmentPOSTCodeReporterName OBJECT-TYPE
    SYNTAX       SnmpAdminString
    MAX-ACCESS   read-only
    STATUS       current
    DESCRIPTION
        "Cisco UCS equipment:POSTCodeReporter:name managed
        object property"
    ::= { cucsEquipmentPOSTCodeReporterEntry 10 }

cucsEquipmentPOSTCodeTemplateTable OBJECT-TYPE
    SYNTAX           SEQUENCE OF CucsEquipmentPOSTCodeTemplateEntry
    MAX-ACCESS       not-accessible
    STATUS           current
    DESCRIPTION
        "Cisco UCS equipment:POSTCodeTemplate managed object table"
    ::= { cucsEquipmentObjects 74 }

cucsEquipmentPOSTCodeTemplateEntry OBJECT-TYPE
    SYNTAX           CucsEquipmentPOSTCodeTemplateEntry
    MAX-ACCESS       not-accessible
    STATUS           current
    DESCRIPTION
        "Entry for the cucsEquipmentPOSTCodeTemplateTable table."
    INDEX { cucsEquipmentPOSTCodeTemplateInstanceId }
    ::= { cucsEquipmentPOSTCodeTemplateTable 1 }

CucsEquipmentPOSTCodeTemplateEntry ::= SEQUENCE {
    cucsEquipmentPOSTCodeTemplateInstanceId                          CucsManagedObjectId,
    cucsEquipmentPOSTCodeTemplateDn                                  CucsManagedObjectDn,
    cucsEquipmentPOSTCodeTemplateRn                                  SnmpAdminString,
    cucsEquipmentPOSTCodeTemplateBaseContainer                       SnmpAdminString,
    cucsEquipmentPOSTCodeTemplateName                                SnmpAdminString
}

cucsEquipmentPOSTCodeTemplateInstanceId OBJECT-TYPE
    SYNTAX       CucsManagedObjectId
    MAX-ACCESS   not-accessible
    STATUS       current
    DESCRIPTION
        "Instance identifier of the managed object."
    ::= { cucsEquipmentPOSTCodeTemplateEntry 1 }

cucsEquipmentPOSTCodeTemplateDn OBJECT-TYPE
    SYNTAX       CucsManagedObjectDn
    MAX-ACCESS   read-only
    STATUS       current
    DESCRIPTION
        "Cisco UCS equipment:POSTCodeTemplate:dn managed object property"
    ::= { cucsEquipmentPOSTCodeTemplateEntry 2 }

cucsEquipmentPOSTCodeTemplateRn OBJECT-TYPE
    SYNTAX       SnmpAdminString
    MAX-ACCESS   read-only
    STATUS       current
    DESCRIPTION
        "Cisco UCS equipment:POSTCodeTemplate:rn managed object property"
    ::= { cucsEquipmentPOSTCodeTemplateEntry 3 }

cucsEquipmentPOSTCodeTemplateBaseContainer OBJECT-TYPE
    SYNTAX       SnmpAdminString
    MAX-ACCESS   read-only
    STATUS       current
    DESCRIPTION
        "Cisco UCS equipment:POSTCodeTemplate:baseContainer
        managed object property"
    ::= { cucsEquipmentPOSTCodeTemplateEntry 4 }

cucsEquipmentPOSTCodeTemplateName OBJECT-TYPE
    SYNTAX       SnmpAdminString
    MAX-ACCESS   read-only
    STATUS       current
    DESCRIPTION
        "Cisco UCS equipment:POSTCodeTemplate:name managed
        object property"
    ::= { cucsEquipmentPOSTCodeTemplateEntry 5 }

cucsEquipmentPciDefTable OBJECT-TYPE
    SYNTAX           SEQUENCE OF CucsEquipmentPciDefEntry
    MAX-ACCESS       not-accessible
    STATUS           current
    DESCRIPTION
        "Cisco UCS equipment:PciDef managed object table"
    ::= { cucsEquipmentObjects 50 }

cucsEquipmentPciDefEntry OBJECT-TYPE
    SYNTAX           CucsEquipmentPciDefEntry
    MAX-ACCESS       not-accessible
    STATUS           current
    DESCRIPTION
        "Entry for the cucsEquipmentPciDefTable table."
    INDEX { cucsEquipmentPciDefInstanceId }
    ::= { cucsEquipmentPciDefTable 1 }

CucsEquipmentPciDefEntry ::= SEQUENCE {
    cucsEquipmentPciDefInstanceId                                    CucsManagedObjectId,
    cucsEquipmentPciDefDn                                            CucsManagedObjectDn,
    cucsEquipmentPciDefRn                                            SnmpAdminString,
    cucsEquipmentPciDefDescr                                         SnmpAdminString,
    cucsEquipmentPciDefDevice                                        Gauge32,
    cucsEquipmentPciDefIntId                                         SnmpAdminString,
    cucsEquipmentPciDefName                                          SnmpAdminString,
    cucsEquipmentPciDefSubdevice                                     Gauge32,
    cucsEquipmentPciDefSubvendor                                     Gauge32,
    cucsEquipmentPciDefVendor                                        Gauge32,
    cucsEquipmentPciDefPolicyLevel                                   Gauge32,
    cucsEquipmentPciDefPolicyOwner                                   CucsPolicyPolicyOwner,
    cucsEquipmentPciDefDeviceType                                    CucsEquipmentDeviceType
}

cucsEquipmentPciDefInstanceId OBJECT-TYPE
    SYNTAX       CucsManagedObjectId
    MAX-ACCESS   not-accessible
    STATUS       current
    DESCRIPTION
        "Instance identifier of the managed object."
    ::= { cucsEquipmentPciDefEntry 1 }

cucsEquipmentPciDefDn OBJECT-TYPE
    SYNTAX       CucsManagedObjectDn
    MAX-ACCESS   read-only
    STATUS       current
    DESCRIPTION
        "Cisco UCS equipment:PciDef:dn managed object property"
    ::= { cucsEquipmentPciDefEntry 2 }

cucsEquipmentPciDefRn OBJECT-TYPE
    SYNTAX       SnmpAdminString
    MAX-ACCESS   read-only
    STATUS       current
    DESCRIPTION
        "Cisco UCS equipment:PciDef:rn managed object property"
    ::= { cucsEquipmentPciDefEntry 3 }

cucsEquipmentPciDefDescr OBJECT-TYPE
    SYNTAX       SnmpAdminString
    MAX-ACCESS   read-only
    STATUS       current
    DESCRIPTION
        "Cisco UCS equipment:PciDef:descr managed object property"
    ::= { cucsEquipmentPciDefEntry 4 }

cucsEquipmentPciDefDevice OBJECT-TYPE
    SYNTAX       Gauge32
    MAX-ACCESS   read-only
    STATUS       current
    DESCRIPTION
        "Cisco UCS equipment:PciDef:device managed object property"
    ::= { cucsEquipmentPciDefEntry 5 }

cucsEquipmentPciDefIntId OBJECT-TYPE
    SYNTAX       SnmpAdminString
    MAX-ACCESS   read-only
    STATUS       current
    DESCRIPTION
        "Cisco UCS equipment:PciDef:intId managed object property"
    ::= { cucsEquipmentPciDefEntry 6 }

cucsEquipmentPciDefName OBJECT-TYPE
    SYNTAX       SnmpAdminString
    MAX-ACCESS   read-only
    STATUS       current
    DESCRIPTION
        "Cisco UCS equipment:PciDef:name managed object property"
    ::= { cucsEquipmentPciDefEntry 7 }

cucsEquipmentPciDefSubdevice OBJECT-TYPE
    SYNTAX       Gauge32
    MAX-ACCESS   read-only
    STATUS       current
    DESCRIPTION
        "Cisco UCS equipment:PciDef:subdevice managed object property"
    ::= { cucsEquipmentPciDefEntry 8 }

cucsEquipmentPciDefSubvendor OBJECT-TYPE
    SYNTAX       Gauge32
    MAX-ACCESS   read-only
    STATUS       current
    DESCRIPTION
        "Cisco UCS equipment:PciDef:subvendor managed object property"
    ::= { cucsEquipmentPciDefEntry 9 }

cucsEquipmentPciDefVendor OBJECT-TYPE
    SYNTAX       Gauge32
    MAX-ACCESS   read-only
    STATUS       current
    DESCRIPTION
        "Cisco UCS equipment:PciDef:vendor managed object property"
    ::= { cucsEquipmentPciDefEntry 10 }

cucsEquipmentPciDefPolicyLevel OBJECT-TYPE
    SYNTAX       Gauge32
    MAX-ACCESS   read-only
    STATUS       current
    DESCRIPTION
        "Cisco UCS equipment:PciDef:policyLevel managed object property"
    ::= { cucsEquipmentPciDefEntry 11 }

cucsEquipmentPciDefPolicyOwner OBJECT-TYPE
    SYNTAX       CucsPolicyPolicyOwner
    MAX-ACCESS   read-only
    STATUS       current
    DESCRIPTION
        "Cisco UCS equipment:PciDef:policyOwner managed object property"
    ::= { cucsEquipmentPciDefEntry 12 }

cucsEquipmentPciDefDeviceType OBJECT-TYPE
    SYNTAX       CucsEquipmentDeviceType
    MAX-ACCESS   read-only
    STATUS       current
    DESCRIPTION
        "Cisco UCS equipment:PciDef:deviceType managed object property"
    ::= { cucsEquipmentPciDefEntry 13 }

cucsEquipmentPciSlotIdEntryTable OBJECT-TYPE
    SYNTAX           SEQUENCE OF CucsEquipmentPciSlotIdEntryEntry
    MAX-ACCESS       not-accessible
    STATUS           current
    DESCRIPTION
        "Cisco UCS equipment:PciSlotIdEntry managed object table"
    ::= { cucsEquipmentObjects 212 }

cucsEquipmentPciSlotIdEntryEntry OBJECT-TYPE
    SYNTAX           CucsEquipmentPciSlotIdEntryEntry
    MAX-ACCESS       not-accessible
    STATUS           current
    DESCRIPTION
        "Entry for the cucsEquipmentPciSlotIdEntryTable table."
    INDEX { cucsEquipmentPciSlotIdEntryInstanceId }
    ::= { cucsEquipmentPciSlotIdEntryTable 1 }

CucsEquipmentPciSlotIdEntryEntry ::= SEQUENCE {
    cucsEquipmentPciSlotIdEntryInstanceId                            CucsManagedObjectId,
    cucsEquipmentPciSlotIdEntryDn                                    CucsManagedObjectDn,
    cucsEquipmentPciSlotIdEntryRn                                    SnmpAdminString,
    cucsEquipmentPciSlotIdEntryId                                    Gauge32,
    cucsEquipmentPciSlotIdEntryName                                  SnmpAdminString
}

cucsEquipmentPciSlotIdEntryInstanceId OBJECT-TYPE
    SYNTAX       CucsManagedObjectId
    MAX-ACCESS   not-accessible
    STATUS       current
    DESCRIPTION
        "Instance identifier of the managed object."
    ::= { cucsEquipmentPciSlotIdEntryEntry 1 }

cucsEquipmentPciSlotIdEntryDn OBJECT-TYPE
    SYNTAX       CucsManagedObjectDn
    MAX-ACCESS   read-only
    STATUS       current
    DESCRIPTION
        "Cisco UCS equipment:PciSlotIdEntry:dn managed object property"
    ::= { cucsEquipmentPciSlotIdEntryEntry 2 }

cucsEquipmentPciSlotIdEntryRn OBJECT-TYPE
    SYNTAX       SnmpAdminString
    MAX-ACCESS   read-only
    STATUS       current
    DESCRIPTION
        "Cisco UCS equipment:PciSlotIdEntry:rn managed object property"
    ::= { cucsEquipmentPciSlotIdEntryEntry 3 }

cucsEquipmentPciSlotIdEntryId OBJECT-TYPE
    SYNTAX       Gauge32
    MAX-ACCESS   read-only
    STATUS       current
    DESCRIPTION
        "Cisco UCS equipment:PciSlotIdEntry:id managed object property"
    ::= { cucsEquipmentPciSlotIdEntryEntry 4 }

cucsEquipmentPciSlotIdEntryName OBJECT-TYPE
    SYNTAX       SnmpAdminString
    MAX-ACCESS   read-only
    STATUS       current
    DESCRIPTION
        "Cisco UCS equipment:PciSlotIdEntry:name managed object property"
    ::= { cucsEquipmentPciSlotIdEntryEntry 5 }

cucsEquipmentPciSlotIdMappingTable OBJECT-TYPE
    SYNTAX           SEQUENCE OF CucsEquipmentPciSlotIdMappingEntry
    MAX-ACCESS       not-accessible
    STATUS           current
    DESCRIPTION
        "Cisco UCS equipment:PciSlotIdMapping managed object table"
    ::= { cucsEquipmentObjects 213 }

cucsEquipmentPciSlotIdMappingEntry OBJECT-TYPE
    SYNTAX           CucsEquipmentPciSlotIdMappingEntry
    MAX-ACCESS       not-accessible
    STATUS           current
    DESCRIPTION
        "Entry for the cucsEquipmentPciSlotIdMappingTable table."
    INDEX { cucsEquipmentPciSlotIdMappingInstanceId }
    ::= { cucsEquipmentPciSlotIdMappingTable 1 }

CucsEquipmentPciSlotIdMappingEntry ::= SEQUENCE {
    cucsEquipmentPciSlotIdMappingInstanceId                          CucsManagedObjectId,
    cucsEquipmentPciSlotIdMappingDn                                  CucsManagedObjectDn,
    cucsEquipmentPciSlotIdMappingRn                                  SnmpAdminString,
    cucsEquipmentPciSlotIdMappingDescr                               SnmpAdminString,
    cucsEquipmentPciSlotIdMappingIntId                               SnmpAdminString,
    cucsEquipmentPciSlotIdMappingName                                SnmpAdminString,
    cucsEquipmentPciSlotIdMappingPolicyLevel                         Gauge32,
    cucsEquipmentPciSlotIdMappingPolicyOwner                         CucsPolicyPolicyOwner
}

cucsEquipmentPciSlotIdMappingInstanceId OBJECT-TYPE
    SYNTAX       CucsManagedObjectId
    MAX-ACCESS   not-accessible
    STATUS       current
    DESCRIPTION
        "Instance identifier of the managed object."
    ::= { cucsEquipmentPciSlotIdMappingEntry 1 }

cucsEquipmentPciSlotIdMappingDn OBJECT-TYPE
    SYNTAX       CucsManagedObjectDn
    MAX-ACCESS   read-only
    STATUS       current
    DESCRIPTION
        "Cisco UCS equipment:PciSlotIdMapping:dn managed object property"
    ::= { cucsEquipmentPciSlotIdMappingEntry 2 }

cucsEquipmentPciSlotIdMappingRn OBJECT-TYPE
    SYNTAX       SnmpAdminString
    MAX-ACCESS   read-only
    STATUS       current
    DESCRIPTION
        "Cisco UCS equipment:PciSlotIdMapping:rn managed object property"
    ::= { cucsEquipmentPciSlotIdMappingEntry 3 }

cucsEquipmentPciSlotIdMappingDescr OBJECT-TYPE
    SYNTAX       SnmpAdminString
    MAX-ACCESS   read-only
    STATUS       current
    DESCRIPTION
        "Cisco UCS equipment:PciSlotIdMapping:descr managed
        object property"
    ::= { cucsEquipmentPciSlotIdMappingEntry 4 }

cucsEquipmentPciSlotIdMappingIntId OBJECT-TYPE
    SYNTAX       SnmpAdminString
    MAX-ACCESS   read-only
    STATUS       current
    DESCRIPTION
        "Cisco UCS equipment:PciSlotIdMapping:intId managed
        object property"
    ::= { cucsEquipmentPciSlotIdMappingEntry 5 }

cucsEquipmentPciSlotIdMappingName OBJECT-TYPE
    SYNTAX       SnmpAdminString
    MAX-ACCESS   read-only
    STATUS       current
    DESCRIPTION
        "Cisco UCS equipment:PciSlotIdMapping:name managed
        object property"
    ::= { cucsEquipmentPciSlotIdMappingEntry 6 }

cucsEquipmentPciSlotIdMappingPolicyLevel OBJECT-TYPE
    SYNTAX       Gauge32
    MAX-ACCESS   read-only
    STATUS       current
    DESCRIPTION
        "Cisco UCS equipment:PciSlotIdMapping:policyLevel
        managed object property"
    ::= { cucsEquipmentPciSlotIdMappingEntry 7 }

cucsEquipmentPciSlotIdMappingPolicyOwner OBJECT-TYPE
    SYNTAX       CucsPolicyPolicyOwner
    MAX-ACCESS   read-only
    STATUS       current
    DESCRIPTION
        "Cisco UCS equipment:PciSlotIdMapping:policyOwner
        managed object property"
    ::= { cucsEquipmentPciSlotIdMappingEntry 8 }

cucsEquipmentPciSlotSubOEMIdEntryTable OBJECT-TYPE
    SYNTAX           SEQUENCE OF CucsEquipmentPciSlotSubOEMIdEntryEntry
    MAX-ACCESS       not-accessible
    STATUS           current
    DESCRIPTION
        "Cisco UCS equipment:PciSlotSubOEMIdEntry managed object table"
    ::= { cucsEquipmentObjects 214 }

cucsEquipmentPciSlotSubOEMIdEntryEntry OBJECT-TYPE
    SYNTAX           CucsEquipmentPciSlotSubOEMIdEntryEntry
    MAX-ACCESS       not-accessible
    STATUS           current
    DESCRIPTION
        "Entry for the cucsEquipmentPciSlotSubOEMIdEntryTable table."
    INDEX { cucsEquipmentPciSlotSubOEMIdEntryInstanceId }
    ::= { cucsEquipmentPciSlotSubOEMIdEntryTable 1 }

CucsEquipmentPciSlotSubOEMIdEntryEntry ::= SEQUENCE {
    cucsEquipmentPciSlotSubOEMIdEntryInstanceId                      CucsManagedObjectId,
    cucsEquipmentPciSlotSubOEMIdEntryDn                              CucsManagedObjectDn,
    cucsEquipmentPciSlotSubOEMIdEntryRn                              SnmpAdminString,
    cucsEquipmentPciSlotSubOEMIdEntryName                            SnmpAdminString,
    cucsEquipmentPciSlotSubOEMIdEntrySubOemId                        Gauge32
}

cucsEquipmentPciSlotSubOEMIdEntryInstanceId OBJECT-TYPE
    SYNTAX       CucsManagedObjectId
    MAX-ACCESS   not-accessible
    STATUS       current
    DESCRIPTION
        "Instance identifier of the managed object."
    ::= { cucsEquipmentPciSlotSubOEMIdEntryEntry 1 }

cucsEquipmentPciSlotSubOEMIdEntryDn OBJECT-TYPE
    SYNTAX       CucsManagedObjectDn
    MAX-ACCESS   read-only
    STATUS       current
    DESCRIPTION
        "Cisco UCS equipment:PciSlotSubOEMIdEntry:dn managed
        object property"
    ::= { cucsEquipmentPciSlotSubOEMIdEntryEntry 2 }

cucsEquipmentPciSlotSubOEMIdEntryRn OBJECT-TYPE
    SYNTAX       SnmpAdminString
    MAX-ACCESS   read-only
    STATUS       current
    DESCRIPTION
        "Cisco UCS equipment:PciSlotSubOEMIdEntry:rn managed
        object property"
    ::= { cucsEquipmentPciSlotSubOEMIdEntryEntry 3 }

cucsEquipmentPciSlotSubOEMIdEntryName OBJECT-TYPE
    SYNTAX       SnmpAdminString
    MAX-ACCESS   read-only
    STATUS       current
    DESCRIPTION
        "Cisco UCS equipment:PciSlotSubOEMIdEntry:name
        managed object property"
    ::= { cucsEquipmentPciSlotSubOEMIdEntryEntry 4 }

cucsEquipmentPciSlotSubOEMIdEntrySubOemId OBJECT-TYPE
    SYNTAX       Gauge32
    MAX-ACCESS   read-only
    STATUS       current
    DESCRIPTION
        "Cisco UCS equipment:PciSlotSubOEMIdEntry:subOemId
        managed object property"
    ::= { cucsEquipmentPciSlotSubOEMIdEntryEntry 5 }

cucsEquipmentPfcMmuCapTable OBJECT-TYPE
    SYNTAX           SEQUENCE OF CucsEquipmentPfcMmuCapEntry
    MAX-ACCESS       not-accessible
    STATUS           current
    DESCRIPTION
        "Cisco UCS equipment:PfcMmuCap managed object table"
    ::= { cucsEquipmentObjects 167 }

cucsEquipmentPfcMmuCapEntry OBJECT-TYPE
    SYNTAX           CucsEquipmentPfcMmuCapEntry
    MAX-ACCESS       not-accessible
    STATUS           current
    DESCRIPTION
        "Entry for the cucsEquipmentPfcMmuCapTable table."
    INDEX { cucsEquipmentPfcMmuCapInstanceId }
    ::= { cucsEquipmentPfcMmuCapTable 1 }

CucsEquipmentPfcMmuCapEntry ::= SEQUENCE {
    cucsEquipmentPfcMmuCapInstanceId                                 CucsManagedObjectId,
    cucsEquipmentPfcMmuCapDn                                         CucsManagedObjectDn,
    cucsEquipmentPfcMmuCapRn                                         SnmpAdminString,
    cucsEquipmentPfcMmuCapDescr                                      SnmpAdminString,
    cucsEquipmentPfcMmuCapFcoe                                       CucsEquipmentMmuPercent,
    cucsEquipmentPfcMmuCapFcoeJumboNodrop                            CucsEquipmentMmuPercent,
    cucsEquipmentPfcMmuCapFcoeNormalNodrop                           CucsEquipmentMmuPercent,
    cucsEquipmentPfcMmuCapIntId                                      SnmpAdminString,
    cucsEquipmentPfcMmuCapJumboBreakoutPort                          Gauge32,
    cucsEquipmentPfcMmuCapName                                       SnmpAdminString,
    cucsEquipmentPfcMmuCapPolicyLevel                                Gauge32,
    cucsEquipmentPfcMmuCapPolicyOwner                                CucsPolicyPolicyOwner
}

cucsEquipmentPfcMmuCapInstanceId OBJECT-TYPE
    SYNTAX       CucsManagedObjectId
    MAX-ACCESS   not-accessible
    STATUS       current
    DESCRIPTION
        "Instance identifier of the managed object."
    ::= { cucsEquipmentPfcMmuCapEntry 1 }

cucsEquipmentPfcMmuCapDn OBJECT-TYPE
    SYNTAX       CucsManagedObjectDn
    MAX-ACCESS   read-only
    STATUS       current
    DESCRIPTION
        "Cisco UCS equipment:PfcMmuCap:dn managed object property"
    ::= { cucsEquipmentPfcMmuCapEntry 2 }

cucsEquipmentPfcMmuCapRn OBJECT-TYPE
    SYNTAX       SnmpAdminString
    MAX-ACCESS   read-only
    STATUS       current
    DESCRIPTION
        "Cisco UCS equipment:PfcMmuCap:rn managed object property"
    ::= { cucsEquipmentPfcMmuCapEntry 3 }

cucsEquipmentPfcMmuCapDescr OBJECT-TYPE
    SYNTAX       SnmpAdminString
    MAX-ACCESS   read-only
    STATUS       current
    DESCRIPTION
        "Cisco UCS equipment:PfcMmuCap:descr managed object property"
    ::= { cucsEquipmentPfcMmuCapEntry 4 }

cucsEquipmentPfcMmuCapFcoe OBJECT-TYPE
    SYNTAX       CucsEquipmentMmuPercent
    MAX-ACCESS   read-only
    STATUS       current
    DESCRIPTION
        "Cisco UCS equipment:PfcMmuCap:fcoe managed object property"
    ::= { cucsEquipmentPfcMmuCapEntry 5 }

cucsEquipmentPfcMmuCapFcoeJumboNodrop OBJECT-TYPE
    SYNTAX       CucsEquipmentMmuPercent
    MAX-ACCESS   read-only
    STATUS       current
    DESCRIPTION
        "Cisco UCS equipment:PfcMmuCap:fcoeJumboNodrop
        managed object property"
    ::= { cucsEquipmentPfcMmuCapEntry 6 }

cucsEquipmentPfcMmuCapFcoeNormalNodrop OBJECT-TYPE
    SYNTAX       CucsEquipmentMmuPercent
    MAX-ACCESS   read-only
    STATUS       current
    DESCRIPTION
        "Cisco UCS equipment:PfcMmuCap:fcoeNormalNodrop
        managed object property"
    ::= { cucsEquipmentPfcMmuCapEntry 7 }

cucsEquipmentPfcMmuCapIntId OBJECT-TYPE
    SYNTAX       SnmpAdminString
    MAX-ACCESS   read-only
    STATUS       current
    DESCRIPTION
        "Cisco UCS equipment:PfcMmuCap:intId managed object property"
    ::= { cucsEquipmentPfcMmuCapEntry 8 }

cucsEquipmentPfcMmuCapJumboBreakoutPort OBJECT-TYPE
    SYNTAX       Gauge32
    MAX-ACCESS   read-only
    STATUS       current
    DESCRIPTION
        "Cisco UCS equipment:PfcMmuCap:jumboBreakoutPort
        managed object property"
    ::= { cucsEquipmentPfcMmuCapEntry 9 }

cucsEquipmentPfcMmuCapName OBJECT-TYPE
    SYNTAX       SnmpAdminString
    MAX-ACCESS   read-only
    STATUS       current
    DESCRIPTION
        "Cisco UCS equipment:PfcMmuCap:name managed object property"
    ::= { cucsEquipmentPfcMmuCapEntry 10 }

cucsEquipmentPfcMmuCapPolicyLevel OBJECT-TYPE
    SYNTAX       Gauge32
    MAX-ACCESS   read-only
    STATUS       current
    DESCRIPTION
        "Cisco UCS equipment:PfcMmuCap:policyLevel managed
        object property"
    ::= { cucsEquipmentPfcMmuCapEntry 11 }

cucsEquipmentPfcMmuCapPolicyOwner OBJECT-TYPE
    SYNTAX       CucsPolicyPolicyOwner
    MAX-ACCESS   read-only
    STATUS       current
    DESCRIPTION
        "Cisco UCS equipment:PfcMmuCap:policyOwner managed
        object property"
    ::= { cucsEquipmentPfcMmuCapEntry 12 }

cucsEquipmentPhysDevicesPerBoardTable OBJECT-TYPE
    SYNTAX           SEQUENCE OF CucsEquipmentPhysDevicesPerBoardEntry
    MAX-ACCESS       not-accessible
    STATUS           current
    DESCRIPTION
        "Cisco UCS equipment:PhysDevicesPerBoard managed object table"
    ::= { cucsEquipmentObjects 129 }

cucsEquipmentPhysDevicesPerBoardEntry OBJECT-TYPE
    SYNTAX           CucsEquipmentPhysDevicesPerBoardEntry
    MAX-ACCESS       not-accessible
    STATUS           current
    DESCRIPTION
        "Entry for the cucsEquipmentPhysDevicesPerBoardTable table."
    INDEX { cucsEquipmentPhysDevicesPerBoardInstanceId }
    ::= { cucsEquipmentPhysDevicesPerBoardTable 1 }

CucsEquipmentPhysDevicesPerBoardEntry ::= SEQUENCE {
    cucsEquipmentPhysDevicesPerBoardInstanceId                       CucsManagedObjectId,
    cucsEquipmentPhysDevicesPerBoardDn                               CucsManagedObjectDn,
    cucsEquipmentPhysDevicesPerBoardRn                               SnmpAdminString,
    cucsEquipmentPhysDevicesPerBoardNumOfCpu                         Gauge32,
    cucsEquipmentPhysDevicesPerBoardNumOfDimm                        Gauge32,
    cucsEquipmentPhysDevicesPerBoardNumOfLocalDisk                   Gauge32,
    cucsEquipmentPhysDevicesPerBoardNumOfStorageController           Gauge32,
    cucsEquipmentPhysDevicesPerBoardNumOfadaptor                     Gauge32
}

cucsEquipmentPhysDevicesPerBoardInstanceId OBJECT-TYPE
    SYNTAX       CucsManagedObjectId
    MAX-ACCESS   not-accessible
    STATUS       current
    DESCRIPTION
        "Instance identifier of the managed object."
    ::= { cucsEquipmentPhysDevicesPerBoardEntry 1 }

cucsEquipmentPhysDevicesPerBoardDn OBJECT-TYPE
    SYNTAX       CucsManagedObjectDn
    MAX-ACCESS   read-only
    STATUS       current
    DESCRIPTION
        "Cisco UCS equipment:PhysDevicesPerBoard:dn managed
        object property"
    ::= { cucsEquipmentPhysDevicesPerBoardEntry 2 }

cucsEquipmentPhysDevicesPerBoardRn OBJECT-TYPE
    SYNTAX       SnmpAdminString
    MAX-ACCESS   read-only
    STATUS       current
    DESCRIPTION
        "Cisco UCS equipment:PhysDevicesPerBoard:rn managed
        object property"
    ::= { cucsEquipmentPhysDevicesPerBoardEntry 3 }

cucsEquipmentPhysDevicesPerBoardNumOfCpu OBJECT-TYPE
    SYNTAX       Gauge32
    MAX-ACCESS   read-only
    STATUS       current
    DESCRIPTION
        "Cisco UCS equipment:PhysDevicesPerBoard:numOfCpu
        managed object property"
    ::= { cucsEquipmentPhysDevicesPerBoardEntry 4 }

cucsEquipmentPhysDevicesPerBoardNumOfDimm OBJECT-TYPE
    SYNTAX       Gauge32
    MAX-ACCESS   read-only
    STATUS       current
    DESCRIPTION
        "Cisco UCS equipment:PhysDevicesPerBoard:numOfDimm
        managed object property"
    ::= { cucsEquipmentPhysDevicesPerBoardEntry 5 }

cucsEquipmentPhysDevicesPerBoardNumOfLocalDisk OBJECT-TYPE
    SYNTAX       Gauge32
    MAX-ACCESS   read-only
    STATUS       current
    DESCRIPTION
        "Cisco UCS equipment:PhysDevicesPerBoard:numOfLocalDisk
        managed object property"
    ::= { cucsEquipmentPhysDevicesPerBoardEntry 6 }

cucsEquipmentPhysDevicesPerBoardNumOfStorageController OBJECT-TYPE
    SYNTAX       Gauge32
    MAX-ACCESS   read-only
    STATUS       current
    DESCRIPTION
        "Cisco UCS equipment:PhysDevicesPerBoard:numOfStorageController
        managed object property"
    ::= { cucsEquipmentPhysDevicesPerBoardEntry 7 }

cucsEquipmentPhysDevicesPerBoardNumOfadaptor OBJECT-TYPE
    SYNTAX       Gauge32
    MAX-ACCESS   read-only
    STATUS       current
    DESCRIPTION
        "Cisco UCS equipment:PhysDevicesPerBoard:numOfadaptor
        managed object property"
    ::= { cucsEquipmentPhysDevicesPerBoardEntry 8 }

cucsEquipmentPhysicalDefTable OBJECT-TYPE
    SYNTAX           SEQUENCE OF CucsEquipmentPhysicalDefEntry
    MAX-ACCESS       not-accessible
    STATUS           current
    DESCRIPTION
        "Cisco UCS equipment:PhysicalDef managed object table"
    ::= { cucsEquipmentObjects 51 }

cucsEquipmentPhysicalDefEntry OBJECT-TYPE
    SYNTAX           CucsEquipmentPhysicalDefEntry
    MAX-ACCESS       not-accessible
    STATUS           current
    DESCRIPTION
        "Entry for the cucsEquipmentPhysicalDefTable table."
    INDEX { cucsEquipmentPhysicalDefInstanceId }
    ::= { cucsEquipmentPhysicalDefTable 1 }

CucsEquipmentPhysicalDefEntry ::= SEQUENCE {
    cucsEquipmentPhysicalDefInstanceId                               CucsManagedObjectId,
    cucsEquipmentPhysicalDefDn                                       CucsManagedObjectDn,
    cucsEquipmentPhysicalDefRn                                       SnmpAdminString,
    cucsEquipmentPhysicalDefDepth                                    SnmpAdminString,
    cucsEquipmentPhysicalDefDescr                                    SnmpAdminString,
    cucsEquipmentPhysicalDefHeight                                   SnmpAdminString,
    cucsEquipmentPhysicalDefIntId                                    SnmpAdminString,
    cucsEquipmentPhysicalDefMaximumPower                             SnmpAdminString,
    cucsEquipmentPhysicalDefMaximumTemperature                       SnmpAdminString,
    cucsEquipmentPhysicalDefMinimumPower                             SnmpAdminString,
    cucsEquipmentPhysicalDefMinimumTemperature                       SnmpAdminString,
    cucsEquipmentPhysicalDefName                                     SnmpAdminString,
    cucsEquipmentPhysicalDefNominalPower                             SnmpAdminString,
    cucsEquipmentPhysicalDefNominalTemperature                       SnmpAdminString,
    cucsEquipmentPhysicalDefOperatingVoltages                        SnmpAdminString,
    cucsEquipmentPhysicalDefWeight                                   SnmpAdminString,
    cucsEquipmentPhysicalDefWidth                                    SnmpAdminString,
    cucsEquipmentPhysicalDefPolicyLevel                              Gauge32,
    cucsEquipmentPhysicalDefPolicyOwner                              CucsPolicyPolicyOwner
}

cucsEquipmentPhysicalDefInstanceId OBJECT-TYPE
    SYNTAX       CucsManagedObjectId
    MAX-ACCESS   not-accessible
    STATUS       current
    DESCRIPTION
        "Instance identifier of the managed object."
    ::= { cucsEquipmentPhysicalDefEntry 1 }

cucsEquipmentPhysicalDefDn OBJECT-TYPE
    SYNTAX       CucsManagedObjectDn
    MAX-ACCESS   read-only
    STATUS       current
    DESCRIPTION
        "Cisco UCS equipment:PhysicalDef:dn managed object property"
    ::= { cucsEquipmentPhysicalDefEntry 2 }

cucsEquipmentPhysicalDefRn OBJECT-TYPE
    SYNTAX       SnmpAdminString
    MAX-ACCESS   read-only
    STATUS       current
    DESCRIPTION
        "Cisco UCS equipment:PhysicalDef:rn managed object property"
    ::= { cucsEquipmentPhysicalDefEntry 3 }

cucsEquipmentPhysicalDefDepth OBJECT-TYPE
    SYNTAX       SnmpAdminString
    MAX-ACCESS   read-only
    STATUS       current
    DESCRIPTION
        "Cisco UCS equipment:PhysicalDef:depth managed object property"
    ::= { cucsEquipmentPhysicalDefEntry 4 }

cucsEquipmentPhysicalDefDescr OBJECT-TYPE
    SYNTAX       SnmpAdminString
    MAX-ACCESS   read-only
    STATUS       current
    DESCRIPTION
        "Cisco UCS equipment:PhysicalDef:descr managed object property"
    ::= { cucsEquipmentPhysicalDefEntry 5 }

cucsEquipmentPhysicalDefHeight OBJECT-TYPE
    SYNTAX       SnmpAdminString
    MAX-ACCESS   read-only
    STATUS       current
    DESCRIPTION
        "Cisco UCS equipment:PhysicalDef:height managed object property"
    ::= { cucsEquipmentPhysicalDefEntry 6 }

cucsEquipmentPhysicalDefIntId OBJECT-TYPE
    SYNTAX       SnmpAdminString
    MAX-ACCESS   read-only
    STATUS       current
    DESCRIPTION
        "Cisco UCS equipment:PhysicalDef:intId managed object property"
    ::= { cucsEquipmentPhysicalDefEntry 7 }

cucsEquipmentPhysicalDefMaximumPower OBJECT-TYPE
    SYNTAX       SnmpAdminString
    MAX-ACCESS   read-only
    STATUS       current
    DESCRIPTION
        "Cisco UCS equipment:PhysicalDef:maximumPower managed
        object property"
    ::= { cucsEquipmentPhysicalDefEntry 8 }

cucsEquipmentPhysicalDefMaximumTemperature OBJECT-TYPE
    SYNTAX       SnmpAdminString
    MAX-ACCESS   read-only
    STATUS       current
    DESCRIPTION
        "Cisco UCS equipment:PhysicalDef:maximumTemperature
        managed object property"
    ::= { cucsEquipmentPhysicalDefEntry 9 }

cucsEquipmentPhysicalDefMinimumPower OBJECT-TYPE
    SYNTAX       SnmpAdminString
    MAX-ACCESS   read-only
    STATUS       current
    DESCRIPTION
        "Cisco UCS equipment:PhysicalDef:minimumPower managed
        object property"
    ::= { cucsEquipmentPhysicalDefEntry 10 }

cucsEquipmentPhysicalDefMinimumTemperature OBJECT-TYPE
    SYNTAX       SnmpAdminString
    MAX-ACCESS   read-only
    STATUS       current
    DESCRIPTION
        "Cisco UCS equipment:PhysicalDef:minimumTemperature
        managed object property"
    ::= { cucsEquipmentPhysicalDefEntry 11 }

cucsEquipmentPhysicalDefName OBJECT-TYPE
    SYNTAX       SnmpAdminString
    MAX-ACCESS   read-only
    STATUS       current
    DESCRIPTION
        "Cisco UCS equipment:PhysicalDef:name managed object property"
    ::= { cucsEquipmentPhysicalDefEntry 12 }

cucsEquipmentPhysicalDefNominalPower OBJECT-TYPE
    SYNTAX       SnmpAdminString
    MAX-ACCESS   read-only
    STATUS       current
    DESCRIPTION
        "Cisco UCS equipment:PhysicalDef:nominalPower managed
        object property"
    ::= { cucsEquipmentPhysicalDefEntry 13 }

cucsEquipmentPhysicalDefNominalTemperature OBJECT-TYPE
    SYNTAX       SnmpAdminString
    MAX-ACCESS   read-only
    STATUS       current
    DESCRIPTION
        "Cisco UCS equipment:PhysicalDef:nominalTemperature
        managed object property"
    ::= { cucsEquipmentPhysicalDefEntry 14 }

cucsEquipmentPhysicalDefOperatingVoltages OBJECT-TYPE
    SYNTAX       SnmpAdminString
    MAX-ACCESS   read-only
    STATUS       current
    DESCRIPTION
        "Cisco UCS equipment:PhysicalDef:operatingVoltages
        managed object property"
    ::= { cucsEquipmentPhysicalDefEntry 15 }

cucsEquipmentPhysicalDefWeight OBJECT-TYPE
    SYNTAX       SnmpAdminString
    MAX-ACCESS   read-only
    STATUS       current
    DESCRIPTION
        "Cisco UCS equipment:PhysicalDef:weight managed object property"
    ::= { cucsEquipmentPhysicalDefEntry 16 }

cucsEquipmentPhysicalDefWidth OBJECT-TYPE
    SYNTAX       SnmpAdminString
    MAX-ACCESS   read-only
    STATUS       current
    DESCRIPTION
        "Cisco UCS equipment:PhysicalDef:width managed object property"
    ::= { cucsEquipmentPhysicalDefEntry 17 }

cucsEquipmentPhysicalDefPolicyLevel OBJECT-TYPE
    SYNTAX       Gauge32
    MAX-ACCESS   read-only
    STATUS       current
    DESCRIPTION
        "Cisco UCS equipment:PhysicalDef:policyLevel managed
        object property"
    ::= { cucsEquipmentPhysicalDefEntry 18 }

cucsEquipmentPhysicalDefPolicyOwner OBJECT-TYPE
    SYNTAX       CucsPolicyPolicyOwner
    MAX-ACCESS   read-only
    STATUS       current
    DESCRIPTION
        "Cisco UCS equipment:PhysicalDef:policyOwner managed
        object property"
    ::= { cucsEquipmentPhysicalDefEntry 19 }

cucsEquipmentPhysicalQualTable OBJECT-TYPE
    SYNTAX           SEQUENCE OF CucsEquipmentPhysicalQualEntry
    MAX-ACCESS       not-accessible
    STATUS           current
    DESCRIPTION
        "Cisco UCS equipment:PhysicalQual managed object table"
    ::= { cucsEquipmentObjects 191 }

cucsEquipmentPhysicalQualEntry OBJECT-TYPE
    SYNTAX           CucsEquipmentPhysicalQualEntry
    MAX-ACCESS       not-accessible
    STATUS           current
    DESCRIPTION
        "Entry for the cucsEquipmentPhysicalQualTable table."
    INDEX { cucsEquipmentPhysicalQualInstanceId }
    ::= { cucsEquipmentPhysicalQualTable 1 }

CucsEquipmentPhysicalQualEntry ::= SEQUENCE {
    cucsEquipmentPhysicalQualInstanceId                              CucsManagedObjectId,
    cucsEquipmentPhysicalQualDn                                      CucsManagedObjectDn,
    cucsEquipmentPhysicalQualRn                                      SnmpAdminString,
    cucsEquipmentPhysicalQualModel                                   SnmpAdminString,
    cucsEquipmentPhysicalQualPropAcl                                 Unsigned64
}

cucsEquipmentPhysicalQualInstanceId OBJECT-TYPE
    SYNTAX       CucsManagedObjectId
    MAX-ACCESS   not-accessible
    STATUS       current
    DESCRIPTION
        "Instance identifier of the managed object."
    ::= { cucsEquipmentPhysicalQualEntry 1 }

cucsEquipmentPhysicalQualDn OBJECT-TYPE
    SYNTAX       CucsManagedObjectDn
    MAX-ACCESS   read-only
    STATUS       current
    DESCRIPTION
        "Cisco UCS equipment:PhysicalQual:dn managed object property"
    ::= { cucsEquipmentPhysicalQualEntry 2 }

cucsEquipmentPhysicalQualRn OBJECT-TYPE
    SYNTAX       SnmpAdminString
    MAX-ACCESS   read-only
    STATUS       current
    DESCRIPTION
        "Cisco UCS equipment:PhysicalQual:rn managed object property"
    ::= { cucsEquipmentPhysicalQualEntry 3 }

cucsEquipmentPhysicalQualModel OBJECT-TYPE
    SYNTAX       SnmpAdminString
    MAX-ACCESS   read-only
    STATUS       current
    DESCRIPTION
        "Cisco UCS equipment:PhysicalQual:model managed object property"
    ::= { cucsEquipmentPhysicalQualEntry 4 }

cucsEquipmentPhysicalQualPropAcl OBJECT-TYPE
    SYNTAX       Unsigned64
    MAX-ACCESS   read-only
    STATUS       current
    DESCRIPTION
        "Cisco UCS equipment:PhysicalQual:propAcl managed object property"
    ::= { cucsEquipmentPhysicalQualEntry 5 }

cucsEquipmentPictureTable OBJECT-TYPE
    SYNTAX           SEQUENCE OF CucsEquipmentPictureEntry
    MAX-ACCESS       not-accessible
    STATUS           current
    DESCRIPTION
        "Cisco UCS equipment:Picture managed object table"
    ::= { cucsEquipmentObjects 52 }

cucsEquipmentPictureEntry OBJECT-TYPE
    SYNTAX           CucsEquipmentPictureEntry
    MAX-ACCESS       not-accessible
    STATUS           current
    DESCRIPTION
        "Entry for the cucsEquipmentPictureTable table."
    INDEX { cucsEquipmentPictureInstanceId }
    ::= { cucsEquipmentPictureTable 1 }

CucsEquipmentPictureEntry ::= SEQUENCE {
    cucsEquipmentPictureInstanceId                                   CucsManagedObjectId,
    cucsEquipmentPictureDn                                           CucsManagedObjectDn,
    cucsEquipmentPictureRn                                           SnmpAdminString,
    cucsEquipmentPictureFileName                                     SnmpAdminString,
    cucsEquipmentPictureType                                         CucsEquipmentPictureType
}

cucsEquipmentPictureInstanceId OBJECT-TYPE
    SYNTAX       CucsManagedObjectId
    MAX-ACCESS   not-accessible
    STATUS       current
    DESCRIPTION
        "Instance identifier of the managed object."
    ::= { cucsEquipmentPictureEntry 1 }

cucsEquipmentPictureDn OBJECT-TYPE
    SYNTAX       CucsManagedObjectDn
    MAX-ACCESS   read-only
    STATUS       current
    DESCRIPTION
        "Cisco UCS equipment:Picture:dn managed object property"
    ::= { cucsEquipmentPictureEntry 2 }

cucsEquipmentPictureRn OBJECT-TYPE
    SYNTAX       SnmpAdminString
    MAX-ACCESS   read-only
    STATUS       current
    DESCRIPTION
        "Cisco UCS equipment:Picture:rn managed object property"
    ::= { cucsEquipmentPictureEntry 3 }

cucsEquipmentPictureFileName OBJECT-TYPE
    SYNTAX       SnmpAdminString
    MAX-ACCESS   read-only
    STATUS       current
    DESCRIPTION
        "Cisco UCS equipment:Picture:fileName managed object property"
    ::= { cucsEquipmentPictureEntry 4 }

cucsEquipmentPictureType OBJECT-TYPE
    SYNTAX       CucsEquipmentPictureType
    MAX-ACCESS   read-only
    STATUS       current
    DESCRIPTION
        "Cisco UCS equipment:Picture:type managed object property"
    ::= { cucsEquipmentPictureEntry 5 }

cucsEquipmentPoolTable OBJECT-TYPE
    SYNTAX           SEQUENCE OF CucsEquipmentPoolEntry
    MAX-ACCESS       not-accessible
    STATUS           current
    DESCRIPTION
        "Cisco UCS equipment:Pool managed object table"
    ::= { cucsEquipmentObjects 192 }

cucsEquipmentPoolEntry OBJECT-TYPE
    SYNTAX           CucsEquipmentPoolEntry
    MAX-ACCESS       not-accessible
    STATUS           current
    DESCRIPTION
        "Entry for the cucsEquipmentPoolTable table."
    INDEX { cucsEquipmentPoolInstanceId }
    ::= { cucsEquipmentPoolTable 1 }

CucsEquipmentPoolEntry ::= SEQUENCE {
    cucsEquipmentPoolInstanceId                                      CucsManagedObjectId,
    cucsEquipmentPoolDn                                              CucsManagedObjectDn,
    cucsEquipmentPoolRn                                              SnmpAdminString,
    cucsEquipmentPoolAssigned                                        Gauge32,
    cucsEquipmentPoolDescr                                           SnmpAdminString,
    cucsEquipmentPoolIntId                                           SnmpAdminString,
    cucsEquipmentPoolName                                            SnmpAdminString,
    cucsEquipmentPoolPolicyLevel                                     Gauge32,
    cucsEquipmentPoolPolicyOwner                                     CucsPolicyPolicyOwner,
    cucsEquipmentPoolSize                                            Gauge32,
    cucsEquipmentPoolAssignmentOrder                                 CucsPoolPoolAssignmentOrder
}

cucsEquipmentPoolInstanceId OBJECT-TYPE
    SYNTAX       CucsManagedObjectId
    MAX-ACCESS   not-accessible
    STATUS       current
    DESCRIPTION
        "Instance identifier of the managed object."
    ::= { cucsEquipmentPoolEntry 1 }

cucsEquipmentPoolDn OBJECT-TYPE
    SYNTAX       CucsManagedObjectDn
    MAX-ACCESS   read-only
    STATUS       current
    DESCRIPTION
        "Cisco UCS equipment:Pool:dn managed object property"
    ::= { cucsEquipmentPoolEntry 2 }

cucsEquipmentPoolRn OBJECT-TYPE
    SYNTAX       SnmpAdminString
    MAX-ACCESS   read-only
    STATUS       current
    DESCRIPTION
        "Cisco UCS equipment:Pool:rn managed object property"
    ::= { cucsEquipmentPoolEntry 3 }

cucsEquipmentPoolAssigned OBJECT-TYPE
    SYNTAX       Gauge32
    MAX-ACCESS   read-only
    STATUS       current
    DESCRIPTION
        "Cisco UCS equipment:Pool:assigned managed object property"
    ::= { cucsEquipmentPoolEntry 4 }

cucsEquipmentPoolDescr OBJECT-TYPE
    SYNTAX       SnmpAdminString
    MAX-ACCESS   read-only
    STATUS       current
    DESCRIPTION
        "Cisco UCS equipment:Pool:descr managed object property"
    ::= { cucsEquipmentPoolEntry 5 }

cucsEquipmentPoolIntId OBJECT-TYPE
    SYNTAX       SnmpAdminString
    MAX-ACCESS   read-only
    STATUS       current
    DESCRIPTION
        "Cisco UCS equipment:Pool:intId managed object property"
    ::= { cucsEquipmentPoolEntry 7 }

cucsEquipmentPoolName OBJECT-TYPE
    SYNTAX       SnmpAdminString
    MAX-ACCESS   read-only
    STATUS       current
    DESCRIPTION
        "Cisco UCS equipment:Pool:name managed object property"
    ::= { cucsEquipmentPoolEntry 8 }

cucsEquipmentPoolPolicyLevel OBJECT-TYPE
    SYNTAX       Gauge32
    MAX-ACCESS   read-only
    STATUS       current
    DESCRIPTION
        "Cisco UCS equipment:Pool:policyLevel managed object property"
    ::= { cucsEquipmentPoolEntry 9 }

cucsEquipmentPoolPolicyOwner OBJECT-TYPE
    SYNTAX       CucsPolicyPolicyOwner
    MAX-ACCESS   read-only
    STATUS       current
    DESCRIPTION
        "Cisco UCS equipment:Pool:policyOwner managed object property"
    ::= { cucsEquipmentPoolEntry 10 }

cucsEquipmentPoolSize OBJECT-TYPE
    SYNTAX       Gauge32
    MAX-ACCESS   read-only
    STATUS       current
    DESCRIPTION
        "Cisco UCS equipment:Pool:size managed object property"
    ::= { cucsEquipmentPoolEntry 12 }

cucsEquipmentPoolAssignmentOrder OBJECT-TYPE
    SYNTAX       CucsPoolPoolAssignmentOrder
    MAX-ACCESS   read-only
    STATUS       current
    DESCRIPTION
        "Cisco UCS equipment:Pool:assignmentOrder managed object property"
    ::= { cucsEquipmentPoolEntry 13 }

cucsEquipmentPoolPolicyRefTable OBJECT-TYPE
    SYNTAX           SEQUENCE OF CucsEquipmentPoolPolicyRefEntry
    MAX-ACCESS       not-accessible
    STATUS           current
    DESCRIPTION
        "Cisco UCS equipment:PoolPolicyRef managed object table"
    ::= { cucsEquipmentObjects 215 }

cucsEquipmentPoolPolicyRefEntry OBJECT-TYPE
    SYNTAX           CucsEquipmentPoolPolicyRefEntry
    MAX-ACCESS       not-accessible
    STATUS           current
    DESCRIPTION
        "Entry for the cucsEquipmentPoolPolicyRefTable table."
    INDEX { cucsEquipmentPoolPolicyRefInstanceId }
    ::= { cucsEquipmentPoolPolicyRefTable 1 }

CucsEquipmentPoolPolicyRefEntry ::= SEQUENCE {
    cucsEquipmentPoolPolicyRefInstanceId                             CucsManagedObjectId,
    cucsEquipmentPoolPolicyRefDn                                     CucsManagedObjectDn,
    cucsEquipmentPoolPolicyRefRn                                     SnmpAdminString,
    cucsEquipmentPoolPolicyRefId                                     Unsigned64,
    cucsEquipmentPoolPolicyRefPolicyDn                               SnmpAdminString
}

cucsEquipmentPoolPolicyRefInstanceId OBJECT-TYPE
    SYNTAX       CucsManagedObjectId
    MAX-ACCESS   not-accessible
    STATUS       current
    DESCRIPTION
        "Instance identifier of the managed object."
    ::= { cucsEquipmentPoolPolicyRefEntry 1 }

cucsEquipmentPoolPolicyRefDn OBJECT-TYPE
    SYNTAX       CucsManagedObjectDn
    MAX-ACCESS   read-only
    STATUS       current
    DESCRIPTION
        "Cisco UCS equipment:PoolPolicyRef:dn managed object property"
    ::= { cucsEquipmentPoolPolicyRefEntry 2 }

cucsEquipmentPoolPolicyRefRn OBJECT-TYPE
    SYNTAX       SnmpAdminString
    MAX-ACCESS   read-only
    STATUS       current
    DESCRIPTION
        "Cisco UCS equipment:PoolPolicyRef:rn managed object property"
    ::= { cucsEquipmentPoolPolicyRefEntry 3 }

cucsEquipmentPoolPolicyRefId OBJECT-TYPE
    SYNTAX       Unsigned64
    MAX-ACCESS   read-only
    STATUS       current
    DESCRIPTION
        "Cisco UCS equipment:PoolPolicyRef:id managed object property"
    ::= { cucsEquipmentPoolPolicyRefEntry 4 }

cucsEquipmentPoolPolicyRefPolicyDn OBJECT-TYPE
    SYNTAX       SnmpAdminString
    MAX-ACCESS   read-only
    STATUS       current
    DESCRIPTION
        "Cisco UCS equipment:PoolPolicyRef:policyDn managed
        object property"
    ::= { cucsEquipmentPoolPolicyRefEntry 5 }

cucsEquipmentPoolableTable OBJECT-TYPE
    SYNTAX           SEQUENCE OF CucsEquipmentPoolableEntry
    MAX-ACCESS       not-accessible
    STATUS           current
    DESCRIPTION
        "Cisco UCS equipment:Poolable managed object table"
    ::= { cucsEquipmentObjects 193 }

cucsEquipmentPoolableEntry OBJECT-TYPE
    SYNTAX           CucsEquipmentPoolableEntry
    MAX-ACCESS       not-accessible
    STATUS           current
    DESCRIPTION
        "Entry for the cucsEquipmentPoolableTable table."
    INDEX { cucsEquipmentPoolableInstanceId }
    ::= { cucsEquipmentPoolableTable 1 }

CucsEquipmentPoolableEntry ::= SEQUENCE {
    cucsEquipmentPoolableInstanceId                                  CucsManagedObjectId,
    cucsEquipmentPoolableDn                                          CucsManagedObjectDn,
    cucsEquipmentPoolableRn                                          SnmpAdminString,
    cucsEquipmentPoolableId                                          Unsigned64,
    cucsEquipmentPoolablePoolDn                                      SnmpAdminString
}

cucsEquipmentPoolableInstanceId OBJECT-TYPE
    SYNTAX       CucsManagedObjectId
    MAX-ACCESS   not-accessible
    STATUS       current
    DESCRIPTION
        "Instance identifier of the managed object."
    ::= { cucsEquipmentPoolableEntry 1 }

cucsEquipmentPoolableDn OBJECT-TYPE
    SYNTAX       CucsManagedObjectDn
    MAX-ACCESS   read-only
    STATUS       current
    DESCRIPTION
        "Cisco UCS equipment:Poolable:dn managed object property"
    ::= { cucsEquipmentPoolableEntry 2 }

cucsEquipmentPoolableRn OBJECT-TYPE
    SYNTAX       SnmpAdminString
    MAX-ACCESS   read-only
    STATUS       current
    DESCRIPTION
        "Cisco UCS equipment:Poolable:rn managed object property"
    ::= { cucsEquipmentPoolableEntry 3 }

cucsEquipmentPoolableId OBJECT-TYPE
    SYNTAX       Unsigned64
    MAX-ACCESS   read-only
    STATUS       current
    DESCRIPTION
        "Cisco UCS equipment:Poolable:id managed object property"
    ::= { cucsEquipmentPoolableEntry 5 }

cucsEquipmentPoolablePoolDn OBJECT-TYPE
    SYNTAX       SnmpAdminString
    MAX-ACCESS   read-only
    STATUS       current
    DESCRIPTION
        "Cisco UCS equipment:Poolable:poolDn managed object property"
    ::= { cucsEquipmentPoolableEntry 7 }

cucsEquipmentPooledChassisTable OBJECT-TYPE
    SYNTAX           SEQUENCE OF CucsEquipmentPooledChassisEntry
    MAX-ACCESS       not-accessible
    STATUS           current
    DESCRIPTION
        "Cisco UCS equipment:PooledChassis managed object table"
    ::= { cucsEquipmentObjects 216 }

cucsEquipmentPooledChassisEntry OBJECT-TYPE
    SYNTAX           CucsEquipmentPooledChassisEntry
    MAX-ACCESS       not-accessible
    STATUS           current
    DESCRIPTION
        "Entry for the cucsEquipmentPooledChassisTable table."
    INDEX { cucsEquipmentPooledChassisInstanceId }
    ::= { cucsEquipmentPooledChassisTable 1 }

CucsEquipmentPooledChassisEntry ::= SEQUENCE {
    cucsEquipmentPooledChassisInstanceId                             CucsManagedObjectId,
    cucsEquipmentPooledChassisDn                                     CucsManagedObjectDn,
    cucsEquipmentPooledChassisRn                                     SnmpAdminString,
    cucsEquipmentPooledChassisAssigned                               TruthValue,
    cucsEquipmentPooledChassisAssignedToDn                           SnmpAdminString,
    cucsEquipmentPooledChassisChassisId                              Gauge32,
    cucsEquipmentPooledChassisOwner                                  CucsEquipmentOwner,
    cucsEquipmentPooledChassisPoolableDn                             SnmpAdminString,
    cucsEquipmentPooledChassisPrevAssignedToDn                       SnmpAdminString,
    cucsEquipmentPooledChassisSlotId                                 Gauge32
}

cucsEquipmentPooledChassisInstanceId OBJECT-TYPE
    SYNTAX       CucsManagedObjectId
    MAX-ACCESS   not-accessible
    STATUS       current
    DESCRIPTION
        "Instance identifier of the managed object."
    ::= { cucsEquipmentPooledChassisEntry 1 }

cucsEquipmentPooledChassisDn OBJECT-TYPE
    SYNTAX       CucsManagedObjectDn
    MAX-ACCESS   read-only
    STATUS       current
    DESCRIPTION
        "Cisco UCS equipment:PooledChassis:dn managed object property"
    ::= { cucsEquipmentPooledChassisEntry 2 }

cucsEquipmentPooledChassisRn OBJECT-TYPE
    SYNTAX       SnmpAdminString
    MAX-ACCESS   read-only
    STATUS       current
    DESCRIPTION
        "Cisco UCS equipment:PooledChassis:rn managed object property"
    ::= { cucsEquipmentPooledChassisEntry 3 }

cucsEquipmentPooledChassisAssigned OBJECT-TYPE
    SYNTAX       TruthValue
    MAX-ACCESS   read-only
    STATUS       current
    DESCRIPTION
        "Cisco UCS equipment:PooledChassis:assigned managed
        object property"
    ::= { cucsEquipmentPooledChassisEntry 4 }

cucsEquipmentPooledChassisAssignedToDn OBJECT-TYPE
    SYNTAX       SnmpAdminString
    MAX-ACCESS   read-only
    STATUS       current
    DESCRIPTION
        "Cisco UCS equipment:PooledChassis:assignedToDn
        managed object property"
    ::= { cucsEquipmentPooledChassisEntry 5 }

cucsEquipmentPooledChassisChassisId OBJECT-TYPE
    SYNTAX       Gauge32
    MAX-ACCESS   read-only
    STATUS       current
    DESCRIPTION
        "Cisco UCS equipment:PooledChassis:chassisId managed
        object property"
    ::= { cucsEquipmentPooledChassisEntry 6 }

cucsEquipmentPooledChassisOwner OBJECT-TYPE
    SYNTAX       CucsEquipmentOwner
    MAX-ACCESS   read-only
    STATUS       current
    DESCRIPTION
        "Cisco UCS equipment:PooledChassis:owner managed object property"
    ::= { cucsEquipmentPooledChassisEntry 7 }

cucsEquipmentPooledChassisPoolableDn OBJECT-TYPE
    SYNTAX       SnmpAdminString
    MAX-ACCESS   read-only
    STATUS       current
    DESCRIPTION
        "Cisco UCS equipment:PooledChassis:poolableDn managed
        object property"
    ::= { cucsEquipmentPooledChassisEntry 8 }

cucsEquipmentPooledChassisPrevAssignedToDn OBJECT-TYPE
    SYNTAX       SnmpAdminString
    MAX-ACCESS   read-only
    STATUS       current
    DESCRIPTION
        "Cisco UCS equipment:PooledChassis:prevAssignedToDn
        managed object property"
    ::= { cucsEquipmentPooledChassisEntry 9 }

cucsEquipmentPooledChassisSlotId OBJECT-TYPE
    SYNTAX       Gauge32
    MAX-ACCESS   read-only
    STATUS       current
    DESCRIPTION
        "Cisco UCS equipment:PooledChassis:slotId managed object property"
    ::= { cucsEquipmentPooledChassisEntry 10 }

cucsEquipmentPoolingPolicyTable OBJECT-TYPE
    SYNTAX           SEQUENCE OF CucsEquipmentPoolingPolicyEntry
    MAX-ACCESS       not-accessible
    STATUS           current
    DESCRIPTION
        "Cisco UCS equipment:PoolingPolicy managed object table"
    ::= { cucsEquipmentObjects 194 }

cucsEquipmentPoolingPolicyEntry OBJECT-TYPE
    SYNTAX           CucsEquipmentPoolingPolicyEntry
    MAX-ACCESS       not-accessible
    STATUS           current
    DESCRIPTION
        "Entry for the cucsEquipmentPoolingPolicyTable table."
    INDEX { cucsEquipmentPoolingPolicyInstanceId }
    ::= { cucsEquipmentPoolingPolicyTable 1 }

CucsEquipmentPoolingPolicyEntry ::= SEQUENCE {
    cucsEquipmentPoolingPolicyInstanceId                             CucsManagedObjectId,
    cucsEquipmentPoolingPolicyDn                                     CucsManagedObjectDn,
    cucsEquipmentPoolingPolicyRn                                     SnmpAdminString,
    cucsEquipmentPoolingPolicyDescr                                  SnmpAdminString,
    cucsEquipmentPoolingPolicyIntId                                  SnmpAdminString,
    cucsEquipmentPoolingPolicyName                                   SnmpAdminString,
    cucsEquipmentPoolingPolicyPolicyLevel                            Gauge32,
    cucsEquipmentPoolingPolicyPolicyOwner                            CucsPolicyPolicyOwner,
    cucsEquipmentPoolingPolicyPoolDn                                 SnmpAdminString,
    cucsEquipmentPoolingPolicyQualifier                              SnmpAdminString
}

cucsEquipmentPoolingPolicyInstanceId OBJECT-TYPE
    SYNTAX       CucsManagedObjectId
    MAX-ACCESS   not-accessible
    STATUS       current
    DESCRIPTION
        "Instance identifier of the managed object."
    ::= { cucsEquipmentPoolingPolicyEntry 1 }

cucsEquipmentPoolingPolicyDn OBJECT-TYPE
    SYNTAX       CucsManagedObjectDn
    MAX-ACCESS   read-only
    STATUS       current
    DESCRIPTION
        "Cisco UCS equipment:PoolingPolicy:dn managed object property"
    ::= { cucsEquipmentPoolingPolicyEntry 2 }

cucsEquipmentPoolingPolicyRn OBJECT-TYPE
    SYNTAX       SnmpAdminString
    MAX-ACCESS   read-only
    STATUS       current
    DESCRIPTION
        "Cisco UCS equipment:PoolingPolicy:rn managed object property"
    ::= { cucsEquipmentPoolingPolicyEntry 3 }

cucsEquipmentPoolingPolicyDescr OBJECT-TYPE
    SYNTAX       SnmpAdminString
    MAX-ACCESS   read-only
    STATUS       current
    DESCRIPTION
        "Cisco UCS equipment:PoolingPolicy:descr managed object property"
    ::= { cucsEquipmentPoolingPolicyEntry 4 }

cucsEquipmentPoolingPolicyIntId OBJECT-TYPE
    SYNTAX       SnmpAdminString
    MAX-ACCESS   read-only
    STATUS       current
    DESCRIPTION
        "Cisco UCS equipment:PoolingPolicy:intId managed object property"
    ::= { cucsEquipmentPoolingPolicyEntry 5 }

cucsEquipmentPoolingPolicyName OBJECT-TYPE
    SYNTAX       SnmpAdminString
    MAX-ACCESS   read-only
    STATUS       current
    DESCRIPTION
        "Cisco UCS equipment:PoolingPolicy:name managed object property"
    ::= { cucsEquipmentPoolingPolicyEntry 6 }

cucsEquipmentPoolingPolicyPolicyLevel OBJECT-TYPE
    SYNTAX       Gauge32
    MAX-ACCESS   read-only
    STATUS       current
    DESCRIPTION
        "Cisco UCS equipment:PoolingPolicy:policyLevel
        managed object property"
    ::= { cucsEquipmentPoolingPolicyEntry 7 }

cucsEquipmentPoolingPolicyPolicyOwner OBJECT-TYPE
    SYNTAX       CucsPolicyPolicyOwner
    MAX-ACCESS   read-only
    STATUS       current
    DESCRIPTION
        "Cisco UCS equipment:PoolingPolicy:policyOwner
        managed object property"
    ::= { cucsEquipmentPoolingPolicyEntry 8 }

cucsEquipmentPoolingPolicyPoolDn OBJECT-TYPE
    SYNTAX       SnmpAdminString
    MAX-ACCESS   read-only
    STATUS       current
    DESCRIPTION
        "Cisco UCS equipment:PoolingPolicy:poolDn managed object property"
    ::= { cucsEquipmentPoolingPolicyEntry 9 }

cucsEquipmentPoolingPolicyQualifier OBJECT-TYPE
    SYNTAX       SnmpAdminString
    MAX-ACCESS   read-only
    STATUS       current
    DESCRIPTION
        "Cisco UCS equipment:PoolingPolicy:qualifier managed
        object property"
    ::= { cucsEquipmentPoolingPolicyEntry 10 }

cucsEquipmentPortCapTable OBJECT-TYPE
    SYNTAX           SEQUENCE OF CucsEquipmentPortCapEntry
    MAX-ACCESS       not-accessible
    STATUS           current
    DESCRIPTION
        "Cisco UCS equipment:PortCap managed object table"
    ::= { cucsEquipmentObjects 134 }

cucsEquipmentPortCapEntry OBJECT-TYPE
    SYNTAX           CucsEquipmentPortCapEntry
    MAX-ACCESS       not-accessible
    STATUS           current
    DESCRIPTION
        "Entry for the cucsEquipmentPortCapTable table."
    INDEX { cucsEquipmentPortCapInstanceId }
    ::= { cucsEquipmentPortCapTable 1 }

CucsEquipmentPortCapEntry ::= SEQUENCE {
    cucsEquipmentPortCapInstanceId                                   CucsManagedObjectId,
    cucsEquipmentPortCapDn                                           CucsManagedObjectDn,
    cucsEquipmentPortCapRn                                           SnmpAdminString,
    cucsEquipmentPortCapBreakoutPortSpeedGb                          Gauge32,
    cucsEquipmentPortCapCountBreakoutPorts                           Gauge32,
    cucsEquipmentPortCapDescr                                        SnmpAdminString,
    cucsEquipmentPortCapEndPortId                                    Gauge32,
    cucsEquipmentPortCapIntId                                        SnmpAdminString,
    cucsEquipmentPortCapName                                         SnmpAdminString,
    cucsEquipmentPortCapPolicyLevel                                  Gauge32,
    cucsEquipmentPortCapPolicyOwner                                  CucsPolicyPolicyOwner,
    cucsEquipmentPortCapPortAttribute                                CucsEquipmentPortAttribute,
    cucsEquipmentPortCapPortSpeedGb                                  Gauge32,
    cucsEquipmentPortCapStartPortId                                  Gauge32
}

cucsEquipmentPortCapInstanceId OBJECT-TYPE
    SYNTAX       CucsManagedObjectId
    MAX-ACCESS   not-accessible
    STATUS       current
    DESCRIPTION
        "Instance identifier of the managed object."
    ::= { cucsEquipmentPortCapEntry 1 }

cucsEquipmentPortCapDn OBJECT-TYPE
    SYNTAX       CucsManagedObjectDn
    MAX-ACCESS   read-only
    STATUS       current
    DESCRIPTION
        "Cisco UCS equipment:PortCap:dn managed object property"
    ::= { cucsEquipmentPortCapEntry 2 }

cucsEquipmentPortCapRn OBJECT-TYPE
    SYNTAX       SnmpAdminString
    MAX-ACCESS   read-only
    STATUS       current
    DESCRIPTION
        "Cisco UCS equipment:PortCap:rn managed object property"
    ::= { cucsEquipmentPortCapEntry 3 }

cucsEquipmentPortCapBreakoutPortSpeedGb OBJECT-TYPE
    SYNTAX       Gauge32
    MAX-ACCESS   read-only
    STATUS       current
    DESCRIPTION
        "Cisco UCS equipment:PortCap:breakoutPortSpeedGb
        managed object property"
    ::= { cucsEquipmentPortCapEntry 4 }

cucsEquipmentPortCapCountBreakoutPorts OBJECT-TYPE
    SYNTAX       Gauge32
    MAX-ACCESS   read-only
    STATUS       current
    DESCRIPTION
        "Cisco UCS equipment:PortCap:countBreakoutPorts
        managed object property"
    ::= { cucsEquipmentPortCapEntry 5 }

cucsEquipmentPortCapDescr OBJECT-TYPE
    SYNTAX       SnmpAdminString
    MAX-ACCESS   read-only
    STATUS       current
    DESCRIPTION
        "Cisco UCS equipment:PortCap:descr managed object property"
    ::= { cucsEquipmentPortCapEntry 6 }

cucsEquipmentPortCapEndPortId OBJECT-TYPE
    SYNTAX       Gauge32
    MAX-ACCESS   read-only
    STATUS       current
    DESCRIPTION
        "Cisco UCS equipment:PortCap:endPortId managed object property"
    ::= { cucsEquipmentPortCapEntry 7 }

cucsEquipmentPortCapIntId OBJECT-TYPE
    SYNTAX       SnmpAdminString
    MAX-ACCESS   read-only
    STATUS       current
    DESCRIPTION
        "Cisco UCS equipment:PortCap:intId managed object property"
    ::= { cucsEquipmentPortCapEntry 8 }

cucsEquipmentPortCapName OBJECT-TYPE
    SYNTAX       SnmpAdminString
    MAX-ACCESS   read-only
    STATUS       current
    DESCRIPTION
        "Cisco UCS equipment:PortCap:name managed object property"
    ::= { cucsEquipmentPortCapEntry 9 }

cucsEquipmentPortCapPolicyLevel OBJECT-TYPE
    SYNTAX       Gauge32
    MAX-ACCESS   read-only
    STATUS       current
    DESCRIPTION
        "Cisco UCS equipment:PortCap:policyLevel managed object property"
    ::= { cucsEquipmentPortCapEntry 10 }

cucsEquipmentPortCapPolicyOwner OBJECT-TYPE
    SYNTAX       CucsPolicyPolicyOwner
    MAX-ACCESS   read-only
    STATUS       current
    DESCRIPTION
        "Cisco UCS equipment:PortCap:policyOwner managed object property"
    ::= { cucsEquipmentPortCapEntry 11 }

cucsEquipmentPortCapPortAttribute OBJECT-TYPE
    SYNTAX       CucsEquipmentPortAttribute
    MAX-ACCESS   read-only
    STATUS       current
    DESCRIPTION
        "Cisco UCS equipment:PortCap:portAttribute managed
        object property"
    ::= { cucsEquipmentPortCapEntry 12 }

cucsEquipmentPortCapPortSpeedGb OBJECT-TYPE
    SYNTAX       Gauge32
    MAX-ACCESS   read-only
    STATUS       current
    DESCRIPTION
        "Cisco UCS equipment:PortCap:portSpeedGb managed object property"
    ::= { cucsEquipmentPortCapEntry 13 }

cucsEquipmentPortCapStartPortId OBJECT-TYPE
    SYNTAX       Gauge32
    MAX-ACCESS   read-only
    STATUS       current
    DESCRIPTION
        "Cisco UCS equipment:PortCap:startPortId managed object property"
    ::= { cucsEquipmentPortCapEntry 14 }

cucsEquipmentPortGroupAggregationDefTable OBJECT-TYPE
    SYNTAX           SEQUENCE OF CucsEquipmentPortGroupAggregationDefEntry
    MAX-ACCESS       not-accessible
    STATUS           current
    DESCRIPTION
        "Cisco UCS equipment:PortGroupAggregationDef managed object table"
    ::= { cucsEquipmentObjects 88 }

cucsEquipmentPortGroupAggregationDefEntry OBJECT-TYPE
    SYNTAX           CucsEquipmentPortGroupAggregationDefEntry
    MAX-ACCESS       not-accessible
    STATUS           current
    DESCRIPTION
        "Entry for the cucsEquipmentPortGroupAggregationDefTable table."
    INDEX { cucsEquipmentPortGroupAggregationDefInstanceId }
    ::= { cucsEquipmentPortGroupAggregationDefTable 1 }

CucsEquipmentPortGroupAggregationDefEntry ::= SEQUENCE {
    cucsEquipmentPortGroupAggregationDefInstanceId                   CucsManagedObjectId,
    cucsEquipmentPortGroupAggregationDefDn                           CucsManagedObjectDn,
    cucsEquipmentPortGroupAggregationDefRn                           SnmpAdminString,
    cucsEquipmentPortGroupAggregationDefAggregationCap               CucsComputeLinkAggregationCap,
    cucsEquipmentPortGroupAggregationDefDescr                        SnmpAdminString,
    cucsEquipmentPortGroupAggregationDefIntId                        SnmpAdminString,
    cucsEquipmentPortGroupAggregationDefName                         SnmpAdminString,
    cucsEquipmentPortGroupAggregationDefType                         CucsPortGroupType,
    cucsEquipmentPortGroupAggregationDefPolicyLevel                  Gauge32,
    cucsEquipmentPortGroupAggregationDefPolicyOwner                  CucsPolicyPolicyOwner,
    cucsEquipmentPortGroupAggregationDefHw40GPortGroupCap            TruthValue
}

cucsEquipmentPortGroupAggregationDefInstanceId OBJECT-TYPE
    SYNTAX       CucsManagedObjectId
    MAX-ACCESS   not-accessible
    STATUS       current
    DESCRIPTION
        "Instance identifier of the managed object."
    ::= { cucsEquipmentPortGroupAggregationDefEntry 1 }

cucsEquipmentPortGroupAggregationDefDn OBJECT-TYPE
    SYNTAX       CucsManagedObjectDn
    MAX-ACCESS   read-only
    STATUS       current
    DESCRIPTION
        "Cisco UCS equipment:PortGroupAggregationDef:dn
        managed object property"
    ::= { cucsEquipmentPortGroupAggregationDefEntry 2 }

cucsEquipmentPortGroupAggregationDefRn OBJECT-TYPE
    SYNTAX       SnmpAdminString
    MAX-ACCESS   read-only
    STATUS       current
    DESCRIPTION
        "Cisco UCS equipment:PortGroupAggregationDef:rn
        managed object property"
    ::= { cucsEquipmentPortGroupAggregationDefEntry 3 }

cucsEquipmentPortGroupAggregationDefAggregationCap OBJECT-TYPE
    SYNTAX       CucsComputeLinkAggregationCap
    MAX-ACCESS   read-only
    STATUS       current
    DESCRIPTION
        "Cisco UCS equipment:PortGroupAggregationDef:aggregationCap
        managed object property"
    ::= { cucsEquipmentPortGroupAggregationDefEntry 4 }

cucsEquipmentPortGroupAggregationDefDescr OBJECT-TYPE
    SYNTAX       SnmpAdminString
    MAX-ACCESS   read-only
    STATUS       current
    DESCRIPTION
        "Cisco UCS equipment:PortGroupAggregationDef:descr
        managed object property"
    ::= { cucsEquipmentPortGroupAggregationDefEntry 5 }

cucsEquipmentPortGroupAggregationDefIntId OBJECT-TYPE
    SYNTAX       SnmpAdminString
    MAX-ACCESS   read-only
    STATUS       current
    DESCRIPTION
        "Cisco UCS equipment:PortGroupAggregationDef:intId
        managed object property"
    ::= { cucsEquipmentPortGroupAggregationDefEntry 6 }

cucsEquipmentPortGroupAggregationDefName OBJECT-TYPE
    SYNTAX       SnmpAdminString
    MAX-ACCESS   read-only
    STATUS       current
    DESCRIPTION
        "Cisco UCS equipment:PortGroupAggregationDef:name
        managed object property"
    ::= { cucsEquipmentPortGroupAggregationDefEntry 7 }

cucsEquipmentPortGroupAggregationDefType OBJECT-TYPE
    SYNTAX       CucsPortGroupType
    MAX-ACCESS   read-only
    STATUS       current
    DESCRIPTION
        "Cisco UCS equipment:PortGroupAggregationDef:type
        managed object property"
    ::= { cucsEquipmentPortGroupAggregationDefEntry 8 }

cucsEquipmentPortGroupAggregationDefPolicyLevel OBJECT-TYPE
    SYNTAX       Gauge32
    MAX-ACCESS   read-only
    STATUS       current
    DESCRIPTION
        "Cisco UCS equipment:PortGroupAggregationDef:policyLevel
        managed object property"
    ::= { cucsEquipmentPortGroupAggregationDefEntry 9 }

cucsEquipmentPortGroupAggregationDefPolicyOwner OBJECT-TYPE
    SYNTAX       CucsPolicyPolicyOwner
    MAX-ACCESS   read-only
    STATUS       current
    DESCRIPTION
        "Cisco UCS equipment:PortGroupAggregationDef:policyOwner
        managed object property"
    ::= { cucsEquipmentPortGroupAggregationDefEntry 10 }

cucsEquipmentPortGroupAggregationDefHw40GPortGroupCap OBJECT-TYPE
    SYNTAX       TruthValue
    MAX-ACCESS   read-only
    STATUS       current
    DESCRIPTION
        "Cisco UCS equipment:PortGroupAggregationDef:hw40GPortGroupCap
        managed object property"
    ::= { cucsEquipmentPortGroupAggregationDefEntry 11 }

cucsEquipmentPortGroupDefTable OBJECT-TYPE
    SYNTAX           SEQUENCE OF CucsEquipmentPortGroupDefEntry
    MAX-ACCESS       not-accessible
    STATUS           current
    DESCRIPTION
        "Cisco UCS equipment:PortGroupDef managed object table"
    ::= { cucsEquipmentObjects 53 }

cucsEquipmentPortGroupDefEntry OBJECT-TYPE
    SYNTAX           CucsEquipmentPortGroupDefEntry
    MAX-ACCESS       not-accessible
    STATUS           current
    DESCRIPTION
        "Entry for the cucsEquipmentPortGroupDefTable table."
    INDEX { cucsEquipmentPortGroupDefInstanceId }
    ::= { cucsEquipmentPortGroupDefTable 1 }

CucsEquipmentPortGroupDefEntry ::= SEQUENCE {
    cucsEquipmentPortGroupDefInstanceId                              CucsManagedObjectId,
    cucsEquipmentPortGroupDefDn                                      CucsManagedObjectDn,
    cucsEquipmentPortGroupDefRn                                      SnmpAdminString,
    cucsEquipmentPortGroupDefDescr                                   SnmpAdminString,
    cucsEquipmentPortGroupDefIntId                                   SnmpAdminString,
    cucsEquipmentPortGroupDefName                                    SnmpAdminString,
    cucsEquipmentPortGroupDefNumberOfPorts                           Gauge32,
    cucsEquipmentPortGroupDefType                                    CucsPortGroupType,
    cucsEquipmentPortGroupDefPolicyLevel                             Gauge32,
    cucsEquipmentPortGroupDefPolicyOwner                             CucsPolicyPolicyOwner,
    cucsEquipmentPortGroupDefStartPortId                             Gauge32
}

cucsEquipmentPortGroupDefInstanceId OBJECT-TYPE
    SYNTAX       CucsManagedObjectId
    MAX-ACCESS   not-accessible
    STATUS       current
    DESCRIPTION
        "Instance identifier of the managed object."
    ::= { cucsEquipmentPortGroupDefEntry 1 }

cucsEquipmentPortGroupDefDn OBJECT-TYPE
    SYNTAX       CucsManagedObjectDn
    MAX-ACCESS   read-only
    STATUS       current
    DESCRIPTION
        "Cisco UCS equipment:PortGroupDef:dn managed object property"
    ::= { cucsEquipmentPortGroupDefEntry 2 }

cucsEquipmentPortGroupDefRn OBJECT-TYPE
    SYNTAX       SnmpAdminString
    MAX-ACCESS   read-only
    STATUS       current
    DESCRIPTION
        "Cisco UCS equipment:PortGroupDef:rn managed object property"
    ::= { cucsEquipmentPortGroupDefEntry 3 }

cucsEquipmentPortGroupDefDescr OBJECT-TYPE
    SYNTAX       SnmpAdminString
    MAX-ACCESS   read-only
    STATUS       current
    DESCRIPTION
        "Cisco UCS equipment:PortGroupDef:descr managed object property"
    ::= { cucsEquipmentPortGroupDefEntry 4 }

cucsEquipmentPortGroupDefIntId OBJECT-TYPE
    SYNTAX       SnmpAdminString
    MAX-ACCESS   read-only
    STATUS       current
    DESCRIPTION
        "Cisco UCS equipment:PortGroupDef:intId managed object property"
    ::= { cucsEquipmentPortGroupDefEntry 5 }

cucsEquipmentPortGroupDefName OBJECT-TYPE
    SYNTAX       SnmpAdminString
    MAX-ACCESS   read-only
    STATUS       current
    DESCRIPTION
        "Cisco UCS equipment:PortGroupDef:name managed object property"
    ::= { cucsEquipmentPortGroupDefEntry 6 }

cucsEquipmentPortGroupDefNumberOfPorts OBJECT-TYPE
    SYNTAX       Gauge32
    MAX-ACCESS   read-only
    STATUS       current
    DESCRIPTION
        "Cisco UCS equipment:PortGroupDef:numberOfPorts
        managed object property"
    ::= { cucsEquipmentPortGroupDefEntry 7 }

cucsEquipmentPortGroupDefType OBJECT-TYPE
    SYNTAX       CucsPortGroupType
    MAX-ACCESS   read-only
    STATUS       current
    DESCRIPTION
        "Cisco UCS equipment:PortGroupDef:type managed object property"
    ::= { cucsEquipmentPortGroupDefEntry 8 }

cucsEquipmentPortGroupDefPolicyLevel OBJECT-TYPE
    SYNTAX       Gauge32
    MAX-ACCESS   read-only
    STATUS       current
    DESCRIPTION
        "Cisco UCS equipment:PortGroupDef:policyLevel managed
        object property"
    ::= { cucsEquipmentPortGroupDefEntry 9 }

cucsEquipmentPortGroupDefPolicyOwner OBJECT-TYPE
    SYNTAX       CucsPolicyPolicyOwner
    MAX-ACCESS   read-only
    STATUS       current
    DESCRIPTION
        "Cisco UCS equipment:PortGroupDef:policyOwner managed
        object property"
    ::= { cucsEquipmentPortGroupDefEntry 10 }

cucsEquipmentPortGroupDefStartPortId OBJECT-TYPE
    SYNTAX       Gauge32
    MAX-ACCESS   read-only
    STATUS       current
    DESCRIPTION
        "Cisco UCS equipment:PortGroupDef:startPortId managed
        object property"
    ::= { cucsEquipmentPortGroupDefEntry 11 }

cucsEquipmentPortGroupSwComplexDefTable OBJECT-TYPE
    SYNTAX           SEQUENCE OF CucsEquipmentPortGroupSwComplexDefEntry
    MAX-ACCESS       not-accessible
    STATUS           current
    DESCRIPTION
        "Cisco UCS equipment:PortGroupSwComplexDef managed object table"
    ::= { cucsEquipmentObjects 89 }

cucsEquipmentPortGroupSwComplexDefEntry OBJECT-TYPE
    SYNTAX           CucsEquipmentPortGroupSwComplexDefEntry
    MAX-ACCESS       not-accessible
    STATUS           current
    DESCRIPTION
        "Entry for the cucsEquipmentPortGroupSwComplexDefTable table."
    INDEX { cucsEquipmentPortGroupSwComplexDefInstanceId }
    ::= { cucsEquipmentPortGroupSwComplexDefTable 1 }

CucsEquipmentPortGroupSwComplexDefEntry ::= SEQUENCE {
    cucsEquipmentPortGroupSwComplexDefInstanceId                     CucsManagedObjectId,
    cucsEquipmentPortGroupSwComplexDefDn                             CucsManagedObjectDn,
    cucsEquipmentPortGroupSwComplexDefRn                             SnmpAdminString,
    cucsEquipmentPortGroupSwComplexDefAsic                           CucsEquipmentAsicType,
    cucsEquipmentPortGroupSwComplexDefDescr                          SnmpAdminString,
    cucsEquipmentPortGroupSwComplexDefIntId                          SnmpAdminString,
    cucsEquipmentPortGroupSwComplexDefName                           SnmpAdminString,
    cucsEquipmentPortGroupSwComplexDefPortCapacity                   Gauge32,
    cucsEquipmentPortGroupSwComplexDefSwComplexCapacity              Gauge32,
    cucsEquipmentPortGroupSwComplexDefVifCapacity                    Gauge32,
    cucsEquipmentPortGroupSwComplexDefPolicyLevel                    Gauge32,
    cucsEquipmentPortGroupSwComplexDefPolicyOwner                    CucsPolicyPolicyOwner
}

cucsEquipmentPortGroupSwComplexDefInstanceId OBJECT-TYPE
    SYNTAX       CucsManagedObjectId
    MAX-ACCESS   not-accessible
    STATUS       current
    DESCRIPTION
        "Instance identifier of the managed object."
    ::= { cucsEquipmentPortGroupSwComplexDefEntry 1 }

cucsEquipmentPortGroupSwComplexDefDn OBJECT-TYPE
    SYNTAX       CucsManagedObjectDn
    MAX-ACCESS   read-only
    STATUS       current
    DESCRIPTION
        "Cisco UCS equipment:PortGroupSwComplexDef:dn managed
        object property"
    ::= { cucsEquipmentPortGroupSwComplexDefEntry 2 }

cucsEquipmentPortGroupSwComplexDefRn OBJECT-TYPE
    SYNTAX       SnmpAdminString
    MAX-ACCESS   read-only
    STATUS       current
    DESCRIPTION
        "Cisco UCS equipment:PortGroupSwComplexDef:rn managed
        object property"
    ::= { cucsEquipmentPortGroupSwComplexDefEntry 3 }

cucsEquipmentPortGroupSwComplexDefAsic OBJECT-TYPE
    SYNTAX       CucsEquipmentAsicType
    MAX-ACCESS   read-only
    STATUS       current
    DESCRIPTION
        "Cisco UCS equipment:PortGroupSwComplexDef:asic
        managed object property"
    ::= { cucsEquipmentPortGroupSwComplexDefEntry 4 }

cucsEquipmentPortGroupSwComplexDefDescr OBJECT-TYPE
    SYNTAX       SnmpAdminString
    MAX-ACCESS   read-only
    STATUS       current
    DESCRIPTION
        "Cisco UCS equipment:PortGroupSwComplexDef:descr
        managed object property"
    ::= { cucsEquipmentPortGroupSwComplexDefEntry 5 }

cucsEquipmentPortGroupSwComplexDefIntId OBJECT-TYPE
    SYNTAX       SnmpAdminString
    MAX-ACCESS   read-only
    STATUS       current
    DESCRIPTION
        "Cisco UCS equipment:PortGroupSwComplexDef:intId
        managed object property"
    ::= { cucsEquipmentPortGroupSwComplexDefEntry 6 }

cucsEquipmentPortGroupSwComplexDefName OBJECT-TYPE
    SYNTAX       SnmpAdminString
    MAX-ACCESS   read-only
    STATUS       current
    DESCRIPTION
        "Cisco UCS equipment:PortGroupSwComplexDef:name
        managed object property"
    ::= { cucsEquipmentPortGroupSwComplexDefEntry 7 }

cucsEquipmentPortGroupSwComplexDefPortCapacity OBJECT-TYPE
    SYNTAX       Gauge32
    MAX-ACCESS   read-only
    STATUS       current
    DESCRIPTION
        "Cisco UCS equipment:PortGroupSwComplexDef:portCapacity
        managed object property"
    ::= { cucsEquipmentPortGroupSwComplexDefEntry 8 }

cucsEquipmentPortGroupSwComplexDefSwComplexCapacity OBJECT-TYPE
    SYNTAX       Gauge32
    MAX-ACCESS   read-only
    STATUS       current
    DESCRIPTION
        "Cisco UCS equipment:PortGroupSwComplexDef:swComplexCapacity
        managed object property"
    ::= { cucsEquipmentPortGroupSwComplexDefEntry 9 }

cucsEquipmentPortGroupSwComplexDefVifCapacity OBJECT-TYPE
    SYNTAX       Gauge32
    MAX-ACCESS   read-only
    STATUS       current
    DESCRIPTION
        "Cisco UCS equipment:PortGroupSwComplexDef:vifCapacity
        managed object property"
    ::= { cucsEquipmentPortGroupSwComplexDefEntry 10 }

cucsEquipmentPortGroupSwComplexDefPolicyLevel OBJECT-TYPE
    SYNTAX       Gauge32
    MAX-ACCESS   read-only
    STATUS       current
    DESCRIPTION
        "Cisco UCS equipment:PortGroupSwComplexDef:policyLevel
        managed object property"
    ::= { cucsEquipmentPortGroupSwComplexDefEntry 11 }

cucsEquipmentPortGroupSwComplexDefPolicyOwner OBJECT-TYPE
    SYNTAX       CucsPolicyPolicyOwner
    MAX-ACCESS   read-only
    STATUS       current
    DESCRIPTION
        "Cisco UCS equipment:PortGroupSwComplexDef:policyOwner
        managed object property"
    ::= { cucsEquipmentPortGroupSwComplexDefEntry 12 }

cucsEquipmentPortSwComplexRefTable OBJECT-TYPE
    SYNTAX           SEQUENCE OF CucsEquipmentPortSwComplexRefEntry
    MAX-ACCESS       not-accessible
    STATUS           current
    DESCRIPTION
        "Cisco UCS equipment:PortSwComplexRef managed object table"
    ::= { cucsEquipmentObjects 90 }

cucsEquipmentPortSwComplexRefEntry OBJECT-TYPE
    SYNTAX           CucsEquipmentPortSwComplexRefEntry
    MAX-ACCESS       not-accessible
    STATUS           current
    DESCRIPTION
        "Entry for the cucsEquipmentPortSwComplexRefTable table."
    INDEX { cucsEquipmentPortSwComplexRefInstanceId }
    ::= { cucsEquipmentPortSwComplexRefTable 1 }

CucsEquipmentPortSwComplexRefEntry ::= SEQUENCE {
    cucsEquipmentPortSwComplexRefInstanceId                          CucsManagedObjectId,
    cucsEquipmentPortSwComplexRefDn                                  CucsManagedObjectDn,
    cucsEquipmentPortSwComplexRefRn                                  SnmpAdminString,
    cucsEquipmentPortSwComplexRefDescr                               SnmpAdminString,
    cucsEquipmentPortSwComplexRefIntId                               SnmpAdminString,
    cucsEquipmentPortSwComplexRefMaxPortId                           Gauge32,
    cucsEquipmentPortSwComplexRefMinPortId                           Gauge32,
    cucsEquipmentPortSwComplexRefName                                SnmpAdminString,
    cucsEquipmentPortSwComplexRefSlotId                              Gauge32,
    cucsEquipmentPortSwComplexRefSwComplexId                         Gauge32,
    cucsEquipmentPortSwComplexRefPolicyLevel                         Gauge32,
    cucsEquipmentPortSwComplexRefPolicyOwner                         CucsPolicyPolicyOwner
}

cucsEquipmentPortSwComplexRefInstanceId OBJECT-TYPE
    SYNTAX       CucsManagedObjectId
    MAX-ACCESS   not-accessible
    STATUS       current
    DESCRIPTION
        "Instance identifier of the managed object."
    ::= { cucsEquipmentPortSwComplexRefEntry 1 }

cucsEquipmentPortSwComplexRefDn OBJECT-TYPE
    SYNTAX       CucsManagedObjectDn
    MAX-ACCESS   read-only
    STATUS       current
    DESCRIPTION
        "Cisco UCS equipment:PortSwComplexRef:dn managed object property"
    ::= { cucsEquipmentPortSwComplexRefEntry 2 }

cucsEquipmentPortSwComplexRefRn OBJECT-TYPE
    SYNTAX       SnmpAdminString
    MAX-ACCESS   read-only
    STATUS       current
    DESCRIPTION
        "Cisco UCS equipment:PortSwComplexRef:rn managed object property"
    ::= { cucsEquipmentPortSwComplexRefEntry 3 }

cucsEquipmentPortSwComplexRefDescr OBJECT-TYPE
    SYNTAX       SnmpAdminString
    MAX-ACCESS   read-only
    STATUS       current
    DESCRIPTION
        "Cisco UCS equipment:PortSwComplexRef:descr managed
        object property"
    ::= { cucsEquipmentPortSwComplexRefEntry 4 }

cucsEquipmentPortSwComplexRefIntId OBJECT-TYPE
    SYNTAX       SnmpAdminString
    MAX-ACCESS   read-only
    STATUS       current
    DESCRIPTION
        "Cisco UCS equipment:PortSwComplexRef:intId managed
        object property"
    ::= { cucsEquipmentPortSwComplexRefEntry 5 }

cucsEquipmentPortSwComplexRefMaxPortId OBJECT-TYPE
    SYNTAX       Gauge32
    MAX-ACCESS   read-only
    STATUS       current
    DESCRIPTION
        "Cisco UCS equipment:PortSwComplexRef:maxPortId
        managed object property"
    ::= { cucsEquipmentPortSwComplexRefEntry 6 }

cucsEquipmentPortSwComplexRefMinPortId OBJECT-TYPE
    SYNTAX       Gauge32
    MAX-ACCESS   read-only
    STATUS       current
    DESCRIPTION
        "Cisco UCS equipment:PortSwComplexRef:minPortId
        managed object property"
    ::= { cucsEquipmentPortSwComplexRefEntry 7 }

cucsEquipmentPortSwComplexRefName OBJECT-TYPE
    SYNTAX       SnmpAdminString
    MAX-ACCESS   read-only
    STATUS       current
    DESCRIPTION
        "Cisco UCS equipment:PortSwComplexRef:name managed
        object property"
    ::= { cucsEquipmentPortSwComplexRefEntry 8 }

cucsEquipmentPortSwComplexRefSlotId OBJECT-TYPE
    SYNTAX       Gauge32
    MAX-ACCESS   read-only
    STATUS       current
    DESCRIPTION
        "Cisco UCS equipment:PortSwComplexRef:slotId managed
        object property"
    ::= { cucsEquipmentPortSwComplexRefEntry 9 }

cucsEquipmentPortSwComplexRefSwComplexId OBJECT-TYPE
    SYNTAX       Gauge32
    MAX-ACCESS   read-only
    STATUS       current
    DESCRIPTION
        "Cisco UCS equipment:PortSwComplexRef:swComplexId
        managed object property"
    ::= { cucsEquipmentPortSwComplexRefEntry 10 }

cucsEquipmentPortSwComplexRefPolicyLevel OBJECT-TYPE
    SYNTAX       Gauge32
    MAX-ACCESS   read-only
    STATUS       current
    DESCRIPTION
        "Cisco UCS equipment:PortSwComplexRef:policyLevel
        managed object property"
    ::= { cucsEquipmentPortSwComplexRefEntry 11 }

cucsEquipmentPortSwComplexRefPolicyOwner OBJECT-TYPE
    SYNTAX       CucsPolicyPolicyOwner
    MAX-ACCESS   read-only
    STATUS       current
    DESCRIPTION
        "Cisco UCS equipment:PortSwComplexRef:policyOwner
        managed object property"
    ::= { cucsEquipmentPortSwComplexRefEntry 12 }

cucsEquipmentPowerCapDefTable OBJECT-TYPE
    SYNTAX           SEQUENCE OF CucsEquipmentPowerCapDefEntry
    MAX-ACCESS       not-accessible
    STATUS           current
    DESCRIPTION
        "Cisco UCS equipment:PowerCapDef managed object table"
    ::= { cucsEquipmentObjects 135 }

cucsEquipmentPowerCapDefEntry OBJECT-TYPE
    SYNTAX           CucsEquipmentPowerCapDefEntry
    MAX-ACCESS       not-accessible
    STATUS           current
    DESCRIPTION
        "Entry for the cucsEquipmentPowerCapDefTable table."
    INDEX { cucsEquipmentPowerCapDefInstanceId }
    ::= { cucsEquipmentPowerCapDefTable 1 }

CucsEquipmentPowerCapDefEntry ::= SEQUENCE {
    cucsEquipmentPowerCapDefInstanceId                               CucsManagedObjectId,
    cucsEquipmentPowerCapDefDn                                       CucsManagedObjectDn,
    cucsEquipmentPowerCapDefRn                                       SnmpAdminString,
    cucsEquipmentPowerCapDefMinBiosVersion                           SnmpAdminString,
    cucsEquipmentPowerCapDefMinCimcVersion                           SnmpAdminString,
    cucsEquipmentPowerCapDefMinCmcVersion                            SnmpAdminString,
    cucsEquipmentPowerCapDefProfileMethod                            CucsEquipmentPowerCapDefProfileMethod,
    cucsEquipmentPowerCapDefIsPowerDeploymentNeeded                  TruthValue
}

cucsEquipmentPowerCapDefInstanceId OBJECT-TYPE
    SYNTAX       CucsManagedObjectId
    MAX-ACCESS   not-accessible
    STATUS       current
    DESCRIPTION
        "Instance identifier of the managed object."
    ::= { cucsEquipmentPowerCapDefEntry 1 }

cucsEquipmentPowerCapDefDn OBJECT-TYPE
    SYNTAX       CucsManagedObjectDn
    MAX-ACCESS   read-only
    STATUS       current
    DESCRIPTION
        "Cisco UCS equipment:PowerCapDef:dn managed object property"
    ::= { cucsEquipmentPowerCapDefEntry 2 }

cucsEquipmentPowerCapDefRn OBJECT-TYPE
    SYNTAX       SnmpAdminString
    MAX-ACCESS   read-only
    STATUS       current
    DESCRIPTION
        "Cisco UCS equipment:PowerCapDef:rn managed object property"
    ::= { cucsEquipmentPowerCapDefEntry 3 }

cucsEquipmentPowerCapDefMinBiosVersion OBJECT-TYPE
    SYNTAX       SnmpAdminString
    MAX-ACCESS   read-only
    STATUS       current
    DESCRIPTION
        "Cisco UCS equipment:PowerCapDef:minBiosVersion
        managed object property"
    ::= { cucsEquipmentPowerCapDefEntry 4 }

cucsEquipmentPowerCapDefMinCimcVersion OBJECT-TYPE
    SYNTAX       SnmpAdminString
    MAX-ACCESS   read-only
    STATUS       current
    DESCRIPTION
        "Cisco UCS equipment:PowerCapDef:minCimcVersion
        managed object property"
    ::= { cucsEquipmentPowerCapDefEntry 5 }

cucsEquipmentPowerCapDefMinCmcVersion OBJECT-TYPE
    SYNTAX       SnmpAdminString
    MAX-ACCESS   read-only
    STATUS       current
    DESCRIPTION
        "Cisco UCS equipment:PowerCapDef:minCmcVersion
        managed object property"
    ::= { cucsEquipmentPowerCapDefEntry 6 }

cucsEquipmentPowerCapDefProfileMethod OBJECT-TYPE
    SYNTAX       CucsEquipmentPowerCapDefProfileMethod
    MAX-ACCESS   read-only
    STATUS       current
    DESCRIPTION
        "Cisco UCS equipment:PowerCapDef:profileMethod
        managed object property"
    ::= { cucsEquipmentPowerCapDefEntry 7 }

cucsEquipmentPowerCapDefIsPowerDeploymentNeeded OBJECT-TYPE
    SYNTAX       TruthValue
    MAX-ACCESS   read-only
    STATUS       current
    DESCRIPTION
        "Cisco UCS equipment:PowerCapDef:isPowerDeploymentNeeded
        managed object property"
    ::= { cucsEquipmentPowerCapDefEntry 8 }

cucsEquipmentProcessorUnitCapProviderTable OBJECT-TYPE
    SYNTAX           SEQUENCE OF CucsEquipmentProcessorUnitCapProviderEntry
    MAX-ACCESS       not-accessible
    STATUS           current
    DESCRIPTION
        "Cisco UCS equipment:ProcessorUnitCapProvider managed
        object table"
    ::= { cucsEquipmentObjects 54 }

cucsEquipmentProcessorUnitCapProviderEntry OBJECT-TYPE
    SYNTAX           CucsEquipmentProcessorUnitCapProviderEntry
    MAX-ACCESS       not-accessible
    STATUS           current
    DESCRIPTION
        "Entry for the cucsEquipmentProcessorUnitCapProviderTable table."
    INDEX { cucsEquipmentProcessorUnitCapProviderInstanceId }
    ::= { cucsEquipmentProcessorUnitCapProviderTable 1 }

CucsEquipmentProcessorUnitCapProviderEntry ::= SEQUENCE {
    cucsEquipmentProcessorUnitCapProviderInstanceId                  CucsManagedObjectId,
    cucsEquipmentProcessorUnitCapProviderDn                          CucsManagedObjectDn,
    cucsEquipmentProcessorUnitCapProviderRn                          SnmpAdminString,
    cucsEquipmentProcessorUnitCapProviderDeprecated                  TruthValue,
    cucsEquipmentProcessorUnitCapProviderGencount                    Gauge32,
    cucsEquipmentProcessorUnitCapProviderMgmtPlaneVer                SnmpAdminString,
    cucsEquipmentProcessorUnitCapProviderModel                       SnmpAdminString,
    cucsEquipmentProcessorUnitCapProviderRevision                    SnmpAdminString,
    cucsEquipmentProcessorUnitCapProviderVendor                      SnmpAdminString,
    cucsEquipmentProcessorUnitCapProviderPromCardType                Gauge32,
    cucsEquipmentProcessorUnitCapProviderDeleted                     TruthValue,
    cucsEquipmentProcessorUnitCapProviderElementLoadFailures         Gauge32,
    cucsEquipmentProcessorUnitCapProviderElementsLoaded              Gauge32,
    cucsEquipmentProcessorUnitCapProviderLoadErrors                  Gauge32,
    cucsEquipmentProcessorUnitCapProviderLoadWarnings                Gauge32
}

cucsEquipmentProcessorUnitCapProviderInstanceId OBJECT-TYPE
    SYNTAX       CucsManagedObjectId
    MAX-ACCESS   not-accessible
    STATUS       current
    DESCRIPTION
        "Instance identifier of the managed object."
    ::= { cucsEquipmentProcessorUnitCapProviderEntry 1 }

cucsEquipmentProcessorUnitCapProviderDn OBJECT-TYPE
    SYNTAX       CucsManagedObjectDn
    MAX-ACCESS   read-only
    STATUS       current
    DESCRIPTION
        "Cisco UCS equipment:ProcessorUnitCapProvider:dn
        managed object property"
    ::= { cucsEquipmentProcessorUnitCapProviderEntry 2 }

cucsEquipmentProcessorUnitCapProviderRn OBJECT-TYPE
    SYNTAX       SnmpAdminString
    MAX-ACCESS   read-only
    STATUS       current
    DESCRIPTION
        "Cisco UCS equipment:ProcessorUnitCapProvider:rn
        managed object property"
    ::= { cucsEquipmentProcessorUnitCapProviderEntry 3 }

cucsEquipmentProcessorUnitCapProviderDeprecated OBJECT-TYPE
    SYNTAX       TruthValue
    MAX-ACCESS   read-only
    STATUS       current
    DESCRIPTION
        "Cisco UCS equipment:ProcessorUnitCapProvider:deprecated
        managed object property"
    ::= { cucsEquipmentProcessorUnitCapProviderEntry 4 }

cucsEquipmentProcessorUnitCapProviderGencount OBJECT-TYPE
    SYNTAX       Gauge32
    MAX-ACCESS   read-only
    STATUS       current
    DESCRIPTION
        "Cisco UCS equipment:ProcessorUnitCapProvider:gencount
        managed object property"
    ::= { cucsEquipmentProcessorUnitCapProviderEntry 5 }

cucsEquipmentProcessorUnitCapProviderMgmtPlaneVer OBJECT-TYPE
    SYNTAX       SnmpAdminString
    MAX-ACCESS   read-only
    STATUS       current
    DESCRIPTION
        "Cisco UCS equipment:ProcessorUnitCapProvider:mgmtPlaneVer
        managed object property"
    ::= { cucsEquipmentProcessorUnitCapProviderEntry 6 }

cucsEquipmentProcessorUnitCapProviderModel OBJECT-TYPE
    SYNTAX       SnmpAdminString
    MAX-ACCESS   read-only
    STATUS       current
    DESCRIPTION
        "Cisco UCS equipment:ProcessorUnitCapProvider:model
        managed object property"
    ::= { cucsEquipmentProcessorUnitCapProviderEntry 7 }

cucsEquipmentProcessorUnitCapProviderRevision OBJECT-TYPE
    SYNTAX       SnmpAdminString
    MAX-ACCESS   read-only
    STATUS       current
    DESCRIPTION
        "Cisco UCS equipment:ProcessorUnitCapProvider:revision
        managed object property"
    ::= { cucsEquipmentProcessorUnitCapProviderEntry 8 }

cucsEquipmentProcessorUnitCapProviderVendor OBJECT-TYPE
    SYNTAX       SnmpAdminString
    MAX-ACCESS   read-only
    STATUS       current
    DESCRIPTION
        "Cisco UCS equipment:ProcessorUnitCapProvider:vendor
        managed object property"
    ::= { cucsEquipmentProcessorUnitCapProviderEntry 9 }

cucsEquipmentProcessorUnitCapProviderPromCardType OBJECT-TYPE
    SYNTAX       Gauge32
    MAX-ACCESS   read-only
    STATUS       current
    DESCRIPTION
        "Cisco UCS equipment:ProcessorUnitCapProvider:promCardType
        managed object property"
    ::= { cucsEquipmentProcessorUnitCapProviderEntry 10 }

cucsEquipmentProcessorUnitCapProviderDeleted OBJECT-TYPE
    SYNTAX       TruthValue
    MAX-ACCESS   read-only
    STATUS       current
    DESCRIPTION
        "Cisco UCS equipment:ProcessorUnitCapProvider:deleted
        managed object property"
    ::= { cucsEquipmentProcessorUnitCapProviderEntry 11 }

cucsEquipmentProcessorUnitCapProviderElementLoadFailures OBJECT-TYPE
    SYNTAX       Gauge32
    MAX-ACCESS   read-only
    STATUS       current
    DESCRIPTION
        "Cisco UCS equipment:ProcessorUnitCapProvider:elementLoadFailures
        managed object property"
    ::= { cucsEquipmentProcessorUnitCapProviderEntry 12 }

cucsEquipmentProcessorUnitCapProviderElementsLoaded OBJECT-TYPE
    SYNTAX       Gauge32
    MAX-ACCESS   read-only
    STATUS       current
    DESCRIPTION
        "Cisco UCS equipment:ProcessorUnitCapProvider:elementsLoaded
        managed object property"
    ::= { cucsEquipmentProcessorUnitCapProviderEntry 13 }

cucsEquipmentProcessorUnitCapProviderLoadErrors OBJECT-TYPE
    SYNTAX       Gauge32
    MAX-ACCESS   read-only
    STATUS       current
    DESCRIPTION
        "Cisco UCS equipment:ProcessorUnitCapProvider:loadErrors
        managed object property"
    ::= { cucsEquipmentProcessorUnitCapProviderEntry 14 }

cucsEquipmentProcessorUnitCapProviderLoadWarnings OBJECT-TYPE
    SYNTAX       Gauge32
    MAX-ACCESS   read-only
    STATUS       current
    DESCRIPTION
        "Cisco UCS equipment:ProcessorUnitCapProvider:loadWarnings
        managed object property"
    ::= { cucsEquipmentProcessorUnitCapProviderEntry 15 }

cucsEquipmentProcessorUnitDefTable OBJECT-TYPE
    SYNTAX           SEQUENCE OF CucsEquipmentProcessorUnitDefEntry
    MAX-ACCESS       not-accessible
    STATUS           current
    DESCRIPTION
        "Cisco UCS equipment:ProcessorUnitDef managed object table"
    ::= { cucsEquipmentObjects 55 }

cucsEquipmentProcessorUnitDefEntry OBJECT-TYPE
    SYNTAX           CucsEquipmentProcessorUnitDefEntry
    MAX-ACCESS       not-accessible
    STATUS           current
    DESCRIPTION
        "Entry for the cucsEquipmentProcessorUnitDefTable table."
    INDEX { cucsEquipmentProcessorUnitDefInstanceId }
    ::= { cucsEquipmentProcessorUnitDefTable 1 }

CucsEquipmentProcessorUnitDefEntry ::= SEQUENCE {
    cucsEquipmentProcessorUnitDefInstanceId                          CucsManagedObjectId,
    cucsEquipmentProcessorUnitDefDn                                  CucsManagedObjectDn,
    cucsEquipmentProcessorUnitDefRn                                  SnmpAdminString,
    cucsEquipmentProcessorUnitDefAddressWidth                        Gauge32,
    cucsEquipmentProcessorUnitDefDataWidth                           Gauge32,
    cucsEquipmentProcessorUnitDefDescr                               SnmpAdminString,
    cucsEquipmentProcessorUnitDefIntId                               SnmpAdminString,
    cucsEquipmentProcessorUnitDefMaxSpeed                            SnmpAdminString,
    cucsEquipmentProcessorUnitDefName                                SnmpAdminString,
    cucsEquipmentProcessorUnitDefPolicyLevel                         Gauge32,
    cucsEquipmentProcessorUnitDefPolicyOwner                         CucsPolicyPolicyOwner,
    cucsEquipmentProcessorUnitDefMemoryCapacity                      SnmpAdminString
}

cucsEquipmentProcessorUnitDefInstanceId OBJECT-TYPE
    SYNTAX       CucsManagedObjectId
    MAX-ACCESS   not-accessible
    STATUS       current
    DESCRIPTION
        "Instance identifier of the managed object."
    ::= { cucsEquipmentProcessorUnitDefEntry 1 }

cucsEquipmentProcessorUnitDefDn OBJECT-TYPE
    SYNTAX       CucsManagedObjectDn
    MAX-ACCESS   read-only
    STATUS       current
    DESCRIPTION
        "Cisco UCS equipment:ProcessorUnitDef:dn managed object property"
    ::= { cucsEquipmentProcessorUnitDefEntry 2 }

cucsEquipmentProcessorUnitDefRn OBJECT-TYPE
    SYNTAX       SnmpAdminString
    MAX-ACCESS   read-only
    STATUS       current
    DESCRIPTION
        "Cisco UCS equipment:ProcessorUnitDef:rn managed object property"
    ::= { cucsEquipmentProcessorUnitDefEntry 3 }

cucsEquipmentProcessorUnitDefAddressWidth OBJECT-TYPE
    SYNTAX       Gauge32
    MAX-ACCESS   read-only
    STATUS       current
    DESCRIPTION
        "Cisco UCS equipment:ProcessorUnitDef:addressWidth
        managed object property"
    ::= { cucsEquipmentProcessorUnitDefEntry 4 }

cucsEquipmentProcessorUnitDefDataWidth OBJECT-TYPE
    SYNTAX       Gauge32
    MAX-ACCESS   read-only
    STATUS       current
    DESCRIPTION
        "Cisco UCS equipment:ProcessorUnitDef:dataWidth
        managed object property"
    ::= { cucsEquipmentProcessorUnitDefEntry 5 }

cucsEquipmentProcessorUnitDefDescr OBJECT-TYPE
    SYNTAX       SnmpAdminString
    MAX-ACCESS   read-only
    STATUS       current
    DESCRIPTION
        "Cisco UCS equipment:ProcessorUnitDef:descr managed
        object property"
    ::= { cucsEquipmentProcessorUnitDefEntry 6 }

cucsEquipmentProcessorUnitDefIntId OBJECT-TYPE
    SYNTAX       SnmpAdminString
    MAX-ACCESS   read-only
    STATUS       current
    DESCRIPTION
        "Cisco UCS equipment:ProcessorUnitDef:intId managed
        object property"
    ::= { cucsEquipmentProcessorUnitDefEntry 7 }

cucsEquipmentProcessorUnitDefMaxSpeed OBJECT-TYPE
    SYNTAX       SnmpAdminString
    MAX-ACCESS   read-only
    STATUS       current
    DESCRIPTION
        "Cisco UCS equipment:ProcessorUnitDef:maxSpeed
        managed object property"
    ::= { cucsEquipmentProcessorUnitDefEntry 8 }

cucsEquipmentProcessorUnitDefName OBJECT-TYPE
    SYNTAX       SnmpAdminString
    MAX-ACCESS   read-only
    STATUS       current
    DESCRIPTION
        "Cisco UCS equipment:ProcessorUnitDef:name managed
        object property"
    ::= { cucsEquipmentProcessorUnitDefEntry 9 }

cucsEquipmentProcessorUnitDefPolicyLevel OBJECT-TYPE
    SYNTAX       Gauge32
    MAX-ACCESS   read-only
    STATUS       current
    DESCRIPTION
        "Cisco UCS equipment:ProcessorUnitDef:policyLevel
        managed object property"
    ::= { cucsEquipmentProcessorUnitDefEntry 10 }

cucsEquipmentProcessorUnitDefPolicyOwner OBJECT-TYPE
    SYNTAX       CucsPolicyPolicyOwner
    MAX-ACCESS   read-only
    STATUS       current
    DESCRIPTION
        "Cisco UCS equipment:ProcessorUnitDef:policyOwner
        managed object property"
    ::= { cucsEquipmentProcessorUnitDefEntry 11 }

cucsEquipmentProcessorUnitDefMemoryCapacity OBJECT-TYPE
    SYNTAX       SnmpAdminString
    MAX-ACCESS   read-only
    STATUS       current
    DESCRIPTION
        "Cisco UCS equipment:ProcessorUnitDef:memoryCapacity
        managed object property"
    ::= { cucsEquipmentProcessorUnitDefEntry 12 }

cucsEquipmentPsuTable OBJECT-TYPE
    SYNTAX           SEQUENCE OF CucsEquipmentPsuEntry
    MAX-ACCESS       not-accessible
    STATUS           current
    DESCRIPTION
        "Cisco UCS equipment:Psu managed object table"
    ::= { cucsEquipmentObjects 56 }

cucsEquipmentPsuEntry OBJECT-TYPE
    SYNTAX           CucsEquipmentPsuEntry
    MAX-ACCESS       not-accessible
    STATUS           current
    DESCRIPTION
        "Entry for the cucsEquipmentPsuTable table."
    INDEX { cucsEquipmentPsuInstanceId }
    ::= { cucsEquipmentPsuTable 1 }

CucsEquipmentPsuEntry ::= SEQUENCE {
    cucsEquipmentPsuInstanceId                                       CucsManagedObjectId,
    cucsEquipmentPsuDn                                               CucsManagedObjectDn,
    cucsEquipmentPsuRn                                               SnmpAdminString,
    cucsEquipmentPsuFltAggr                                          Unsigned64,
    cucsEquipmentPsuId                                               CucsEquipmentPsuId,
    cucsEquipmentPsuModel                                            SnmpAdminString,
    cucsEquipmentPsuOperState                                        CucsEquipmentOperability,
    cucsEquipmentPsuOperability                                      CucsEquipmentOperability,
    cucsEquipmentPsuPerf                                             CucsEquipmentSensorThresholdStatus,
    cucsEquipmentPsuPower                                            CucsEquipmentPowerState,
    cucsEquipmentPsuPresence                                         CucsEquipmentPresence,
    cucsEquipmentPsuRevision                                         SnmpAdminString,
    cucsEquipmentPsuSerial                                           SnmpAdminString,
    cucsEquipmentPsuThermal                                          CucsEquipmentSensorThresholdStatus,
    cucsEquipmentPsuVendor                                           SnmpAdminString,
    cucsEquipmentPsuVoltage                                          CucsEquipmentSensorThresholdStatus,
    cucsEquipmentPsuType                                             CucsEquipmentPsuType,
    cucsEquipmentPsuPowerStateQualifier                              CucsEquipmentPsuStateQualifier,
    cucsEquipmentPsuOperQualifierReason                              SnmpAdminString,
    cucsEquipmentPsuPsuFirmwareVersion                               SnmpAdminString,
    cucsEquipmentPsuPartNumber                                       SnmpAdminString,
    cucsEquipmentPsuVid                                              SnmpAdminString,
    cucsEquipmentPsuPsuInputSrc                                      CucsEquipmentPsuInputSrc,
    cucsEquipmentPsuPsuType                                          CucsEquipmentPsuVoltageType,
    cucsEquipmentPsuPsuWattage                                       Gauge32,
    cucsEquipmentPsuFsmDescr                                         SnmpAdminString,
    cucsEquipmentPsuFsmFlags                                         SnmpAdminString,
    cucsEquipmentPsuFsmPrev                                          SnmpAdminString,
    cucsEquipmentPsuFsmProgr                                         Gauge32,
    cucsEquipmentPsuFsmRmtInvErrCode                                 Gauge32,
    cucsEquipmentPsuFsmRmtInvErrDescr                                SnmpAdminString,
    cucsEquipmentPsuFsmRmtInvRslt                                    CucsConditionRemoteInvRslt,
    cucsEquipmentPsuFsmStageDescr                                    SnmpAdminString,
    cucsEquipmentPsuFsmStamp                                         DateAndTime,
    cucsEquipmentPsuFsmStatus                                        SnmpAdminString,
    cucsEquipmentPsuFsmTry                                           Gauge32,
    cucsEquipmentPsuAssetTag                                         SnmpAdminString
}

cucsEquipmentPsuInstanceId OBJECT-TYPE
    SYNTAX       CucsManagedObjectId
    MAX-ACCESS   not-accessible
    STATUS       current
    DESCRIPTION
        "Instance identifier of the managed object."
    ::= { cucsEquipmentPsuEntry 1 }

cucsEquipmentPsuDn OBJECT-TYPE
    SYNTAX       CucsManagedObjectDn
    MAX-ACCESS   read-only
    STATUS       current
    DESCRIPTION
        "Cisco UCS equipment:Psu:dn managed object property"
    ::= { cucsEquipmentPsuEntry 2 }

cucsEquipmentPsuRn OBJECT-TYPE
    SYNTAX       SnmpAdminString
    MAX-ACCESS   read-only
    STATUS       current
    DESCRIPTION
        "Cisco UCS equipment:Psu:rn managed object property"
    ::= { cucsEquipmentPsuEntry 3 }

cucsEquipmentPsuFltAggr OBJECT-TYPE
    SYNTAX       Unsigned64
    MAX-ACCESS   read-only
    STATUS       current
    DESCRIPTION
        "Cisco UCS equipment:Psu:fltAggr managed object property"
    ::= { cucsEquipmentPsuEntry 4 }

cucsEquipmentPsuId OBJECT-TYPE
    SYNTAX       CucsEquipmentPsuId
    MAX-ACCESS   read-only
    STATUS       current
    DESCRIPTION
        "Cisco UCS equipment:Psu:id managed object property"
    ::= { cucsEquipmentPsuEntry 5 }

cucsEquipmentPsuModel OBJECT-TYPE
    SYNTAX       SnmpAdminString
    MAX-ACCESS   read-only
    STATUS       current
    DESCRIPTION
        "Cisco UCS equipment:Psu:model managed object property"
    ::= { cucsEquipmentPsuEntry 6 }

cucsEquipmentPsuOperState OBJECT-TYPE
    SYNTAX       CucsEquipmentOperability
    MAX-ACCESS   read-only
    STATUS       current
    DESCRIPTION
        "Cisco UCS equipment:Psu:operState managed object property"
    ::= { cucsEquipmentPsuEntry 7 }

cucsEquipmentPsuOperability OBJECT-TYPE
    SYNTAX       CucsEquipmentOperability
    MAX-ACCESS   read-only
    STATUS       current
    DESCRIPTION
        "Cisco UCS equipment:Psu:operability managed object property"
    ::= { cucsEquipmentPsuEntry 8 }

cucsEquipmentPsuPerf OBJECT-TYPE
    SYNTAX       CucsEquipmentSensorThresholdStatus
    MAX-ACCESS   read-only
    STATUS       current
    DESCRIPTION
        "Cisco UCS equipment:Psu:perf managed object property"
    ::= { cucsEquipmentPsuEntry 9 }

cucsEquipmentPsuPower OBJECT-TYPE
    SYNTAX       CucsEquipmentPowerState
    MAX-ACCESS   read-only
    STATUS       current
    DESCRIPTION
        "Cisco UCS equipment:Psu:power managed object property"
    ::= { cucsEquipmentPsuEntry 10 }

cucsEquipmentPsuPresence OBJECT-TYPE
    SYNTAX       CucsEquipmentPresence
    MAX-ACCESS   read-only
    STATUS       current
    DESCRIPTION
        "Cisco UCS equipment:Psu:presence managed object property"
    ::= { cucsEquipmentPsuEntry 11 }

cucsEquipmentPsuRevision OBJECT-TYPE
    SYNTAX       SnmpAdminString
    MAX-ACCESS   read-only
    STATUS       current
    DESCRIPTION
        "Cisco UCS equipment:Psu:revision managed object property"
    ::= { cucsEquipmentPsuEntry 12 }

cucsEquipmentPsuSerial OBJECT-TYPE
    SYNTAX       SnmpAdminString
    MAX-ACCESS   read-only
    STATUS       current
    DESCRIPTION
        "Cisco UCS equipment:Psu:serial managed object property"
    ::= { cucsEquipmentPsuEntry 13 }

cucsEquipmentPsuThermal OBJECT-TYPE
    SYNTAX       CucsEquipmentSensorThresholdStatus
    MAX-ACCESS   read-only
    STATUS       current
    DESCRIPTION
        "Cisco UCS equipment:Psu:thermal managed object property"
    ::= { cucsEquipmentPsuEntry 14 }

cucsEquipmentPsuVendor OBJECT-TYPE
    SYNTAX       SnmpAdminString
    MAX-ACCESS   read-only
    STATUS       current
    DESCRIPTION
        "Cisco UCS equipment:Psu:vendor managed object property"
    ::= { cucsEquipmentPsuEntry 15 }

cucsEquipmentPsuVoltage OBJECT-TYPE
    SYNTAX       CucsEquipmentSensorThresholdStatus
    MAX-ACCESS   read-only
    STATUS       current
    DESCRIPTION
        "Cisco UCS equipment:Psu:voltage managed object property"
    ::= { cucsEquipmentPsuEntry 16 }

cucsEquipmentPsuType OBJECT-TYPE
    SYNTAX       CucsEquipmentPsuType
    MAX-ACCESS   read-only
    STATUS       current
    DESCRIPTION
        "Cisco UCS equipment:Psu:Type managed object property"
    ::= { cucsEquipmentPsuEntry 17 }

cucsEquipmentPsuPowerStateQualifier OBJECT-TYPE
    SYNTAX       CucsEquipmentPsuStateQualifier
    MAX-ACCESS   read-only
    STATUS       current
    DESCRIPTION
        "Cisco UCS equipment:Psu:powerStateQualifier managed
        object property"
    ::= { cucsEquipmentPsuEntry 18 }

cucsEquipmentPsuOperQualifierReason OBJECT-TYPE
    SYNTAX       SnmpAdminString
    MAX-ACCESS   read-only
    STATUS       current
    DESCRIPTION
        "Cisco UCS equipment:Psu:operQualifierReason managed
        object property"
    ::= { cucsEquipmentPsuEntry 19 }

cucsEquipmentPsuPsuFirmwareVersion OBJECT-TYPE
    SYNTAX       SnmpAdminString
    MAX-ACCESS   read-only
    STATUS       current
    DESCRIPTION
        "Cisco UCS equipment:Psu:psuFirmwareVersion managed
        object property"
    ::= { cucsEquipmentPsuEntry 20 }

cucsEquipmentPsuPartNumber OBJECT-TYPE
    SYNTAX       SnmpAdminString
    MAX-ACCESS   read-only
    STATUS       current
    DESCRIPTION
        "Cisco UCS equipment:Psu:partNumber managed object property"
    ::= { cucsEquipmentPsuEntry 21 }

cucsEquipmentPsuVid OBJECT-TYPE
    SYNTAX       SnmpAdminString
    MAX-ACCESS   read-only
    STATUS       current
    DESCRIPTION
        "Cisco UCS equipment:Psu:vid managed object property"
    ::= { cucsEquipmentPsuEntry 22 }

cucsEquipmentPsuPsuInputSrc OBJECT-TYPE
    SYNTAX       CucsEquipmentPsuInputSrc
    MAX-ACCESS   read-only
    STATUS       current
    DESCRIPTION
        "Cisco UCS equipment:Psu:psuInputSrc managed object property"
    ::= { cucsEquipmentPsuEntry 23 }

cucsEquipmentPsuPsuType OBJECT-TYPE
    SYNTAX       CucsEquipmentPsuVoltageType
    MAX-ACCESS   read-only
    STATUS       current
    DESCRIPTION
        "Cisco UCS equipment:Psu:psuType managed object property"
    ::= { cucsEquipmentPsuEntry 24 }

cucsEquipmentPsuPsuWattage OBJECT-TYPE
    SYNTAX       Gauge32
    MAX-ACCESS   read-only
    STATUS       current
    DESCRIPTION
        "Cisco UCS equipment:Psu:psuWattage managed object property"
    ::= { cucsEquipmentPsuEntry 25 }

cucsEquipmentPsuFsmDescr OBJECT-TYPE
    SYNTAX       SnmpAdminString
    MAX-ACCESS   read-only
    STATUS       current
    DESCRIPTION
        "Cisco UCS equipment:Psu:fsmDescr managed object property"
    ::= { cucsEquipmentPsuEntry 26 }

cucsEquipmentPsuFsmFlags OBJECT-TYPE
    SYNTAX       SnmpAdminString
    MAX-ACCESS   read-only
    STATUS       current
    DESCRIPTION
        "Cisco UCS equipment:Psu:fsmFlags managed object property"
    ::= { cucsEquipmentPsuEntry 27 }

cucsEquipmentPsuFsmPrev OBJECT-TYPE
    SYNTAX       SnmpAdminString
    MAX-ACCESS   read-only
    STATUS       current
    DESCRIPTION
        "Cisco UCS equipment:Psu:fsmPrev managed object property"
    ::= { cucsEquipmentPsuEntry 28 }

cucsEquipmentPsuFsmProgr OBJECT-TYPE
    SYNTAX       Gauge32
    MAX-ACCESS   read-only
    STATUS       current
    DESCRIPTION
        "Cisco UCS equipment:Psu:fsmProgr managed object property"
    ::= { cucsEquipmentPsuEntry 29 }

cucsEquipmentPsuFsmRmtInvErrCode OBJECT-TYPE
    SYNTAX       Gauge32
    MAX-ACCESS   read-only
    STATUS       current
    DESCRIPTION
        "Cisco UCS equipment:Psu:fsmRmtInvErrCode managed object property"
    ::= { cucsEquipmentPsuEntry 30 }

cucsEquipmentPsuFsmRmtInvErrDescr OBJECT-TYPE
    SYNTAX       SnmpAdminString
    MAX-ACCESS   read-only
    STATUS       current
    DESCRIPTION
        "Cisco UCS equipment:Psu:fsmRmtInvErrDescr managed
        object property"
    ::= { cucsEquipmentPsuEntry 31 }

cucsEquipmentPsuFsmRmtInvRslt OBJECT-TYPE
    SYNTAX       CucsConditionRemoteInvRslt
    MAX-ACCESS   read-only
    STATUS       current
    DESCRIPTION
        "Cisco UCS equipment:Psu:fsmRmtInvRslt managed object property"
    ::= { cucsEquipmentPsuEntry 32 }

cucsEquipmentPsuFsmStageDescr OBJECT-TYPE
    SYNTAX       SnmpAdminString
    MAX-ACCESS   read-only
    STATUS       current
    DESCRIPTION
        "Cisco UCS equipment:Psu:fsmStageDescr managed object property"
    ::= { cucsEquipmentPsuEntry 33 }

cucsEquipmentPsuFsmStamp OBJECT-TYPE
    SYNTAX       DateAndTime
    MAX-ACCESS   read-only
    STATUS       current
    DESCRIPTION
        "Cisco UCS equipment:Psu:fsmStamp managed object property"
    ::= { cucsEquipmentPsuEntry 34 }

cucsEquipmentPsuFsmStatus OBJECT-TYPE
    SYNTAX       SnmpAdminString
    MAX-ACCESS   read-only
    STATUS       current
    DESCRIPTION
        "Cisco UCS equipment:Psu:fsmStatus managed object property"
    ::= { cucsEquipmentPsuEntry 35 }

cucsEquipmentPsuFsmTry OBJECT-TYPE
    SYNTAX       Gauge32
    MAX-ACCESS   read-only
    STATUS       current
    DESCRIPTION
        "Cisco UCS equipment:Psu:fsmTry managed object property"
    ::= { cucsEquipmentPsuEntry 36 }

cucsEquipmentPsuAssetTag OBJECT-TYPE
    SYNTAX       SnmpAdminString
    MAX-ACCESS   read-only
    STATUS       current
    DESCRIPTION
        "Cisco UCS equipment:Psu:assetTag managed object property"
    ::= { cucsEquipmentPsuEntry 37 }

cucsEquipmentPsuCapProviderTable OBJECT-TYPE
    SYNTAX           SEQUENCE OF CucsEquipmentPsuCapProviderEntry
    MAX-ACCESS       not-accessible
    STATUS           current
    DESCRIPTION
        "Cisco UCS equipment:PsuCapProvider managed object table"
    ::= { cucsEquipmentObjects 57 }

cucsEquipmentPsuCapProviderEntry OBJECT-TYPE
    SYNTAX           CucsEquipmentPsuCapProviderEntry
    MAX-ACCESS       not-accessible
    STATUS           current
    DESCRIPTION
        "Entry for the cucsEquipmentPsuCapProviderTable table."
    INDEX { cucsEquipmentPsuCapProviderInstanceId }
    ::= { cucsEquipmentPsuCapProviderTable 1 }

CucsEquipmentPsuCapProviderEntry ::= SEQUENCE {
    cucsEquipmentPsuCapProviderInstanceId                            CucsManagedObjectId,
    cucsEquipmentPsuCapProviderDn                                    CucsManagedObjectDn,
    cucsEquipmentPsuCapProviderRn                                    SnmpAdminString,
    cucsEquipmentPsuCapProviderDeprecated                            TruthValue,
    cucsEquipmentPsuCapProviderGencount                              Gauge32,
    cucsEquipmentPsuCapProviderMgmtPlaneVer                          SnmpAdminString,
    cucsEquipmentPsuCapProviderModel                                 SnmpAdminString,
    cucsEquipmentPsuCapProviderRevision                              SnmpAdminString,
    cucsEquipmentPsuCapProviderVendor                                SnmpAdminString,
    cucsEquipmentPsuCapProviderPromCardType                          Gauge32,
    cucsEquipmentPsuCapProviderDeleted                               TruthValue,
    cucsEquipmentPsuCapProviderElementLoadFailures                   Gauge32,
    cucsEquipmentPsuCapProviderElementsLoaded                        Gauge32,
    cucsEquipmentPsuCapProviderLoadErrors                            Gauge32,
    cucsEquipmentPsuCapProviderLoadWarnings                          Gauge32
}

cucsEquipmentPsuCapProviderInstanceId OBJECT-TYPE
    SYNTAX       CucsManagedObjectId
    MAX-ACCESS   not-accessible
    STATUS       current
    DESCRIPTION
        "Instance identifier of the managed object."
    ::= { cucsEquipmentPsuCapProviderEntry 1 }

cucsEquipmentPsuCapProviderDn OBJECT-TYPE
    SYNTAX       CucsManagedObjectDn
    MAX-ACCESS   read-only
    STATUS       current
    DESCRIPTION
        "Cisco UCS equipment:PsuCapProvider:dn managed object property"
    ::= { cucsEquipmentPsuCapProviderEntry 2 }

cucsEquipmentPsuCapProviderRn OBJECT-TYPE
    SYNTAX       SnmpAdminString
    MAX-ACCESS   read-only
    STATUS       current
    DESCRIPTION
        "Cisco UCS equipment:PsuCapProvider:rn managed object property"
    ::= { cucsEquipmentPsuCapProviderEntry 3 }

cucsEquipmentPsuCapProviderDeprecated OBJECT-TYPE
    SYNTAX       TruthValue
    MAX-ACCESS   read-only
    STATUS       current
    DESCRIPTION
        "Cisco UCS equipment:PsuCapProvider:deprecated
        managed object property"
    ::= { cucsEquipmentPsuCapProviderEntry 4 }

cucsEquipmentPsuCapProviderGencount OBJECT-TYPE
    SYNTAX       Gauge32
    MAX-ACCESS   read-only
    STATUS       current
    DESCRIPTION
        "Cisco UCS equipment:PsuCapProvider:gencount managed
        object property"
    ::= { cucsEquipmentPsuCapProviderEntry 5 }

cucsEquipmentPsuCapProviderMgmtPlaneVer OBJECT-TYPE
    SYNTAX       SnmpAdminString
    MAX-ACCESS   read-only
    STATUS       current
    DESCRIPTION
        "Cisco UCS equipment:PsuCapProvider:mgmtPlaneVer
        managed object property"
    ::= { cucsEquipmentPsuCapProviderEntry 6 }

cucsEquipmentPsuCapProviderModel OBJECT-TYPE
    SYNTAX       SnmpAdminString
    MAX-ACCESS   read-only
    STATUS       current
    DESCRIPTION
        "Cisco UCS equipment:PsuCapProvider:model managed object property"
    ::= { cucsEquipmentPsuCapProviderEntry 7 }

cucsEquipmentPsuCapProviderRevision OBJECT-TYPE
    SYNTAX       SnmpAdminString
    MAX-ACCESS   read-only
    STATUS       current
    DESCRIPTION
        "Cisco UCS equipment:PsuCapProvider:revision managed
        object property"
    ::= { cucsEquipmentPsuCapProviderEntry 8 }

cucsEquipmentPsuCapProviderVendor OBJECT-TYPE
    SYNTAX       SnmpAdminString
    MAX-ACCESS   read-only
    STATUS       current
    DESCRIPTION
        "Cisco UCS equipment:PsuCapProvider:vendor managed
        object property"
    ::= { cucsEquipmentPsuCapProviderEntry 9 }

cucsEquipmentPsuCapProviderPromCardType OBJECT-TYPE
    SYNTAX       Gauge32
    MAX-ACCESS   read-only
    STATUS       current
    DESCRIPTION
        "Cisco UCS equipment:PsuCapProvider:promCardType
        managed object property"
    ::= { cucsEquipmentPsuCapProviderEntry 10 }

cucsEquipmentPsuCapProviderDeleted OBJECT-TYPE
    SYNTAX       TruthValue
    MAX-ACCESS   read-only
    STATUS       current
    DESCRIPTION
        "Cisco UCS equipment:PsuCapProvider:deleted managed
        object property"
    ::= { cucsEquipmentPsuCapProviderEntry 11 }

cucsEquipmentPsuCapProviderElementLoadFailures OBJECT-TYPE
    SYNTAX       Gauge32
    MAX-ACCESS   read-only
    STATUS       current
    DESCRIPTION
        "Cisco UCS equipment:PsuCapProvider:elementLoadFailures
        managed object property"
    ::= { cucsEquipmentPsuCapProviderEntry 12 }

cucsEquipmentPsuCapProviderElementsLoaded OBJECT-TYPE
    SYNTAX       Gauge32
    MAX-ACCESS   read-only
    STATUS       current
    DESCRIPTION
        "Cisco UCS equipment:PsuCapProvider:elementsLoaded
        managed object property"
    ::= { cucsEquipmentPsuCapProviderEntry 13 }

cucsEquipmentPsuCapProviderLoadErrors OBJECT-TYPE
    SYNTAX       Gauge32
    MAX-ACCESS   read-only
    STATUS       current
    DESCRIPTION
        "Cisco UCS equipment:PsuCapProvider:loadErrors
        managed object property"
    ::= { cucsEquipmentPsuCapProviderEntry 14 }

cucsEquipmentPsuCapProviderLoadWarnings OBJECT-TYPE
    SYNTAX       Gauge32
    MAX-ACCESS   read-only
    STATUS       current
    DESCRIPTION
        "Cisco UCS equipment:PsuCapProvider:loadWarnings
        managed object property"
    ::= { cucsEquipmentPsuCapProviderEntry 15 }

cucsEquipmentPsuDefTable OBJECT-TYPE
    SYNTAX           SEQUENCE OF CucsEquipmentPsuDefEntry
    MAX-ACCESS       not-accessible
    STATUS           current
    DESCRIPTION
        "Cisco UCS equipment:PsuDef managed object table"
    ::= { cucsEquipmentObjects 91 }

cucsEquipmentPsuDefEntry OBJECT-TYPE
    SYNTAX           CucsEquipmentPsuDefEntry
    MAX-ACCESS       not-accessible
    STATUS           current
    DESCRIPTION
        "Entry for the cucsEquipmentPsuDefTable table."
    INDEX { cucsEquipmentPsuDefInstanceId }
    ::= { cucsEquipmentPsuDefTable 1 }

CucsEquipmentPsuDefEntry ::= SEQUENCE {
    cucsEquipmentPsuDefInstanceId                                    CucsManagedObjectId,
    cucsEquipmentPsuDefDn                                            CucsManagedObjectDn,
    cucsEquipmentPsuDefRn                                            SnmpAdminString,
    cucsEquipmentPsuDefPsuType                                       SnmpAdminString,
    cucsEquipmentPsuDefDescr                                         SnmpAdminString,
    cucsEquipmentPsuDefIntId                                         SnmpAdminString,
    cucsEquipmentPsuDefName                                          SnmpAdminString,
    cucsEquipmentPsuDefPolicyLevel                                   Gauge32,
    cucsEquipmentPsuDefPolicyOwner                                   CucsPolicyPolicyOwner
}

cucsEquipmentPsuDefInstanceId OBJECT-TYPE
    SYNTAX       CucsManagedObjectId
    MAX-ACCESS   not-accessible
    STATUS       current
    DESCRIPTION
        "Instance identifier of the managed object."
    ::= { cucsEquipmentPsuDefEntry 1 }

cucsEquipmentPsuDefDn OBJECT-TYPE
    SYNTAX       CucsManagedObjectDn
    MAX-ACCESS   read-only
    STATUS       current
    DESCRIPTION
        "Cisco UCS equipment:PsuDef:dn managed object property"
    ::= { cucsEquipmentPsuDefEntry 2 }

cucsEquipmentPsuDefRn OBJECT-TYPE
    SYNTAX       SnmpAdminString
    MAX-ACCESS   read-only
    STATUS       current
    DESCRIPTION
        "Cisco UCS equipment:PsuDef:rn managed object property"
    ::= { cucsEquipmentPsuDefEntry 3 }

cucsEquipmentPsuDefPsuType OBJECT-TYPE
    SYNTAX       SnmpAdminString
    MAX-ACCESS   read-only
    STATUS       current
    DESCRIPTION
        "Cisco UCS equipment:PsuDef:PsuType managed object property"
    ::= { cucsEquipmentPsuDefEntry 4 }

cucsEquipmentPsuDefDescr OBJECT-TYPE
    SYNTAX       SnmpAdminString
    MAX-ACCESS   read-only
    STATUS       current
    DESCRIPTION
        "Cisco UCS equipment:PsuDef:descr managed object property"
    ::= { cucsEquipmentPsuDefEntry 5 }

cucsEquipmentPsuDefIntId OBJECT-TYPE
    SYNTAX       SnmpAdminString
    MAX-ACCESS   read-only
    STATUS       current
    DESCRIPTION
        "Cisco UCS equipment:PsuDef:intId managed object property"
    ::= { cucsEquipmentPsuDefEntry 6 }

cucsEquipmentPsuDefName OBJECT-TYPE
    SYNTAX       SnmpAdminString
    MAX-ACCESS   read-only
    STATUS       current
    DESCRIPTION
        "Cisco UCS equipment:PsuDef:name managed object property"
    ::= { cucsEquipmentPsuDefEntry 7 }

cucsEquipmentPsuDefPolicyLevel OBJECT-TYPE
    SYNTAX       Gauge32
    MAX-ACCESS   read-only
    STATUS       current
    DESCRIPTION
        "Cisco UCS equipment:PsuDef:policyLevel managed object property"
    ::= { cucsEquipmentPsuDefEntry 8 }

cucsEquipmentPsuDefPolicyOwner OBJECT-TYPE
    SYNTAX       CucsPolicyPolicyOwner
    MAX-ACCESS   read-only
    STATUS       current
    DESCRIPTION
        "Cisco UCS equipment:PsuDef:policyOwner managed object property"
    ::= { cucsEquipmentPsuDefEntry 9 }

cucsEquipmentPsuFsmTable OBJECT-TYPE
    SYNTAX           SEQUENCE OF CucsEquipmentPsuFsmEntry
    MAX-ACCESS       not-accessible
    STATUS           current
    DESCRIPTION
        "Cisco UCS equipment:PsuFsm managed object table"
    ::= { cucsEquipmentObjects 143 }

cucsEquipmentPsuFsmEntry OBJECT-TYPE
    SYNTAX           CucsEquipmentPsuFsmEntry
    MAX-ACCESS       not-accessible
    STATUS           current
    DESCRIPTION
        "Entry for the cucsEquipmentPsuFsmTable table."
    INDEX { cucsEquipmentPsuFsmInstanceId }
    ::= { cucsEquipmentPsuFsmTable 1 }

CucsEquipmentPsuFsmEntry ::= SEQUENCE {
    cucsEquipmentPsuFsmInstanceId                                    CucsManagedObjectId,
    cucsEquipmentPsuFsmDn                                            CucsManagedObjectDn,
    cucsEquipmentPsuFsmRn                                            SnmpAdminString,
    cucsEquipmentPsuFsmCompletionTime                                DateAndTime,
    cucsEquipmentPsuFsmCurrentFsm                                    CucsEquipmentPsuFsmCurrentFsm,
    cucsEquipmentPsuFsmDescrData                                     SnmpAdminString,
    cucsEquipmentPsuFsmFsmStatus                                     CucsFsmFsmStageStatus,
    cucsEquipmentPsuFsmProgress                                      Gauge32,
    cucsEquipmentPsuFsmRmtErrCode                                    Gauge32,
    cucsEquipmentPsuFsmRmtErrDescr                                   SnmpAdminString,
    cucsEquipmentPsuFsmRmtRslt                                       CucsConditionRemoteInvRslt
}

cucsEquipmentPsuFsmInstanceId OBJECT-TYPE
    SYNTAX       CucsManagedObjectId
    MAX-ACCESS   not-accessible
    STATUS       current
    DESCRIPTION
        "Instance identifier of the managed object."
    ::= { cucsEquipmentPsuFsmEntry 1 }

cucsEquipmentPsuFsmDn OBJECT-TYPE
    SYNTAX       CucsManagedObjectDn
    MAX-ACCESS   read-only
    STATUS       current
    DESCRIPTION
        "Cisco UCS equipment:PsuFsm:dn managed object property"
    ::= { cucsEquipmentPsuFsmEntry 2 }

cucsEquipmentPsuFsmRn OBJECT-TYPE
    SYNTAX       SnmpAdminString
    MAX-ACCESS   read-only
    STATUS       current
    DESCRIPTION
        "Cisco UCS equipment:PsuFsm:rn managed object property"
    ::= { cucsEquipmentPsuFsmEntry 3 }

cucsEquipmentPsuFsmCompletionTime OBJECT-TYPE
    SYNTAX       DateAndTime
    MAX-ACCESS   read-only
    STATUS       current
    DESCRIPTION
        "Cisco UCS equipment:PsuFsm:completionTime managed
        object property"
    ::= { cucsEquipmentPsuFsmEntry 4 }

cucsEquipmentPsuFsmCurrentFsm OBJECT-TYPE
    SYNTAX       CucsEquipmentPsuFsmCurrentFsm
    MAX-ACCESS   read-only
    STATUS       current
    DESCRIPTION
        "Cisco UCS equipment:PsuFsm:currentFsm managed object property"
    ::= { cucsEquipmentPsuFsmEntry 5 }

cucsEquipmentPsuFsmDescrData OBJECT-TYPE
    SYNTAX       SnmpAdminString
    MAX-ACCESS   read-only
    STATUS       current
    DESCRIPTION
        "Cisco UCS equipment:PsuFsm:descr managed object property"
    ::= { cucsEquipmentPsuFsmEntry 6 }

cucsEquipmentPsuFsmFsmStatus OBJECT-TYPE
    SYNTAX       CucsFsmFsmStageStatus
    MAX-ACCESS   read-only
    STATUS       current
    DESCRIPTION
        "Cisco UCS equipment:PsuFsm:fsmStatus managed object property"
    ::= { cucsEquipmentPsuFsmEntry 7 }

cucsEquipmentPsuFsmProgress OBJECT-TYPE
    SYNTAX       Gauge32
    MAX-ACCESS   read-only
    STATUS       current
    DESCRIPTION
        "Cisco UCS equipment:PsuFsm:progress managed object property"
    ::= { cucsEquipmentPsuFsmEntry 8 }

cucsEquipmentPsuFsmRmtErrCode OBJECT-TYPE
    SYNTAX       Gauge32
    MAX-ACCESS   read-only
    STATUS       current
    DESCRIPTION
        "Cisco UCS equipment:PsuFsm:rmtErrCode managed object property"
    ::= { cucsEquipmentPsuFsmEntry 9 }

cucsEquipmentPsuFsmRmtErrDescr OBJECT-TYPE
    SYNTAX       SnmpAdminString
    MAX-ACCESS   read-only
    STATUS       current
    DESCRIPTION
        "Cisco UCS equipment:PsuFsm:rmtErrDescr managed object property"
    ::= { cucsEquipmentPsuFsmEntry 10 }

cucsEquipmentPsuFsmRmtRslt OBJECT-TYPE
    SYNTAX       CucsConditionRemoteInvRslt
    MAX-ACCESS   read-only
    STATUS       current
    DESCRIPTION
        "Cisco UCS equipment:PsuFsm:rmtRslt managed object property"
    ::= { cucsEquipmentPsuFsmEntry 11 }

cucsEquipmentPsuFsmStageTable OBJECT-TYPE
    SYNTAX           SEQUENCE OF CucsEquipmentPsuFsmStageEntry
    MAX-ACCESS       not-accessible
    STATUS           current
    DESCRIPTION
        "Cisco UCS equipment:PsuFsmStage managed object table"
    ::= { cucsEquipmentObjects 144 }

cucsEquipmentPsuFsmStageEntry OBJECT-TYPE
    SYNTAX           CucsEquipmentPsuFsmStageEntry
    MAX-ACCESS       not-accessible
    STATUS           current
    DESCRIPTION
        "Entry for the cucsEquipmentPsuFsmStageTable table."
    INDEX { cucsEquipmentPsuFsmStageInstanceId }
    ::= { cucsEquipmentPsuFsmStageTable 1 }

CucsEquipmentPsuFsmStageEntry ::= SEQUENCE {
    cucsEquipmentPsuFsmStageInstanceId                               CucsManagedObjectId,
    cucsEquipmentPsuFsmStageDn                                       CucsManagedObjectDn,
    cucsEquipmentPsuFsmStageRn                                       SnmpAdminString,
    cucsEquipmentPsuFsmStageDescrData                                SnmpAdminString,
    cucsEquipmentPsuFsmStageLastUpdateTime                           DateAndTime,
    cucsEquipmentPsuFsmStageName                                     CucsEquipmentPsuFsmStageName,
    cucsEquipmentPsuFsmStageOrder                                    Gauge32,
    cucsEquipmentPsuFsmStageRetry                                    Gauge32,
    cucsEquipmentPsuFsmStageStageStatus                              CucsFsmFsmStageStatus
}

cucsEquipmentPsuFsmStageInstanceId OBJECT-TYPE
    SYNTAX       CucsManagedObjectId
    MAX-ACCESS   not-accessible
    STATUS       current
    DESCRIPTION
        "Instance identifier of the managed object."
    ::= { cucsEquipmentPsuFsmStageEntry 1 }

cucsEquipmentPsuFsmStageDn OBJECT-TYPE
    SYNTAX       CucsManagedObjectDn
    MAX-ACCESS   read-only
    STATUS       current
    DESCRIPTION
        "Cisco UCS equipment:PsuFsmStage:dn managed object property"
    ::= { cucsEquipmentPsuFsmStageEntry 2 }

cucsEquipmentPsuFsmStageRn OBJECT-TYPE
    SYNTAX       SnmpAdminString
    MAX-ACCESS   read-only
    STATUS       current
    DESCRIPTION
        "Cisco UCS equipment:PsuFsmStage:rn managed object property"
    ::= { cucsEquipmentPsuFsmStageEntry 3 }

cucsEquipmentPsuFsmStageDescrData OBJECT-TYPE
    SYNTAX       SnmpAdminString
    MAX-ACCESS   read-only
    STATUS       current
    DESCRIPTION
        "Cisco UCS equipment:PsuFsmStage:descr managed object property"
    ::= { cucsEquipmentPsuFsmStageEntry 4 }

cucsEquipmentPsuFsmStageLastUpdateTime OBJECT-TYPE
    SYNTAX       DateAndTime
    MAX-ACCESS   read-only
    STATUS       current
    DESCRIPTION
        "Cisco UCS equipment:PsuFsmStage:lastUpdateTime
        managed object property"
    ::= { cucsEquipmentPsuFsmStageEntry 5 }

cucsEquipmentPsuFsmStageName OBJECT-TYPE
    SYNTAX       CucsEquipmentPsuFsmStageName
    MAX-ACCESS   read-only
    STATUS       current
    DESCRIPTION
        "Cisco UCS equipment:PsuFsmStage:name managed object property"
    ::= { cucsEquipmentPsuFsmStageEntry 6 }

cucsEquipmentPsuFsmStageOrder OBJECT-TYPE
    SYNTAX       Gauge32
    MAX-ACCESS   read-only
    STATUS       current
    DESCRIPTION
        "Cisco UCS equipment:PsuFsmStage:order managed object property"
    ::= { cucsEquipmentPsuFsmStageEntry 7 }

cucsEquipmentPsuFsmStageRetry OBJECT-TYPE
    SYNTAX       Gauge32
    MAX-ACCESS   read-only
    STATUS       current
    DESCRIPTION
        "Cisco UCS equipment:PsuFsmStage:retry managed object property"
    ::= { cucsEquipmentPsuFsmStageEntry 8 }

cucsEquipmentPsuFsmStageStageStatus OBJECT-TYPE
    SYNTAX       CucsFsmFsmStageStatus
    MAX-ACCESS   read-only
    STATUS       current
    DESCRIPTION
        "Cisco UCS equipment:PsuFsmStage:stageStatus managed
        object property"
    ::= { cucsEquipmentPsuFsmStageEntry 9 }

cucsEquipmentPsuFsmTaskTable OBJECT-TYPE
    SYNTAX           SEQUENCE OF CucsEquipmentPsuFsmTaskEntry
    MAX-ACCESS       not-accessible
    STATUS           current
    DESCRIPTION
        "Cisco UCS equipment:PsuFsmTask managed object table"
    ::= { cucsEquipmentObjects 145 }

cucsEquipmentPsuFsmTaskEntry OBJECT-TYPE
    SYNTAX           CucsEquipmentPsuFsmTaskEntry
    MAX-ACCESS       not-accessible
    STATUS           current
    DESCRIPTION
        "Entry for the cucsEquipmentPsuFsmTaskTable table."
    INDEX { cucsEquipmentPsuFsmTaskInstanceId }
    ::= { cucsEquipmentPsuFsmTaskTable 1 }

CucsEquipmentPsuFsmTaskEntry ::= SEQUENCE {
    cucsEquipmentPsuFsmTaskInstanceId                                CucsManagedObjectId,
    cucsEquipmentPsuFsmTaskDn                                        CucsManagedObjectDn,
    cucsEquipmentPsuFsmTaskRn                                        SnmpAdminString,
    cucsEquipmentPsuFsmTaskCompletion                                CucsFsmCompletion,
    cucsEquipmentPsuFsmTaskFlags                                     CucsEquipmentPsuFsmTaskFlags,
    cucsEquipmentPsuFsmTaskItem                                      CucsEquipmentPsuFsmTaskItem,
    cucsEquipmentPsuFsmTaskSeqId                                     Gauge32
}

cucsEquipmentPsuFsmTaskInstanceId OBJECT-TYPE
    SYNTAX       CucsManagedObjectId
    MAX-ACCESS   not-accessible
    STATUS       current
    DESCRIPTION
        "Instance identifier of the managed object."
    ::= { cucsEquipmentPsuFsmTaskEntry 1 }

cucsEquipmentPsuFsmTaskDn OBJECT-TYPE
    SYNTAX       CucsManagedObjectDn
    MAX-ACCESS   read-only
    STATUS       current
    DESCRIPTION
        "Cisco UCS equipment:PsuFsmTask:dn managed object property"
    ::= { cucsEquipmentPsuFsmTaskEntry 2 }

cucsEquipmentPsuFsmTaskRn OBJECT-TYPE
    SYNTAX       SnmpAdminString
    MAX-ACCESS   read-only
    STATUS       current
    DESCRIPTION
        "Cisco UCS equipment:PsuFsmTask:rn managed object property"
    ::= { cucsEquipmentPsuFsmTaskEntry 3 }

cucsEquipmentPsuFsmTaskCompletion OBJECT-TYPE
    SYNTAX       CucsFsmCompletion
    MAX-ACCESS   read-only
    STATUS       current
    DESCRIPTION
        "Cisco UCS equipment:PsuFsmTask:completion managed
        object property"
    ::= { cucsEquipmentPsuFsmTaskEntry 4 }

cucsEquipmentPsuFsmTaskFlags OBJECT-TYPE
    SYNTAX       CucsEquipmentPsuFsmTaskFlags
    MAX-ACCESS   read-only
    STATUS       current
    DESCRIPTION
        "Cisco UCS equipment:PsuFsmTask:flags managed object property"
    ::= { cucsEquipmentPsuFsmTaskEntry 5 }

cucsEquipmentPsuFsmTaskItem OBJECT-TYPE
    SYNTAX       CucsEquipmentPsuFsmTaskItem
    MAX-ACCESS   read-only
    STATUS       current
    DESCRIPTION
        "Cisco UCS equipment:PsuFsmTask:item managed object property"
    ::= { cucsEquipmentPsuFsmTaskEntry 6 }

cucsEquipmentPsuFsmTaskSeqId OBJECT-TYPE
    SYNTAX       Gauge32
    MAX-ACCESS   read-only
    STATUS       current
    DESCRIPTION
        "Cisco UCS equipment:PsuFsmTask:seqId managed object property"
    ::= { cucsEquipmentPsuFsmTaskEntry 7 }

cucsEquipmentPsuInputStatsTable OBJECT-TYPE
    SYNTAX           SEQUENCE OF CucsEquipmentPsuInputStatsEntry
    MAX-ACCESS       not-accessible
    STATUS           current
    DESCRIPTION
        "Cisco UCS equipment:PsuInputStats managed object table"
    ::= { cucsEquipmentObjects 58 }

cucsEquipmentPsuInputStatsEntry OBJECT-TYPE
    SYNTAX           CucsEquipmentPsuInputStatsEntry
    MAX-ACCESS       not-accessible
    STATUS           current
    DESCRIPTION
        "Entry for the cucsEquipmentPsuInputStatsTable table."
    INDEX { cucsEquipmentPsuInputStatsInstanceId }
    ::= { cucsEquipmentPsuInputStatsTable 1 }

CucsEquipmentPsuInputStatsEntry ::= SEQUENCE {
    cucsEquipmentPsuInputStatsInstanceId                             CucsManagedObjectId,
    cucsEquipmentPsuInputStatsDn                                     CucsManagedObjectDn,
    cucsEquipmentPsuInputStatsRn                                     SnmpAdminString,
    cucsEquipmentPsuInputStatsCurrent                                INTEGER,
    cucsEquipmentPsuInputStatsCurrentAvg                             INTEGER,
    cucsEquipmentPsuInputStatsCurrentMax                             INTEGER,
    cucsEquipmentPsuInputStatsCurrentMin                             INTEGER,
    cucsEquipmentPsuInputStatsInputStatus                            SnmpAdminString,
    cucsEquipmentPsuInputStatsIntervals                              Gauge32,
    cucsEquipmentPsuInputStatsPower                                  INTEGER,
    cucsEquipmentPsuInputStatsPowerAvg                               INTEGER,
    cucsEquipmentPsuInputStatsPowerMax                               INTEGER,
    cucsEquipmentPsuInputStatsPowerMin                               INTEGER,
    cucsEquipmentPsuInputStatsSuspect                                TruthValue,
    cucsEquipmentPsuInputStatsThresholded                            CucsEquipmentPsuInputStatsThresholded,
    cucsEquipmentPsuInputStatsTimeCollected                          DateAndTime,
    cucsEquipmentPsuInputStatsUpdate                                 Gauge32,
    cucsEquipmentPsuInputStatsVoltage                                INTEGER,
    cucsEquipmentPsuInputStatsVoltageAvg                             INTEGER,
    cucsEquipmentPsuInputStatsVoltageMax                             INTEGER,
    cucsEquipmentPsuInputStatsVoltageMin                             INTEGER
}

cucsEquipmentPsuInputStatsInstanceId OBJECT-TYPE
    SYNTAX       CucsManagedObjectId
    MAX-ACCESS   not-accessible
    STATUS       current
    DESCRIPTION
        "Instance identifier of the managed object."
    ::= { cucsEquipmentPsuInputStatsEntry 1 }

cucsEquipmentPsuInputStatsDn OBJECT-TYPE
    SYNTAX       CucsManagedObjectDn
    MAX-ACCESS   read-only
    STATUS       current
    DESCRIPTION
        "Cisco UCS equipment:PsuInputStats:dn managed object property"
    ::= { cucsEquipmentPsuInputStatsEntry 2 }

cucsEquipmentPsuInputStatsRn OBJECT-TYPE
    SYNTAX       SnmpAdminString
    MAX-ACCESS   read-only
    STATUS       current
    DESCRIPTION
        "Cisco UCS equipment:PsuInputStats:rn managed object property"
    ::= { cucsEquipmentPsuInputStatsEntry 3 }

cucsEquipmentPsuInputStatsCurrent OBJECT-TYPE
    SYNTAX       INTEGER
    MAX-ACCESS   read-only
    STATUS       current
    DESCRIPTION
        "Cisco UCS equipment:PsuInputStats:current managed
        object property"
    ::= { cucsEquipmentPsuInputStatsEntry 4 }

cucsEquipmentPsuInputStatsCurrentAvg OBJECT-TYPE
    SYNTAX       INTEGER
    MAX-ACCESS   read-only
    STATUS       current
    DESCRIPTION
        "Cisco UCS equipment:PsuInputStats:currentAvg managed
        object property"
    ::= { cucsEquipmentPsuInputStatsEntry 5 }

cucsEquipmentPsuInputStatsCurrentMax OBJECT-TYPE
    SYNTAX       INTEGER
    MAX-ACCESS   read-only
    STATUS       current
    DESCRIPTION
        "Cisco UCS equipment:PsuInputStats:currentMax managed
        object property"
    ::= { cucsEquipmentPsuInputStatsEntry 6 }

cucsEquipmentPsuInputStatsCurrentMin OBJECT-TYPE
    SYNTAX       INTEGER
    MAX-ACCESS   read-only
    STATUS       current
    DESCRIPTION
        "Cisco UCS equipment:PsuInputStats:currentMin managed
        object property"
    ::= { cucsEquipmentPsuInputStatsEntry 7 }

cucsEquipmentPsuInputStatsInputStatus OBJECT-TYPE
    SYNTAX       SnmpAdminString
    MAX-ACCESS   read-only
    STATUS       current
    DESCRIPTION
        "Cisco UCS equipment:PsuInputStats:inputStatus
        managed object property"
    ::= { cucsEquipmentPsuInputStatsEntry 8 }

cucsEquipmentPsuInputStatsIntervals OBJECT-TYPE
    SYNTAX       Gauge32
    MAX-ACCESS   read-only
    STATUS       current
    DESCRIPTION
        "Cisco UCS equipment:PsuInputStats:intervals managed
        object property"
    ::= { cucsEquipmentPsuInputStatsEntry 9 }

cucsEquipmentPsuInputStatsPower OBJECT-TYPE
    SYNTAX       INTEGER
    MAX-ACCESS   read-only
    STATUS       current
    DESCRIPTION
        "Cisco UCS equipment:PsuInputStats:power managed object property"
    ::= { cucsEquipmentPsuInputStatsEntry 10 }

cucsEquipmentPsuInputStatsPowerAvg OBJECT-TYPE
    SYNTAX       INTEGER
    MAX-ACCESS   read-only
    STATUS       current
    DESCRIPTION
        "Cisco UCS equipment:PsuInputStats:powerAvg managed
        object property"
    ::= { cucsEquipmentPsuInputStatsEntry 11 }

cucsEquipmentPsuInputStatsPowerMax OBJECT-TYPE
    SYNTAX       INTEGER
    MAX-ACCESS   read-only
    STATUS       current
    DESCRIPTION
        "Cisco UCS equipment:PsuInputStats:powerMax managed
        object property"
    ::= { cucsEquipmentPsuInputStatsEntry 12 }

cucsEquipmentPsuInputStatsPowerMin OBJECT-TYPE
    SYNTAX       INTEGER
    MAX-ACCESS   read-only
    STATUS       current
    DESCRIPTION
        "Cisco UCS equipment:PsuInputStats:powerMin managed
        object property"
    ::= { cucsEquipmentPsuInputStatsEntry 13 }

cucsEquipmentPsuInputStatsSuspect OBJECT-TYPE
    SYNTAX       TruthValue
    MAX-ACCESS   read-only
    STATUS       current
    DESCRIPTION
        "Cisco UCS equipment:PsuInputStats:suspect managed
        object property"
    ::= { cucsEquipmentPsuInputStatsEntry 14 }

cucsEquipmentPsuInputStatsThresholded OBJECT-TYPE
    SYNTAX       CucsEquipmentPsuInputStatsThresholded
    MAX-ACCESS   read-only
    STATUS       current
    DESCRIPTION
        "Cisco UCS equipment:PsuInputStats:thresholded
        managed object property"
    ::= { cucsEquipmentPsuInputStatsEntry 15 }

cucsEquipmentPsuInputStatsTimeCollected OBJECT-TYPE
    SYNTAX       DateAndTime
    MAX-ACCESS   read-only
    STATUS       current
    DESCRIPTION
        "Cisco UCS equipment:PsuInputStats:timeCollected
        managed object property"
    ::= { cucsEquipmentPsuInputStatsEntry 16 }

cucsEquipmentPsuInputStatsUpdate OBJECT-TYPE
    SYNTAX       Gauge32
    MAX-ACCESS   read-only
    STATUS       current
    DESCRIPTION
        "Cisco UCS equipment:PsuInputStats:update managed object property"
    ::= { cucsEquipmentPsuInputStatsEntry 17 }

cucsEquipmentPsuInputStatsVoltage OBJECT-TYPE
    SYNTAX       INTEGER
    MAX-ACCESS   read-only
    STATUS       current
    DESCRIPTION
        "Cisco UCS equipment:PsuInputStats:voltage managed
        object property"
    ::= { cucsEquipmentPsuInputStatsEntry 18 }

cucsEquipmentPsuInputStatsVoltageAvg OBJECT-TYPE
    SYNTAX       INTEGER
    MAX-ACCESS   read-only
    STATUS       current
    DESCRIPTION
        "Cisco UCS equipment:PsuInputStats:voltageAvg managed
        object property"
    ::= { cucsEquipmentPsuInputStatsEntry 19 }

cucsEquipmentPsuInputStatsVoltageMax OBJECT-TYPE
    SYNTAX       INTEGER
    MAX-ACCESS   read-only
    STATUS       current
    DESCRIPTION
        "Cisco UCS equipment:PsuInputStats:voltageMax managed
        object property"
    ::= { cucsEquipmentPsuInputStatsEntry 20 }

cucsEquipmentPsuInputStatsVoltageMin OBJECT-TYPE
    SYNTAX       INTEGER
    MAX-ACCESS   read-only
    STATUS       current
    DESCRIPTION
        "Cisco UCS equipment:PsuInputStats:voltageMin managed
        object property"
    ::= { cucsEquipmentPsuInputStatsEntry 21 }

cucsEquipmentPsuInputStatsHistTable OBJECT-TYPE
    SYNTAX           SEQUENCE OF CucsEquipmentPsuInputStatsHistEntry
    MAX-ACCESS       not-accessible
    STATUS           current
    DESCRIPTION
        "Cisco UCS equipment:PsuInputStatsHist managed object table"
    ::= { cucsEquipmentObjects 59 }

cucsEquipmentPsuInputStatsHistEntry OBJECT-TYPE
    SYNTAX           CucsEquipmentPsuInputStatsHistEntry
    MAX-ACCESS       not-accessible
    STATUS           current
    DESCRIPTION
        "Entry for the cucsEquipmentPsuInputStatsHistTable table."
    INDEX { cucsEquipmentPsuInputStatsHistInstanceId }
    ::= { cucsEquipmentPsuInputStatsHistTable 1 }

CucsEquipmentPsuInputStatsHistEntry ::= SEQUENCE {
    cucsEquipmentPsuInputStatsHistInstanceId                         CucsManagedObjectId,
    cucsEquipmentPsuInputStatsHistDn                                 CucsManagedObjectDn,
    cucsEquipmentPsuInputStatsHistRn                                 SnmpAdminString,
    cucsEquipmentPsuInputStatsHistCurrent                            INTEGER,
    cucsEquipmentPsuInputStatsHistCurrentAvg                         INTEGER,
    cucsEquipmentPsuInputStatsHistCurrentMax                         INTEGER,
    cucsEquipmentPsuInputStatsHistCurrentMin                         INTEGER,
    cucsEquipmentPsuInputStatsHistId                                 Unsigned64,
    cucsEquipmentPsuInputStatsHistMostRecent                         TruthValue,
    cucsEquipmentPsuInputStatsHistPower                              INTEGER,
    cucsEquipmentPsuInputStatsHistPowerAvg                           INTEGER,
    cucsEquipmentPsuInputStatsHistPowerMax                           INTEGER,
    cucsEquipmentPsuInputStatsHistPowerMin                           INTEGER,
    cucsEquipmentPsuInputStatsHistSuspect                            TruthValue,
    cucsEquipmentPsuInputStatsHistThresholded                        CucsEquipmentPsuInputStatsHistThresholded,
    cucsEquipmentPsuInputStatsHistTimeCollected                      DateAndTime,
    cucsEquipmentPsuInputStatsHistVoltage                            INTEGER,
    cucsEquipmentPsuInputStatsHistVoltageAvg                         INTEGER,
    cucsEquipmentPsuInputStatsHistVoltageMax                         INTEGER,
    cucsEquipmentPsuInputStatsHistVoltageMin                         INTEGER
}

cucsEquipmentPsuInputStatsHistInstanceId OBJECT-TYPE
    SYNTAX       CucsManagedObjectId
    MAX-ACCESS   not-accessible
    STATUS       current
    DESCRIPTION
        "Instance identifier of the managed object."
    ::= { cucsEquipmentPsuInputStatsHistEntry 1 }

cucsEquipmentPsuInputStatsHistDn OBJECT-TYPE
    SYNTAX       CucsManagedObjectDn
    MAX-ACCESS   read-only
    STATUS       current
    DESCRIPTION
        "Cisco UCS equipment:PsuInputStatsHist:dn managed object property"
    ::= { cucsEquipmentPsuInputStatsHistEntry 2 }

cucsEquipmentPsuInputStatsHistRn OBJECT-TYPE
    SYNTAX       SnmpAdminString
    MAX-ACCESS   read-only
    STATUS       current
    DESCRIPTION
        "Cisco UCS equipment:PsuInputStatsHist:rn managed object property"
    ::= { cucsEquipmentPsuInputStatsHistEntry 3 }

cucsEquipmentPsuInputStatsHistCurrent OBJECT-TYPE
    SYNTAX       INTEGER
    MAX-ACCESS   read-only
    STATUS       current
    DESCRIPTION
        "Cisco UCS equipment:PsuInputStatsHist:current
        managed object property"
    ::= { cucsEquipmentPsuInputStatsHistEntry 4 }

cucsEquipmentPsuInputStatsHistCurrentAvg OBJECT-TYPE
    SYNTAX       INTEGER
    MAX-ACCESS   read-only
    STATUS       current
    DESCRIPTION
        "Cisco UCS equipment:PsuInputStatsHist:currentAvg
        managed object property"
    ::= { cucsEquipmentPsuInputStatsHistEntry 5 }

cucsEquipmentPsuInputStatsHistCurrentMax OBJECT-TYPE
    SYNTAX       INTEGER
    MAX-ACCESS   read-only
    STATUS       current
    DESCRIPTION
        "Cisco UCS equipment:PsuInputStatsHist:currentMax
        managed object property"
    ::= { cucsEquipmentPsuInputStatsHistEntry 6 }

cucsEquipmentPsuInputStatsHistCurrentMin OBJECT-TYPE
    SYNTAX       INTEGER
    MAX-ACCESS   read-only
    STATUS       current
    DESCRIPTION
        "Cisco UCS equipment:PsuInputStatsHist:currentMin
        managed object property"
    ::= { cucsEquipmentPsuInputStatsHistEntry 7 }

cucsEquipmentPsuInputStatsHistId OBJECT-TYPE
    SYNTAX       Unsigned64
    MAX-ACCESS   read-only
    STATUS       current
    DESCRIPTION
        "Cisco UCS equipment:PsuInputStatsHist:id managed object property"
    ::= { cucsEquipmentPsuInputStatsHistEntry 8 }

cucsEquipmentPsuInputStatsHistMostRecent OBJECT-TYPE
    SYNTAX       TruthValue
    MAX-ACCESS   read-only
    STATUS       current
    DESCRIPTION
        "Cisco UCS equipment:PsuInputStatsHist:mostRecent
        managed object property"
    ::= { cucsEquipmentPsuInputStatsHistEntry 9 }

cucsEquipmentPsuInputStatsHistPower OBJECT-TYPE
    SYNTAX       INTEGER
    MAX-ACCESS   read-only
    STATUS       current
    DESCRIPTION
        "Cisco UCS equipment:PsuInputStatsHist:power managed
        object property"
    ::= { cucsEquipmentPsuInputStatsHistEntry 10 }

cucsEquipmentPsuInputStatsHistPowerAvg OBJECT-TYPE
    SYNTAX       INTEGER
    MAX-ACCESS   read-only
    STATUS       current
    DESCRIPTION
        "Cisco UCS equipment:PsuInputStatsHist:powerAvg
        managed object property"
    ::= { cucsEquipmentPsuInputStatsHistEntry 11 }

cucsEquipmentPsuInputStatsHistPowerMax OBJECT-TYPE
    SYNTAX       INTEGER
    MAX-ACCESS   read-only
    STATUS       current
    DESCRIPTION
        "Cisco UCS equipment:PsuInputStatsHist:powerMax
        managed object property"
    ::= { cucsEquipmentPsuInputStatsHistEntry 12 }

cucsEquipmentPsuInputStatsHistPowerMin OBJECT-TYPE
    SYNTAX       INTEGER
    MAX-ACCESS   read-only
    STATUS       current
    DESCRIPTION
        "Cisco UCS equipment:PsuInputStatsHist:powerMin
        managed object property"
    ::= { cucsEquipmentPsuInputStatsHistEntry 13 }

cucsEquipmentPsuInputStatsHistSuspect OBJECT-TYPE
    SYNTAX       TruthValue
    MAX-ACCESS   read-only
    STATUS       current
    DESCRIPTION
        "Cisco UCS equipment:PsuInputStatsHist:suspect
        managed object property"
    ::= { cucsEquipmentPsuInputStatsHistEntry 14 }

cucsEquipmentPsuInputStatsHistThresholded OBJECT-TYPE
    SYNTAX       CucsEquipmentPsuInputStatsHistThresholded
    MAX-ACCESS   read-only
    STATUS       current
    DESCRIPTION
        "Cisco UCS equipment:PsuInputStatsHist:thresholded
        managed object property"
    ::= { cucsEquipmentPsuInputStatsHistEntry 15 }

cucsEquipmentPsuInputStatsHistTimeCollected OBJECT-TYPE
    SYNTAX       DateAndTime
    MAX-ACCESS   read-only
    STATUS       current
    DESCRIPTION
        "Cisco UCS equipment:PsuInputStatsHist:timeCollected
        managed object property"
    ::= { cucsEquipmentPsuInputStatsHistEntry 16 }

cucsEquipmentPsuInputStatsHistVoltage OBJECT-TYPE
    SYNTAX       INTEGER
    MAX-ACCESS   read-only
    STATUS       current
    DESCRIPTION
        "Cisco UCS equipment:PsuInputStatsHist:voltage
        managed object property"
    ::= { cucsEquipmentPsuInputStatsHistEntry 17 }

cucsEquipmentPsuInputStatsHistVoltageAvg OBJECT-TYPE
    SYNTAX       INTEGER
    MAX-ACCESS   read-only
    STATUS       current
    DESCRIPTION
        "Cisco UCS equipment:PsuInputStatsHist:voltageAvg
        managed object property"
    ::= { cucsEquipmentPsuInputStatsHistEntry 18 }

cucsEquipmentPsuInputStatsHistVoltageMax OBJECT-TYPE
    SYNTAX       INTEGER
    MAX-ACCESS   read-only
    STATUS       current
    DESCRIPTION
        "Cisco UCS equipment:PsuInputStatsHist:voltageMax
        managed object property"
    ::= { cucsEquipmentPsuInputStatsHistEntry 19 }

cucsEquipmentPsuInputStatsHistVoltageMin OBJECT-TYPE
    SYNTAX       INTEGER
    MAX-ACCESS   read-only
    STATUS       current
    DESCRIPTION
        "Cisco UCS equipment:PsuInputStatsHist:voltageMin
        managed object property"
    ::= { cucsEquipmentPsuInputStatsHistEntry 20 }

cucsEquipmentPsuOutputStatsTable OBJECT-TYPE
    SYNTAX           SEQUENCE OF CucsEquipmentPsuOutputStatsEntry
    MAX-ACCESS       not-accessible
    STATUS           current
    DESCRIPTION
        "Cisco UCS equipment:PsuOutputStats managed object table"
    ::= { cucsEquipmentObjects 92 }

cucsEquipmentPsuOutputStatsEntry OBJECT-TYPE
    SYNTAX           CucsEquipmentPsuOutputStatsEntry
    MAX-ACCESS       not-accessible
    STATUS           current
    DESCRIPTION
        "Entry for the cucsEquipmentPsuOutputStatsTable table."
    INDEX { cucsEquipmentPsuOutputStatsInstanceId }
    ::= { cucsEquipmentPsuOutputStatsTable 1 }

CucsEquipmentPsuOutputStatsEntry ::= SEQUENCE {
    cucsEquipmentPsuOutputStatsInstanceId                            CucsManagedObjectId,
    cucsEquipmentPsuOutputStatsDn                                    CucsManagedObjectDn,
    cucsEquipmentPsuOutputStatsRn                                    SnmpAdminString,
    cucsEquipmentPsuOutputStatsCurrent                               INTEGER,
    cucsEquipmentPsuOutputStatsCurrentAvg                            INTEGER,
    cucsEquipmentPsuOutputStatsCurrentMax                            INTEGER,
    cucsEquipmentPsuOutputStatsCurrentMin                            INTEGER,
    cucsEquipmentPsuOutputStatsIntervals                             Gauge32,
    cucsEquipmentPsuOutputStatsOutputStatus                          SnmpAdminString,
    cucsEquipmentPsuOutputStatsPower                                 INTEGER,
    cucsEquipmentPsuOutputStatsPowerAvg                              INTEGER,
    cucsEquipmentPsuOutputStatsPowerMax                              INTEGER,
    cucsEquipmentPsuOutputStatsPowerMin                              INTEGER,
    cucsEquipmentPsuOutputStatsSuspect                               TruthValue,
    cucsEquipmentPsuOutputStatsThresholded                           CucsEquipmentPsuOutputStatsThresholded,
    cucsEquipmentPsuOutputStatsTimeCollected                         DateAndTime,
    cucsEquipmentPsuOutputStatsUpdate                                Gauge32,
    cucsEquipmentPsuOutputStatsVoltage                               INTEGER,
    cucsEquipmentPsuOutputStatsVoltageAvg                            INTEGER,
    cucsEquipmentPsuOutputStatsVoltageMax                            INTEGER,
    cucsEquipmentPsuOutputStatsVoltageMin                            INTEGER
}

cucsEquipmentPsuOutputStatsInstanceId OBJECT-TYPE
    SYNTAX       CucsManagedObjectId
    MAX-ACCESS   not-accessible
    STATUS       current
    DESCRIPTION
        "Instance identifier of the managed object."
    ::= { cucsEquipmentPsuOutputStatsEntry 1 }

cucsEquipmentPsuOutputStatsDn OBJECT-TYPE
    SYNTAX       CucsManagedObjectDn
    MAX-ACCESS   read-only
    STATUS       current
    DESCRIPTION
        "Cisco UCS equipment:PsuOutputStats:dn managed object property"
    ::= { cucsEquipmentPsuOutputStatsEntry 2 }

cucsEquipmentPsuOutputStatsRn OBJECT-TYPE
    SYNTAX       SnmpAdminString
    MAX-ACCESS   read-only
    STATUS       current
    DESCRIPTION
        "Cisco UCS equipment:PsuOutputStats:rn managed object property"
    ::= { cucsEquipmentPsuOutputStatsEntry 3 }

cucsEquipmentPsuOutputStatsCurrent OBJECT-TYPE
    SYNTAX       INTEGER
    MAX-ACCESS   read-only
    STATUS       current
    DESCRIPTION
        "Cisco UCS equipment:PsuOutputStats:current managed
        object property"
    ::= { cucsEquipmentPsuOutputStatsEntry 4 }

cucsEquipmentPsuOutputStatsCurrentAvg OBJECT-TYPE
    SYNTAX       INTEGER
    MAX-ACCESS   read-only
    STATUS       current
    DESCRIPTION
        "Cisco UCS equipment:PsuOutputStats:currentAvg
        managed object property"
    ::= { cucsEquipmentPsuOutputStatsEntry 5 }

cucsEquipmentPsuOutputStatsCurrentMax OBJECT-TYPE
    SYNTAX       INTEGER
    MAX-ACCESS   read-only
    STATUS       current
    DESCRIPTION
        "Cisco UCS equipment:PsuOutputStats:currentMax
        managed object property"
    ::= { cucsEquipmentPsuOutputStatsEntry 6 }

cucsEquipmentPsuOutputStatsCurrentMin OBJECT-TYPE
    SYNTAX       INTEGER
    MAX-ACCESS   read-only
    STATUS       current
    DESCRIPTION
        "Cisco UCS equipment:PsuOutputStats:currentMin
        managed object property"
    ::= { cucsEquipmentPsuOutputStatsEntry 7 }

cucsEquipmentPsuOutputStatsIntervals OBJECT-TYPE
    SYNTAX       Gauge32
    MAX-ACCESS   read-only
    STATUS       current
    DESCRIPTION
        "Cisco UCS equipment:PsuOutputStats:intervals managed
        object property"
    ::= { cucsEquipmentPsuOutputStatsEntry 8 }

cucsEquipmentPsuOutputStatsOutputStatus OBJECT-TYPE
    SYNTAX       SnmpAdminString
    MAX-ACCESS   read-only
    STATUS       current
    DESCRIPTION
        "Cisco UCS equipment:PsuOutputStats:outputStatus
        managed object property"
    ::= { cucsEquipmentPsuOutputStatsEntry 9 }

cucsEquipmentPsuOutputStatsPower OBJECT-TYPE
    SYNTAX       INTEGER
    MAX-ACCESS   read-only
    STATUS       current
    DESCRIPTION
        "Cisco UCS equipment:PsuOutputStats:power managed object property"
    ::= { cucsEquipmentPsuOutputStatsEntry 10 }

cucsEquipmentPsuOutputStatsPowerAvg OBJECT-TYPE
    SYNTAX       INTEGER
    MAX-ACCESS   read-only
    STATUS       current
    DESCRIPTION
        "Cisco UCS equipment:PsuOutputStats:powerAvg managed
        object property"
    ::= { cucsEquipmentPsuOutputStatsEntry 11 }

cucsEquipmentPsuOutputStatsPowerMax OBJECT-TYPE
    SYNTAX       INTEGER
    MAX-ACCESS   read-only
    STATUS       current
    DESCRIPTION
        "Cisco UCS equipment:PsuOutputStats:powerMax managed
        object property"
    ::= { cucsEquipmentPsuOutputStatsEntry 12 }

cucsEquipmentPsuOutputStatsPowerMin OBJECT-TYPE
    SYNTAX       INTEGER
    MAX-ACCESS   read-only
    STATUS       current
    DESCRIPTION
        "Cisco UCS equipment:PsuOutputStats:powerMin managed
        object property"
    ::= { cucsEquipmentPsuOutputStatsEntry 13 }

cucsEquipmentPsuOutputStatsSuspect OBJECT-TYPE
    SYNTAX       TruthValue
    MAX-ACCESS   read-only
    STATUS       current
    DESCRIPTION
        "Cisco UCS equipment:PsuOutputStats:suspect managed
        object property"
    ::= { cucsEquipmentPsuOutputStatsEntry 14 }

cucsEquipmentPsuOutputStatsThresholded OBJECT-TYPE
    SYNTAX       CucsEquipmentPsuOutputStatsThresholded
    MAX-ACCESS   read-only
    STATUS       current
    DESCRIPTION
        "Cisco UCS equipment:PsuOutputStats:thresholded
        managed object property"
    ::= { cucsEquipmentPsuOutputStatsEntry 15 }

cucsEquipmentPsuOutputStatsTimeCollected OBJECT-TYPE
    SYNTAX       DateAndTime
    MAX-ACCESS   read-only
    STATUS       current
    DESCRIPTION
        "Cisco UCS equipment:PsuOutputStats:timeCollected
        managed object property"
    ::= { cucsEquipmentPsuOutputStatsEntry 16 }

cucsEquipmentPsuOutputStatsUpdate OBJECT-TYPE
    SYNTAX       Gauge32
    MAX-ACCESS   read-only
    STATUS       current
    DESCRIPTION
        "Cisco UCS equipment:PsuOutputStats:update managed
        object property"
    ::= { cucsEquipmentPsuOutputStatsEntry 17 }

cucsEquipmentPsuOutputStatsVoltage OBJECT-TYPE
    SYNTAX       INTEGER
    MAX-ACCESS   read-only
    STATUS       current
    DESCRIPTION
        "Cisco UCS equipment:PsuOutputStats:voltage managed
        object property"
    ::= { cucsEquipmentPsuOutputStatsEntry 18 }

cucsEquipmentPsuOutputStatsVoltageAvg OBJECT-TYPE
    SYNTAX       INTEGER
    MAX-ACCESS   read-only
    STATUS       current
    DESCRIPTION
        "Cisco UCS equipment:PsuOutputStats:voltageAvg
        managed object property"
    ::= { cucsEquipmentPsuOutputStatsEntry 19 }

cucsEquipmentPsuOutputStatsVoltageMax OBJECT-TYPE
    SYNTAX       INTEGER
    MAX-ACCESS   read-only
    STATUS       current
    DESCRIPTION
        "Cisco UCS equipment:PsuOutputStats:voltageMax
        managed object property"
    ::= { cucsEquipmentPsuOutputStatsEntry 20 }

cucsEquipmentPsuOutputStatsVoltageMin OBJECT-TYPE
    SYNTAX       INTEGER
    MAX-ACCESS   read-only
    STATUS       current
    DESCRIPTION
        "Cisco UCS equipment:PsuOutputStats:voltageMin
        managed object property"
    ::= { cucsEquipmentPsuOutputStatsEntry 21 }

cucsEquipmentPsuOutputStatsHistTable OBJECT-TYPE
    SYNTAX           SEQUENCE OF CucsEquipmentPsuOutputStatsHistEntry
    MAX-ACCESS       not-accessible
    STATUS           current
    DESCRIPTION
        "Cisco UCS equipment:PsuOutputStatsHist managed object table"
    ::= { cucsEquipmentObjects 93 }

cucsEquipmentPsuOutputStatsHistEntry OBJECT-TYPE
    SYNTAX           CucsEquipmentPsuOutputStatsHistEntry
    MAX-ACCESS       not-accessible
    STATUS           current
    DESCRIPTION
        "Entry for the cucsEquipmentPsuOutputStatsHistTable table."
    INDEX { cucsEquipmentPsuOutputStatsHistInstanceId }
    ::= { cucsEquipmentPsuOutputStatsHistTable 1 }

CucsEquipmentPsuOutputStatsHistEntry ::= SEQUENCE {
    cucsEquipmentPsuOutputStatsHistInstanceId                        CucsManagedObjectId,
    cucsEquipmentPsuOutputStatsHistDn                                CucsManagedObjectDn,
    cucsEquipmentPsuOutputStatsHistRn                                SnmpAdminString,
    cucsEquipmentPsuOutputStatsHistCurrent                           INTEGER,
    cucsEquipmentPsuOutputStatsHistCurrentAvg                        INTEGER,
    cucsEquipmentPsuOutputStatsHistCurrentMax                        INTEGER,
    cucsEquipmentPsuOutputStatsHistCurrentMin                        INTEGER,
    cucsEquipmentPsuOutputStatsHistId                                Unsigned64,
    cucsEquipmentPsuOutputStatsHistMostRecent                        TruthValue,
    cucsEquipmentPsuOutputStatsHistPower                             INTEGER,
    cucsEquipmentPsuOutputStatsHistPowerAvg                          INTEGER,
    cucsEquipmentPsuOutputStatsHistPowerMax                          INTEGER,
    cucsEquipmentPsuOutputStatsHistPowerMin                          INTEGER,
    cucsEquipmentPsuOutputStatsHistSuspect                           TruthValue,
    cucsEquipmentPsuOutputStatsHistThresholded                       CucsEquipmentPsuOutputStatsHistThresholded,
    cucsEquipmentPsuOutputStatsHistTimeCollected                     DateAndTime,
    cucsEquipmentPsuOutputStatsHistVoltage                           INTEGER,
    cucsEquipmentPsuOutputStatsHistVoltageAvg                        INTEGER,
    cucsEquipmentPsuOutputStatsHistVoltageMax                        INTEGER,
    cucsEquipmentPsuOutputStatsHistVoltageMin                        INTEGER
}

cucsEquipmentPsuOutputStatsHistInstanceId OBJECT-TYPE
    SYNTAX       CucsManagedObjectId
    MAX-ACCESS   not-accessible
    STATUS       current
    DESCRIPTION
        "Instance identifier of the managed object."
    ::= { cucsEquipmentPsuOutputStatsHistEntry 1 }

cucsEquipmentPsuOutputStatsHistDn OBJECT-TYPE
    SYNTAX       CucsManagedObjectDn
    MAX-ACCESS   read-only
    STATUS       current
    DESCRIPTION
        "Cisco UCS equipment:PsuOutputStatsHist:dn managed
        object property"
    ::= { cucsEquipmentPsuOutputStatsHistEntry 2 }

cucsEquipmentPsuOutputStatsHistRn OBJECT-TYPE
    SYNTAX       SnmpAdminString
    MAX-ACCESS   read-only
    STATUS       current
    DESCRIPTION
        "Cisco UCS equipment:PsuOutputStatsHist:rn managed
        object property"
    ::= { cucsEquipmentPsuOutputStatsHistEntry 3 }

cucsEquipmentPsuOutputStatsHistCurrent OBJECT-TYPE
    SYNTAX       INTEGER
    MAX-ACCESS   read-only
    STATUS       current
    DESCRIPTION
        "Cisco UCS equipment:PsuOutputStatsHist:current
        managed object property"
    ::= { cucsEquipmentPsuOutputStatsHistEntry 4 }

cucsEquipmentPsuOutputStatsHistCurrentAvg OBJECT-TYPE
    SYNTAX       INTEGER
    MAX-ACCESS   read-only
    STATUS       current
    DESCRIPTION
        "Cisco UCS equipment:PsuOutputStatsHist:currentAvg
        managed object property"
    ::= { cucsEquipmentPsuOutputStatsHistEntry 5 }

cucsEquipmentPsuOutputStatsHistCurrentMax OBJECT-TYPE
    SYNTAX       INTEGER
    MAX-ACCESS   read-only
    STATUS       current
    DESCRIPTION
        "Cisco UCS equipment:PsuOutputStatsHist:currentMax
        managed object property"
    ::= { cucsEquipmentPsuOutputStatsHistEntry 6 }

cucsEquipmentPsuOutputStatsHistCurrentMin OBJECT-TYPE
    SYNTAX       INTEGER
    MAX-ACCESS   read-only
    STATUS       current
    DESCRIPTION
        "Cisco UCS equipment:PsuOutputStatsHist:currentMin
        managed object property"
    ::= { cucsEquipmentPsuOutputStatsHistEntry 7 }

cucsEquipmentPsuOutputStatsHistId OBJECT-TYPE
    SYNTAX       Unsigned64
    MAX-ACCESS   read-only
    STATUS       current
    DESCRIPTION
        "Cisco UCS equipment:PsuOutputStatsHist:id managed
        object property"
    ::= { cucsEquipmentPsuOutputStatsHistEntry 8 }

cucsEquipmentPsuOutputStatsHistMostRecent OBJECT-TYPE
    SYNTAX       TruthValue
    MAX-ACCESS   read-only
    STATUS       current
    DESCRIPTION
        "Cisco UCS equipment:PsuOutputStatsHist:mostRecent
        managed object property"
    ::= { cucsEquipmentPsuOutputStatsHistEntry 9 }

cucsEquipmentPsuOutputStatsHistPower OBJECT-TYPE
    SYNTAX       INTEGER
    MAX-ACCESS   read-only
    STATUS       current
    DESCRIPTION
        "Cisco UCS equipment:PsuOutputStatsHist:power managed
        object property"
    ::= { cucsEquipmentPsuOutputStatsHistEntry 10 }

cucsEquipmentPsuOutputStatsHistPowerAvg OBJECT-TYPE
    SYNTAX       INTEGER
    MAX-ACCESS   read-only
    STATUS       current
    DESCRIPTION
        "Cisco UCS equipment:PsuOutputStatsHist:powerAvg
        managed object property"
    ::= { cucsEquipmentPsuOutputStatsHistEntry 11 }

cucsEquipmentPsuOutputStatsHistPowerMax OBJECT-TYPE
    SYNTAX       INTEGER
    MAX-ACCESS   read-only
    STATUS       current
    DESCRIPTION
        "Cisco UCS equipment:PsuOutputStatsHist:powerMax
        managed object property"
    ::= { cucsEquipmentPsuOutputStatsHistEntry 12 }

cucsEquipmentPsuOutputStatsHistPowerMin OBJECT-TYPE
    SYNTAX       INTEGER
    MAX-ACCESS   read-only
    STATUS       current
    DESCRIPTION
        "Cisco UCS equipment:PsuOutputStatsHist:powerMin
        managed object property"
    ::= { cucsEquipmentPsuOutputStatsHistEntry 13 }

cucsEquipmentPsuOutputStatsHistSuspect OBJECT-TYPE
    SYNTAX       TruthValue
    MAX-ACCESS   read-only
    STATUS       current
    DESCRIPTION
        "Cisco UCS equipment:PsuOutputStatsHist:suspect
        managed object property"
    ::= { cucsEquipmentPsuOutputStatsHistEntry 14 }

cucsEquipmentPsuOutputStatsHistThresholded OBJECT-TYPE
    SYNTAX       CucsEquipmentPsuOutputStatsHistThresholded
    MAX-ACCESS   read-only
    STATUS       current
    DESCRIPTION
        "Cisco UCS equipment:PsuOutputStatsHist:thresholded
        managed object property"
    ::= { cucsEquipmentPsuOutputStatsHistEntry 15 }

cucsEquipmentPsuOutputStatsHistTimeCollected OBJECT-TYPE
    SYNTAX       DateAndTime
    MAX-ACCESS   read-only
    STATUS       current
    DESCRIPTION
        "Cisco UCS equipment:PsuOutputStatsHist:timeCollected
        managed object property"
    ::= { cucsEquipmentPsuOutputStatsHistEntry 16 }

cucsEquipmentPsuOutputStatsHistVoltage OBJECT-TYPE
    SYNTAX       INTEGER
    MAX-ACCESS   read-only
    STATUS       current
    DESCRIPTION
        "Cisco UCS equipment:PsuOutputStatsHist:voltage
        managed object property"
    ::= { cucsEquipmentPsuOutputStatsHistEntry 17 }

cucsEquipmentPsuOutputStatsHistVoltageAvg OBJECT-TYPE
    SYNTAX       INTEGER
    MAX-ACCESS   read-only
    STATUS       current
    DESCRIPTION
        "Cisco UCS equipment:PsuOutputStatsHist:voltageAvg
        managed object property"
    ::= { cucsEquipmentPsuOutputStatsHistEntry 18 }

cucsEquipmentPsuOutputStatsHistVoltageMax OBJECT-TYPE
    SYNTAX       INTEGER
    MAX-ACCESS   read-only
    STATUS       current
    DESCRIPTION
        "Cisco UCS equipment:PsuOutputStatsHist:voltageMax
        managed object property"
    ::= { cucsEquipmentPsuOutputStatsHistEntry 19 }

cucsEquipmentPsuOutputStatsHistVoltageMin OBJECT-TYPE
    SYNTAX       INTEGER
    MAX-ACCESS   read-only
    STATUS       current
    DESCRIPTION
        "Cisco UCS equipment:PsuOutputStatsHist:voltageMin
        managed object property"
    ::= { cucsEquipmentPsuOutputStatsHistEntry 20 }

cucsEquipmentPsuStatsTable OBJECT-TYPE
    SYNTAX           SEQUENCE OF CucsEquipmentPsuStatsEntry
    MAX-ACCESS       not-accessible
    STATUS           current
    DESCRIPTION
        "Cisco UCS equipment:PsuStats managed object table"
    ::= { cucsEquipmentObjects 60 }

cucsEquipmentPsuStatsEntry OBJECT-TYPE
    SYNTAX           CucsEquipmentPsuStatsEntry
    MAX-ACCESS       not-accessible
    STATUS           current
    DESCRIPTION
        "Entry for the cucsEquipmentPsuStatsTable table."
    INDEX { cucsEquipmentPsuStatsInstanceId }
    ::= { cucsEquipmentPsuStatsTable 1 }

CucsEquipmentPsuStatsEntry ::= SEQUENCE {
    cucsEquipmentPsuStatsInstanceId                                  CucsManagedObjectId,
    cucsEquipmentPsuStatsDn                                          CucsManagedObjectDn,
    cucsEquipmentPsuStatsRn                                          SnmpAdminString,
    cucsEquipmentPsuStatsAmbientTemp                                 INTEGER,
    cucsEquipmentPsuStatsAmbientTempAvg                              INTEGER,
    cucsEquipmentPsuStatsAmbientTempMax                              INTEGER,
    cucsEquipmentPsuStatsAmbientTempMin                              INTEGER,
    cucsEquipmentPsuStatsInput210v                                   INTEGER,
    cucsEquipmentPsuStatsInput210vAvg                                INTEGER,
    cucsEquipmentPsuStatsInput210vMax                                INTEGER,
    cucsEquipmentPsuStatsInput210vMin                                INTEGER,
    cucsEquipmentPsuStatsIntervals                                   Gauge32,
    cucsEquipmentPsuStatsOutput12v                                   INTEGER,
    cucsEquipmentPsuStatsOutput12vAvg                                INTEGER,
    cucsEquipmentPsuStatsOutput12vMax                                INTEGER,
    cucsEquipmentPsuStatsOutput12vMin                                INTEGER,
    cucsEquipmentPsuStatsOutput3v3                                   INTEGER,
    cucsEquipmentPsuStatsOutput3v3Avg                                INTEGER,
    cucsEquipmentPsuStatsOutput3v3Max                                INTEGER,
    cucsEquipmentPsuStatsOutput3v3Min                                INTEGER,
    cucsEquipmentPsuStatsOutputCurrent                               INTEGER,
    cucsEquipmentPsuStatsOutputCurrentAvg                            INTEGER,
    cucsEquipmentPsuStatsOutputCurrentMax                            INTEGER,
    cucsEquipmentPsuStatsOutputCurrentMin                            INTEGER,
    cucsEquipmentPsuStatsOutputPower                                 INTEGER,
    cucsEquipmentPsuStatsOutputPowerAvg                              INTEGER,
    cucsEquipmentPsuStatsOutputPowerMax                              INTEGER,
    cucsEquipmentPsuStatsOutputPowerMin                              INTEGER,
    cucsEquipmentPsuStatsSuspect                                     TruthValue,
    cucsEquipmentPsuStatsThresholded                                 CucsEquipmentPsuStatsThresholded,
    cucsEquipmentPsuStatsTimeCollected                               DateAndTime,
    cucsEquipmentPsuStatsUpdate                                      Gauge32,
    cucsEquipmentPsuStatsPsuTemp1                                    INTEGER,
    cucsEquipmentPsuStatsPsuTemp2                                    INTEGER,
    cucsEquipmentPsuStatsInputPower                                  SnmpAdminString,
    cucsEquipmentPsuStatsInputPowerAvg                               SnmpAdminString,
    cucsEquipmentPsuStatsInputPowerMax                               SnmpAdminString,
    cucsEquipmentPsuStatsInputPowerMin                               SnmpAdminString,
    cucsEquipmentPsuStatsPsuI2CErrors                                Unsigned64,
    cucsEquipmentPsuStatsPsuI2CErrorsAvg                             Unsigned64,
    cucsEquipmentPsuStatsPsuI2CErrorsMax                             Unsigned64,
    cucsEquipmentPsuStatsPsuI2CErrorsMin                             Unsigned64
}

cucsEquipmentPsuStatsInstanceId OBJECT-TYPE
    SYNTAX       CucsManagedObjectId
    MAX-ACCESS   not-accessible
    STATUS       current
    DESCRIPTION
        "Instance identifier of the managed object."
    ::= { cucsEquipmentPsuStatsEntry 1 }

cucsEquipmentPsuStatsDn OBJECT-TYPE
    SYNTAX       CucsManagedObjectDn
    MAX-ACCESS   read-only
    STATUS       current
    DESCRIPTION
        "Cisco UCS equipment:PsuStats:dn managed object property"
    ::= { cucsEquipmentPsuStatsEntry 2 }

cucsEquipmentPsuStatsRn OBJECT-TYPE
    SYNTAX       SnmpAdminString
    MAX-ACCESS   read-only
    STATUS       current
    DESCRIPTION
        "Cisco UCS equipment:PsuStats:rn managed object property"
    ::= { cucsEquipmentPsuStatsEntry 3 }

cucsEquipmentPsuStatsAmbientTemp OBJECT-TYPE
    SYNTAX       INTEGER
    MAX-ACCESS   read-only
    STATUS       current
    DESCRIPTION
        "Cisco UCS equipment:PsuStats:ambientTemp managed object property"
    ::= { cucsEquipmentPsuStatsEntry 4 }

cucsEquipmentPsuStatsAmbientTempAvg OBJECT-TYPE
    SYNTAX       INTEGER
    MAX-ACCESS   read-only
    STATUS       current
    DESCRIPTION
        "Cisco UCS equipment:PsuStats:ambientTempAvg managed
        object property"
    ::= { cucsEquipmentPsuStatsEntry 5 }

cucsEquipmentPsuStatsAmbientTempMax OBJECT-TYPE
    SYNTAX       INTEGER
    MAX-ACCESS   read-only
    STATUS       current
    DESCRIPTION
        "Cisco UCS equipment:PsuStats:ambientTempMax managed
        object property"
    ::= { cucsEquipmentPsuStatsEntry 6 }

cucsEquipmentPsuStatsAmbientTempMin OBJECT-TYPE
    SYNTAX       INTEGER
    MAX-ACCESS   read-only
    STATUS       current
    DESCRIPTION
        "Cisco UCS equipment:PsuStats:ambientTempMin managed
        object property"
    ::= { cucsEquipmentPsuStatsEntry 7 }

cucsEquipmentPsuStatsInput210v OBJECT-TYPE
    SYNTAX       INTEGER
    MAX-ACCESS   read-only
    STATUS       current
    DESCRIPTION
        "Cisco UCS equipment:PsuStats:input210v managed object property"
    ::= { cucsEquipmentPsuStatsEntry 8 }

cucsEquipmentPsuStatsInput210vAvg OBJECT-TYPE
    SYNTAX       INTEGER
    MAX-ACCESS   read-only
    STATUS       current
    DESCRIPTION
        "Cisco UCS equipment:PsuStats:input210vAvg managed
        object property"
    ::= { cucsEquipmentPsuStatsEntry 9 }

cucsEquipmentPsuStatsInput210vMax OBJECT-TYPE
    SYNTAX       INTEGER
    MAX-ACCESS   read-only
    STATUS       current
    DESCRIPTION
        "Cisco UCS equipment:PsuStats:input210vMax managed
        object property"
    ::= { cucsEquipmentPsuStatsEntry 10 }

cucsEquipmentPsuStatsInput210vMin OBJECT-TYPE
    SYNTAX       INTEGER
    MAX-ACCESS   read-only
    STATUS       current
    DESCRIPTION
        "Cisco UCS equipment:PsuStats:input210vMin managed
        object property"
    ::= { cucsEquipmentPsuStatsEntry 11 }

cucsEquipmentPsuStatsIntervals OBJECT-TYPE
    SYNTAX       Gauge32
    MAX-ACCESS   read-only
    STATUS       current
    DESCRIPTION
        "Cisco UCS equipment:PsuStats:intervals managed object property"
    ::= { cucsEquipmentPsuStatsEntry 12 }

cucsEquipmentPsuStatsOutput12v OBJECT-TYPE
    SYNTAX       INTEGER
    MAX-ACCESS   read-only
    STATUS       current
    DESCRIPTION
        "Cisco UCS equipment:PsuStats:output12v managed object property"
    ::= { cucsEquipmentPsuStatsEntry 13 }

cucsEquipmentPsuStatsOutput12vAvg OBJECT-TYPE
    SYNTAX       INTEGER
    MAX-ACCESS   read-only
    STATUS       current
    DESCRIPTION
        "Cisco UCS equipment:PsuStats:output12vAvg managed
        object property"
    ::= { cucsEquipmentPsuStatsEntry 14 }

cucsEquipmentPsuStatsOutput12vMax OBJECT-TYPE
    SYNTAX       INTEGER
    MAX-ACCESS   read-only
    STATUS       current
    DESCRIPTION
        "Cisco UCS equipment:PsuStats:output12vMax managed
        object property"
    ::= { cucsEquipmentPsuStatsEntry 15 }

cucsEquipmentPsuStatsOutput12vMin OBJECT-TYPE
    SYNTAX       INTEGER
    MAX-ACCESS   read-only
    STATUS       current
    DESCRIPTION
        "Cisco UCS equipment:PsuStats:output12vMin managed
        object property"
    ::= { cucsEquipmentPsuStatsEntry 16 }

cucsEquipmentPsuStatsOutput3v3 OBJECT-TYPE
    SYNTAX       INTEGER
    MAX-ACCESS   read-only
    STATUS       current
    DESCRIPTION
        "Cisco UCS equipment:PsuStats:output3v3 managed object property"
    ::= { cucsEquipmentPsuStatsEntry 17 }

cucsEquipmentPsuStatsOutput3v3Avg OBJECT-TYPE
    SYNTAX       INTEGER
    MAX-ACCESS   read-only
    STATUS       current
    DESCRIPTION
        "Cisco UCS equipment:PsuStats:output3v3Avg managed
        object property"
    ::= { cucsEquipmentPsuStatsEntry 18 }

cucsEquipmentPsuStatsOutput3v3Max OBJECT-TYPE
    SYNTAX       INTEGER
    MAX-ACCESS   read-only
    STATUS       current
    DESCRIPTION
        "Cisco UCS equipment:PsuStats:output3v3Max managed
        object property"
    ::= { cucsEquipmentPsuStatsEntry 19 }

cucsEquipmentPsuStatsOutput3v3Min OBJECT-TYPE
    SYNTAX       INTEGER
    MAX-ACCESS   read-only
    STATUS       current
    DESCRIPTION
        "Cisco UCS equipment:PsuStats:output3v3Min managed
        object property"
    ::= { cucsEquipmentPsuStatsEntry 20 }

cucsEquipmentPsuStatsOutputCurrent OBJECT-TYPE
    SYNTAX       INTEGER
    MAX-ACCESS   read-only
    STATUS       current
    DESCRIPTION
        "Cisco UCS equipment:PsuStats:outputCurrent managed
        object property"
    ::= { cucsEquipmentPsuStatsEntry 21 }

cucsEquipmentPsuStatsOutputCurrentAvg OBJECT-TYPE
    SYNTAX       INTEGER
    MAX-ACCESS   read-only
    STATUS       current
    DESCRIPTION
        "Cisco UCS equipment:PsuStats:outputCurrentAvg
        managed object property"
    ::= { cucsEquipmentPsuStatsEntry 22 }

cucsEquipmentPsuStatsOutputCurrentMax OBJECT-TYPE
    SYNTAX       INTEGER
    MAX-ACCESS   read-only
    STATUS       current
    DESCRIPTION
        "Cisco UCS equipment:PsuStats:outputCurrentMax
        managed object property"
    ::= { cucsEquipmentPsuStatsEntry 23 }

cucsEquipmentPsuStatsOutputCurrentMin OBJECT-TYPE
    SYNTAX       INTEGER
    MAX-ACCESS   read-only
    STATUS       current
    DESCRIPTION
        "Cisco UCS equipment:PsuStats:outputCurrentMin
        managed object property"
    ::= { cucsEquipmentPsuStatsEntry 24 }

cucsEquipmentPsuStatsOutputPower OBJECT-TYPE
    SYNTAX       INTEGER
    MAX-ACCESS   read-only
    STATUS       current
    DESCRIPTION
        "Cisco UCS equipment:PsuStats:outputPower managed object property"
    ::= { cucsEquipmentPsuStatsEntry 25 }

cucsEquipmentPsuStatsOutputPowerAvg OBJECT-TYPE
    SYNTAX       INTEGER
    MAX-ACCESS   read-only
    STATUS       current
    DESCRIPTION
        "Cisco UCS equipment:PsuStats:outputPowerAvg managed
        object property"
    ::= { cucsEquipmentPsuStatsEntry 26 }

cucsEquipmentPsuStatsOutputPowerMax OBJECT-TYPE
    SYNTAX       INTEGER
    MAX-ACCESS   read-only
    STATUS       current
    DESCRIPTION
        "Cisco UCS equipment:PsuStats:outputPowerMax managed
        object property"
    ::= { cucsEquipmentPsuStatsEntry 27 }

cucsEquipmentPsuStatsOutputPowerMin OBJECT-TYPE
    SYNTAX       INTEGER
    MAX-ACCESS   read-only
    STATUS       current
    DESCRIPTION
        "Cisco UCS equipment:PsuStats:outputPowerMin managed
        object property"
    ::= { cucsEquipmentPsuStatsEntry 28 }

cucsEquipmentPsuStatsSuspect OBJECT-TYPE
    SYNTAX       TruthValue
    MAX-ACCESS   read-only
    STATUS       current
    DESCRIPTION
        "Cisco UCS equipment:PsuStats:suspect managed object property"
    ::= { cucsEquipmentPsuStatsEntry 29 }

cucsEquipmentPsuStatsThresholded OBJECT-TYPE
    SYNTAX       CucsEquipmentPsuStatsThresholded
    MAX-ACCESS   read-only
    STATUS       current
    DESCRIPTION
        "Cisco UCS equipment:PsuStats:thresholded managed object property"
    ::= { cucsEquipmentPsuStatsEntry 30 }

cucsEquipmentPsuStatsTimeCollected OBJECT-TYPE
    SYNTAX       DateAndTime
    MAX-ACCESS   read-only
    STATUS       current
    DESCRIPTION
        "Cisco UCS equipment:PsuStats:timeCollected managed
        object property"
    ::= { cucsEquipmentPsuStatsEntry 31 }

cucsEquipmentPsuStatsUpdate OBJECT-TYPE
    SYNTAX       Gauge32
    MAX-ACCESS   read-only
    STATUS       current
    DESCRIPTION
        "Cisco UCS equipment:PsuStats:update managed object property"
    ::= { cucsEquipmentPsuStatsEntry 32 }

cucsEquipmentPsuStatsPsuTemp1 OBJECT-TYPE
    SYNTAX       INTEGER
    MAX-ACCESS   read-only
    STATUS       current
    DESCRIPTION
        "Cisco UCS equipment:PsuStats:psuTemp1 managed object property"
    ::= { cucsEquipmentPsuStatsEntry 33 }

cucsEquipmentPsuStatsPsuTemp2 OBJECT-TYPE
    SYNTAX       INTEGER
    MAX-ACCESS   read-only
    STATUS       current
    DESCRIPTION
        "Cisco UCS equipment:PsuStats:psuTemp2 managed object property"
    ::= { cucsEquipmentPsuStatsEntry 34 }

cucsEquipmentPsuStatsInputPower OBJECT-TYPE
    SYNTAX       SnmpAdminString
    MAX-ACCESS   read-only
    STATUS       current
    DESCRIPTION
        "Cisco UCS equipment:PsuStats:inputPower managed object property"
    ::= { cucsEquipmentPsuStatsEntry 35 }

cucsEquipmentPsuStatsInputPowerAvg OBJECT-TYPE
    SYNTAX       SnmpAdminString
    MAX-ACCESS   read-only
    STATUS       current
    DESCRIPTION
        "Cisco UCS equipment:PsuStats:inputPowerAvg managed
        object property"
    ::= { cucsEquipmentPsuStatsEntry 36 }

cucsEquipmentPsuStatsInputPowerMax OBJECT-TYPE
    SYNTAX       SnmpAdminString
    MAX-ACCESS   read-only
    STATUS       current
    DESCRIPTION
        "Cisco UCS equipment:PsuStats:inputPowerMax managed
        object property"
    ::= { cucsEquipmentPsuStatsEntry 37 }

cucsEquipmentPsuStatsInputPowerMin OBJECT-TYPE
    SYNTAX       SnmpAdminString
    MAX-ACCESS   read-only
    STATUS       current
    DESCRIPTION
        "Cisco UCS equipment:PsuStats:inputPowerMin managed
        object property"
    ::= { cucsEquipmentPsuStatsEntry 38 }

cucsEquipmentPsuStatsPsuI2CErrors OBJECT-TYPE
    SYNTAX       Unsigned64
    MAX-ACCESS   read-only
    STATUS       current
    DESCRIPTION
        "Cisco UCS equipment:PsuStats:PsuI2CErrors managed
        object property"
    ::= { cucsEquipmentPsuStatsEntry 39 }

cucsEquipmentPsuStatsPsuI2CErrorsAvg OBJECT-TYPE
    SYNTAX       Unsigned64
    MAX-ACCESS   read-only
    STATUS       current
    DESCRIPTION
        "Cisco UCS equipment:PsuStats:PsuI2CErrorsAvg managed
        object property"
    ::= { cucsEquipmentPsuStatsEntry 46 }

cucsEquipmentPsuStatsPsuI2CErrorsMax OBJECT-TYPE
    SYNTAX       Unsigned64
    MAX-ACCESS   read-only
    STATUS       current
    DESCRIPTION
        "Cisco UCS equipment:PsuStats:PsuI2CErrorsMax managed
        object property"
    ::= { cucsEquipmentPsuStatsEntry 47 }

cucsEquipmentPsuStatsPsuI2CErrorsMin OBJECT-TYPE
    SYNTAX       Unsigned64
    MAX-ACCESS   read-only
    STATUS       current
    DESCRIPTION
        "Cisco UCS equipment:PsuStats:PsuI2CErrorsMin managed
        object property"
    ::= { cucsEquipmentPsuStatsEntry 48 }

cucsEquipmentPsuStatsHistTable OBJECT-TYPE
    SYNTAX           SEQUENCE OF CucsEquipmentPsuStatsHistEntry
    MAX-ACCESS       not-accessible
    STATUS           current
    DESCRIPTION
        "Cisco UCS equipment:PsuStatsHist managed object table"
    ::= { cucsEquipmentObjects 61 }

cucsEquipmentPsuStatsHistEntry OBJECT-TYPE
    SYNTAX           CucsEquipmentPsuStatsHistEntry
    MAX-ACCESS       not-accessible
    STATUS           current
    DESCRIPTION
        "Entry for the cucsEquipmentPsuStatsHistTable table."
    INDEX { cucsEquipmentPsuStatsHistInstanceId }
    ::= { cucsEquipmentPsuStatsHistTable 1 }

CucsEquipmentPsuStatsHistEntry ::= SEQUENCE {
    cucsEquipmentPsuStatsHistInstanceId                              CucsManagedObjectId,
    cucsEquipmentPsuStatsHistDn                                      CucsManagedObjectDn,
    cucsEquipmentPsuStatsHistRn                                      SnmpAdminString,
    cucsEquipmentPsuStatsHistAmbientTemp                             INTEGER,
    cucsEquipmentPsuStatsHistAmbientTempAvg                          INTEGER,
    cucsEquipmentPsuStatsHistAmbientTempMax                          INTEGER,
    cucsEquipmentPsuStatsHistAmbientTempMin                          INTEGER,
    cucsEquipmentPsuStatsHistId                                      Unsigned64,
    cucsEquipmentPsuStatsHistInput210v                               INTEGER,
    cucsEquipmentPsuStatsHistInput210vAvg                            INTEGER,
    cucsEquipmentPsuStatsHistInput210vMax                            INTEGER,
    cucsEquipmentPsuStatsHistInput210vMin                            INTEGER,
    cucsEquipmentPsuStatsHistMostRecent                              TruthValue,
    cucsEquipmentPsuStatsHistOutput12v                               INTEGER,
    cucsEquipmentPsuStatsHistOutput12vAvg                            INTEGER,
    cucsEquipmentPsuStatsHistOutput12vMax                            INTEGER,
    cucsEquipmentPsuStatsHistOutput12vMin                            INTEGER,
    cucsEquipmentPsuStatsHistOutput3v3                               INTEGER,
    cucsEquipmentPsuStatsHistOutput3v3Avg                            INTEGER,
    cucsEquipmentPsuStatsHistOutput3v3Max                            INTEGER,
    cucsEquipmentPsuStatsHistOutput3v3Min                            INTEGER,
    cucsEquipmentPsuStatsHistOutputCurrent                           INTEGER,
    cucsEquipmentPsuStatsHistOutputCurrentAvg                        INTEGER,
    cucsEquipmentPsuStatsHistOutputCurrentMax                        INTEGER,
    cucsEquipmentPsuStatsHistOutputCurrentMin                        INTEGER,
    cucsEquipmentPsuStatsHistOutputPower                             INTEGER,
    cucsEquipmentPsuStatsHistOutputPowerAvg                          INTEGER,
    cucsEquipmentPsuStatsHistOutputPowerMax                          INTEGER,
    cucsEquipmentPsuStatsHistOutputPowerMin                          INTEGER,
    cucsEquipmentPsuStatsHistSuspect                                 TruthValue,
    cucsEquipmentPsuStatsHistThresholded                             CucsEquipmentPsuStatsHistThresholded,
    cucsEquipmentPsuStatsHistTimeCollected                           DateAndTime,
    cucsEquipmentPsuStatsHistInputPower                              SnmpAdminString,
    cucsEquipmentPsuStatsHistInputPowerAvg                           SnmpAdminString,
    cucsEquipmentPsuStatsHistInputPowerMax                           SnmpAdminString,
    cucsEquipmentPsuStatsHistInputPowerMin                           SnmpAdminString,
    cucsEquipmentPsuStatsHistPsuI2CErrors                            Unsigned64,
    cucsEquipmentPsuStatsHistPsuI2CErrorsAvg                         Unsigned64,
    cucsEquipmentPsuStatsHistPsuI2CErrorsMax                         Unsigned64,
    cucsEquipmentPsuStatsHistPsuI2CErrorsMin                         Unsigned64
}

cucsEquipmentPsuStatsHistInstanceId OBJECT-TYPE
    SYNTAX       CucsManagedObjectId
    MAX-ACCESS   not-accessible
    STATUS       current
    DESCRIPTION
        "Instance identifier of the managed object."
    ::= { cucsEquipmentPsuStatsHistEntry 1 }

cucsEquipmentPsuStatsHistDn OBJECT-TYPE
    SYNTAX       CucsManagedObjectDn
    MAX-ACCESS   read-only
    STATUS       current
    DESCRIPTION
        "Cisco UCS equipment:PsuStatsHist:dn managed object property"
    ::= { cucsEquipmentPsuStatsHistEntry 2 }

cucsEquipmentPsuStatsHistRn OBJECT-TYPE
    SYNTAX       SnmpAdminString
    MAX-ACCESS   read-only
    STATUS       current
    DESCRIPTION
        "Cisco UCS equipment:PsuStatsHist:rn managed object property"
    ::= { cucsEquipmentPsuStatsHistEntry 3 }

cucsEquipmentPsuStatsHistAmbientTemp OBJECT-TYPE
    SYNTAX       INTEGER
    MAX-ACCESS   read-only
    STATUS       current
    DESCRIPTION
        "Cisco UCS equipment:PsuStatsHist:ambientTemp managed
        object property"
    ::= { cucsEquipmentPsuStatsHistEntry 4 }

cucsEquipmentPsuStatsHistAmbientTempAvg OBJECT-TYPE
    SYNTAX       INTEGER
    MAX-ACCESS   read-only
    STATUS       current
    DESCRIPTION
        "Cisco UCS equipment:PsuStatsHist:ambientTempAvg
        managed object property"
    ::= { cucsEquipmentPsuStatsHistEntry 5 }

cucsEquipmentPsuStatsHistAmbientTempMax OBJECT-TYPE
    SYNTAX       INTEGER
    MAX-ACCESS   read-only
    STATUS       current
    DESCRIPTION
        "Cisco UCS equipment:PsuStatsHist:ambientTempMax
        managed object property"
    ::= { cucsEquipmentPsuStatsHistEntry 6 }

cucsEquipmentPsuStatsHistAmbientTempMin OBJECT-TYPE
    SYNTAX       INTEGER
    MAX-ACCESS   read-only
    STATUS       current
    DESCRIPTION
        "Cisco UCS equipment:PsuStatsHist:ambientTempMin
        managed object property"
    ::= { cucsEquipmentPsuStatsHistEntry 7 }

cucsEquipmentPsuStatsHistId OBJECT-TYPE
    SYNTAX       Unsigned64
    MAX-ACCESS   read-only
    STATUS       current
    DESCRIPTION
        "Cisco UCS equipment:PsuStatsHist:id managed object property"
    ::= { cucsEquipmentPsuStatsHistEntry 8 }

cucsEquipmentPsuStatsHistInput210v OBJECT-TYPE
    SYNTAX       INTEGER
    MAX-ACCESS   read-only
    STATUS       current
    DESCRIPTION
        "Cisco UCS equipment:PsuStatsHist:input210v managed
        object property"
    ::= { cucsEquipmentPsuStatsHistEntry 9 }

cucsEquipmentPsuStatsHistInput210vAvg OBJECT-TYPE
    SYNTAX       INTEGER
    MAX-ACCESS   read-only
    STATUS       current
    DESCRIPTION
        "Cisco UCS equipment:PsuStatsHist:input210vAvg
        managed object property"
    ::= { cucsEquipmentPsuStatsHistEntry 10 }

cucsEquipmentPsuStatsHistInput210vMax OBJECT-TYPE
    SYNTAX       INTEGER
    MAX-ACCESS   read-only
    STATUS       current
    DESCRIPTION
        "Cisco UCS equipment:PsuStatsHist:input210vMax
        managed object property"
    ::= { cucsEquipmentPsuStatsHistEntry 11 }

cucsEquipmentPsuStatsHistInput210vMin OBJECT-TYPE
    SYNTAX       INTEGER
    MAX-ACCESS   read-only
    STATUS       current
    DESCRIPTION
        "Cisco UCS equipment:PsuStatsHist:input210vMin
        managed object property"
    ::= { cucsEquipmentPsuStatsHistEntry 12 }

cucsEquipmentPsuStatsHistMostRecent OBJECT-TYPE
    SYNTAX       TruthValue
    MAX-ACCESS   read-only
    STATUS       current
    DESCRIPTION
        "Cisco UCS equipment:PsuStatsHist:mostRecent managed
        object property"
    ::= { cucsEquipmentPsuStatsHistEntry 13 }

cucsEquipmentPsuStatsHistOutput12v OBJECT-TYPE
    SYNTAX       INTEGER
    MAX-ACCESS   read-only
    STATUS       current
    DESCRIPTION
        "Cisco UCS equipment:PsuStatsHist:output12v managed
        object property"
    ::= { cucsEquipmentPsuStatsHistEntry 14 }

cucsEquipmentPsuStatsHistOutput12vAvg OBJECT-TYPE
    SYNTAX       INTEGER
    MAX-ACCESS   read-only
    STATUS       current
    DESCRIPTION
        "Cisco UCS equipment:PsuStatsHist:output12vAvg
        managed object property"
    ::= { cucsEquipmentPsuStatsHistEntry 15 }

cucsEquipmentPsuStatsHistOutput12vMax OBJECT-TYPE
    SYNTAX       INTEGER
    MAX-ACCESS   read-only
    STATUS       current
    DESCRIPTION
        "Cisco UCS equipment:PsuStatsHist:output12vMax
        managed object property"
    ::= { cucsEquipmentPsuStatsHistEntry 16 }

cucsEquipmentPsuStatsHistOutput12vMin OBJECT-TYPE
    SYNTAX       INTEGER
    MAX-ACCESS   read-only
    STATUS       current
    DESCRIPTION
        "Cisco UCS equipment:PsuStatsHist:output12vMin
        managed object property"
    ::= { cucsEquipmentPsuStatsHistEntry 17 }

cucsEquipmentPsuStatsHistOutput3v3 OBJECT-TYPE
    SYNTAX       INTEGER
    MAX-ACCESS   read-only
    STATUS       current
    DESCRIPTION
        "Cisco UCS equipment:PsuStatsHist:output3v3 managed
        object property"
    ::= { cucsEquipmentPsuStatsHistEntry 18 }

cucsEquipmentPsuStatsHistOutput3v3Avg OBJECT-TYPE
    SYNTAX       INTEGER
    MAX-ACCESS   read-only
    STATUS       current
    DESCRIPTION
        "Cisco UCS equipment:PsuStatsHist:output3v3Avg
        managed object property"
    ::= { cucsEquipmentPsuStatsHistEntry 19 }

cucsEquipmentPsuStatsHistOutput3v3Max OBJECT-TYPE
    SYNTAX       INTEGER
    MAX-ACCESS   read-only
    STATUS       current
    DESCRIPTION
        "Cisco UCS equipment:PsuStatsHist:output3v3Max
        managed object property"
    ::= { cucsEquipmentPsuStatsHistEntry 20 }

cucsEquipmentPsuStatsHistOutput3v3Min OBJECT-TYPE
    SYNTAX       INTEGER
    MAX-ACCESS   read-only
    STATUS       current
    DESCRIPTION
        "Cisco UCS equipment:PsuStatsHist:output3v3Min
        managed object property"
    ::= { cucsEquipmentPsuStatsHistEntry 21 }

cucsEquipmentPsuStatsHistOutputCurrent OBJECT-TYPE
    SYNTAX       INTEGER
    MAX-ACCESS   read-only
    STATUS       current
    DESCRIPTION
        "Cisco UCS equipment:PsuStatsHist:outputCurrent
        managed object property"
    ::= { cucsEquipmentPsuStatsHistEntry 22 }

cucsEquipmentPsuStatsHistOutputCurrentAvg OBJECT-TYPE
    SYNTAX       INTEGER
    MAX-ACCESS   read-only
    STATUS       current
    DESCRIPTION
        "Cisco UCS equipment:PsuStatsHist:outputCurrentAvg
        managed object property"
    ::= { cucsEquipmentPsuStatsHistEntry 23 }

cucsEquipmentPsuStatsHistOutputCurrentMax OBJECT-TYPE
    SYNTAX       INTEGER
    MAX-ACCESS   read-only
    STATUS       current
    DESCRIPTION
        "Cisco UCS equipment:PsuStatsHist:outputCurrentMax
        managed object property"
    ::= { cucsEquipmentPsuStatsHistEntry 24 }

cucsEquipmentPsuStatsHistOutputCurrentMin OBJECT-TYPE
    SYNTAX       INTEGER
    MAX-ACCESS   read-only
    STATUS       current
    DESCRIPTION
        "Cisco UCS equipment:PsuStatsHist:outputCurrentMin
        managed object property"
    ::= { cucsEquipmentPsuStatsHistEntry 25 }

cucsEquipmentPsuStatsHistOutputPower OBJECT-TYPE
    SYNTAX       INTEGER
    MAX-ACCESS   read-only
    STATUS       current
    DESCRIPTION
        "Cisco UCS equipment:PsuStatsHist:outputPower managed
        object property"
    ::= { cucsEquipmentPsuStatsHistEntry 26 }

cucsEquipmentPsuStatsHistOutputPowerAvg OBJECT-TYPE
    SYNTAX       INTEGER
    MAX-ACCESS   read-only
    STATUS       current
    DESCRIPTION
        "Cisco UCS equipment:PsuStatsHist:outputPowerAvg
        managed object property"
    ::= { cucsEquipmentPsuStatsHistEntry 27 }

cucsEquipmentPsuStatsHistOutputPowerMax OBJECT-TYPE
    SYNTAX       INTEGER
    MAX-ACCESS   read-only
    STATUS       current
    DESCRIPTION
        "Cisco UCS equipment:PsuStatsHist:outputPowerMax
        managed object property"
    ::= { cucsEquipmentPsuStatsHistEntry 28 }

cucsEquipmentPsuStatsHistOutputPowerMin OBJECT-TYPE
    SYNTAX       INTEGER
    MAX-ACCESS   read-only
    STATUS       current
    DESCRIPTION
        "Cisco UCS equipment:PsuStatsHist:outputPowerMin
        managed object property"
    ::= { cucsEquipmentPsuStatsHistEntry 29 }

cucsEquipmentPsuStatsHistSuspect OBJECT-TYPE
    SYNTAX       TruthValue
    MAX-ACCESS   read-only
    STATUS       current
    DESCRIPTION
        "Cisco UCS equipment:PsuStatsHist:suspect managed object property"
    ::= { cucsEquipmentPsuStatsHistEntry 30 }

cucsEquipmentPsuStatsHistThresholded OBJECT-TYPE
    SYNTAX       CucsEquipmentPsuStatsHistThresholded
    MAX-ACCESS   read-only
    STATUS       current
    DESCRIPTION
        "Cisco UCS equipment:PsuStatsHist:thresholded managed
        object property"
    ::= { cucsEquipmentPsuStatsHistEntry 31 }

cucsEquipmentPsuStatsHistTimeCollected OBJECT-TYPE
    SYNTAX       DateAndTime
    MAX-ACCESS   read-only
    STATUS       current
    DESCRIPTION
        "Cisco UCS equipment:PsuStatsHist:timeCollected
        managed object property"
    ::= { cucsEquipmentPsuStatsHistEntry 32 }

cucsEquipmentPsuStatsHistInputPower OBJECT-TYPE
    SYNTAX       SnmpAdminString
    MAX-ACCESS   read-only
    STATUS       current
    DESCRIPTION
        "Cisco UCS equipment:PsuStatsHist:inputPower managed
        object property"
    ::= { cucsEquipmentPsuStatsHistEntry 33 }

cucsEquipmentPsuStatsHistInputPowerAvg OBJECT-TYPE
    SYNTAX       SnmpAdminString
    MAX-ACCESS   read-only
    STATUS       current
    DESCRIPTION
        "Cisco UCS equipment:PsuStatsHist:inputPowerAvg
        managed object property"
    ::= { cucsEquipmentPsuStatsHistEntry 34 }

cucsEquipmentPsuStatsHistInputPowerMax OBJECT-TYPE
    SYNTAX       SnmpAdminString
    MAX-ACCESS   read-only
    STATUS       current
    DESCRIPTION
        "Cisco UCS equipment:PsuStatsHist:inputPowerMax
        managed object property"
    ::= { cucsEquipmentPsuStatsHistEntry 35 }

cucsEquipmentPsuStatsHistInputPowerMin OBJECT-TYPE
    SYNTAX       SnmpAdminString
    MAX-ACCESS   read-only
    STATUS       current
    DESCRIPTION
        "Cisco UCS equipment:PsuStatsHist:inputPowerMin
        managed object property"
    ::= { cucsEquipmentPsuStatsHistEntry 36 }

cucsEquipmentPsuStatsHistPsuI2CErrors OBJECT-TYPE
    SYNTAX       Unsigned64
    MAX-ACCESS   read-only
    STATUS       current
    DESCRIPTION
        "Cisco UCS equipment:PsuStatsHist:PsuI2CErrors
        managed object property"
    ::= { cucsEquipmentPsuStatsHistEntry 37 }

cucsEquipmentPsuStatsHistPsuI2CErrorsAvg OBJECT-TYPE
    SYNTAX       Unsigned64
    MAX-ACCESS   read-only
    STATUS       current
    DESCRIPTION
        "Cisco UCS equipment:PsuStatsHist:PsuI2CErrorsAvg
        managed object property"
    ::= { cucsEquipmentPsuStatsHistEntry 42 }

cucsEquipmentPsuStatsHistPsuI2CErrorsMax OBJECT-TYPE
    SYNTAX       Unsigned64
    MAX-ACCESS   read-only
    STATUS       current
    DESCRIPTION
        "Cisco UCS equipment:PsuStatsHist:PsuI2CErrorsMax
        managed object property"
    ::= { cucsEquipmentPsuStatsHistEntry 43 }

cucsEquipmentPsuStatsHistPsuI2CErrorsMin OBJECT-TYPE
    SYNTAX       Unsigned64
    MAX-ACCESS   read-only
    STATUS       current
    DESCRIPTION
        "Cisco UCS equipment:PsuStatsHist:PsuI2CErrorsMin
        managed object property"
    ::= { cucsEquipmentPsuStatsHistEntry 44 }

cucsEquipmentQualTable OBJECT-TYPE
    SYNTAX           SEQUENCE OF CucsEquipmentQualEntry
    MAX-ACCESS       not-accessible
    STATUS           current
    DESCRIPTION
        "Cisco UCS equipment:Qual managed object table"
    ::= { cucsEquipmentObjects 195 }

cucsEquipmentQualEntry OBJECT-TYPE
    SYNTAX           CucsEquipmentQualEntry
    MAX-ACCESS       not-accessible
    STATUS           current
    DESCRIPTION
        "Entry for the cucsEquipmentQualTable table."
    INDEX { cucsEquipmentQualInstanceId }
    ::= { cucsEquipmentQualTable 1 }

CucsEquipmentQualEntry ::= SEQUENCE {
    cucsEquipmentQualInstanceId                                      CucsManagedObjectId,
    cucsEquipmentQualDn                                              CucsManagedObjectDn,
    cucsEquipmentQualRn                                              SnmpAdminString,
    cucsEquipmentQualDescr                                           SnmpAdminString,
    cucsEquipmentQualIntId                                           SnmpAdminString,
    cucsEquipmentQualName                                            SnmpAdminString,
    cucsEquipmentQualPolicyLevel                                     Gauge32,
    cucsEquipmentQualPolicyOwner                                     CucsPolicyPolicyOwner
}

cucsEquipmentQualInstanceId OBJECT-TYPE
    SYNTAX       CucsManagedObjectId
    MAX-ACCESS   not-accessible
    STATUS       current
    DESCRIPTION
        "Instance identifier of the managed object."
    ::= { cucsEquipmentQualEntry 1 }

cucsEquipmentQualDn OBJECT-TYPE
    SYNTAX       CucsManagedObjectDn
    MAX-ACCESS   read-only
    STATUS       current
    DESCRIPTION
        "Cisco UCS equipment:Qual:dn managed object property"
    ::= { cucsEquipmentQualEntry 2 }

cucsEquipmentQualRn OBJECT-TYPE
    SYNTAX       SnmpAdminString
    MAX-ACCESS   read-only
    STATUS       current
    DESCRIPTION
        "Cisco UCS equipment:Qual:rn managed object property"
    ::= { cucsEquipmentQualEntry 3 }

cucsEquipmentQualDescr OBJECT-TYPE
    SYNTAX       SnmpAdminString
    MAX-ACCESS   read-only
    STATUS       current
    DESCRIPTION
        "Cisco UCS equipment:Qual:descr managed object property"
    ::= { cucsEquipmentQualEntry 4 }

cucsEquipmentQualIntId OBJECT-TYPE
    SYNTAX       SnmpAdminString
    MAX-ACCESS   read-only
    STATUS       current
    DESCRIPTION
        "Cisco UCS equipment:Qual:intId managed object property"
    ::= { cucsEquipmentQualEntry 5 }

cucsEquipmentQualName OBJECT-TYPE
    SYNTAX       SnmpAdminString
    MAX-ACCESS   read-only
    STATUS       current
    DESCRIPTION
        "Cisco UCS equipment:Qual:name managed object property"
    ::= { cucsEquipmentQualEntry 6 }

cucsEquipmentQualPolicyLevel OBJECT-TYPE
    SYNTAX       Gauge32
    MAX-ACCESS   read-only
    STATUS       current
    DESCRIPTION
        "Cisco UCS equipment:Qual:policyLevel managed object property"
    ::= { cucsEquipmentQualEntry 7 }

cucsEquipmentQualPolicyOwner OBJECT-TYPE
    SYNTAX       CucsPolicyPolicyOwner
    MAX-ACCESS   read-only
    STATUS       current
    DESCRIPTION
        "Cisco UCS equipment:Qual:policyOwner managed object property"
    ::= { cucsEquipmentQualEntry 8 }

cucsEquipmentRackFanModuleDefTable OBJECT-TYPE
    SYNTAX           SEQUENCE OF CucsEquipmentRackFanModuleDefEntry
    MAX-ACCESS       not-accessible
    STATUS           current
    DESCRIPTION
        "Cisco UCS equipment:RackFanModuleDef managed object table"
    ::= { cucsEquipmentObjects 115 }

cucsEquipmentRackFanModuleDefEntry OBJECT-TYPE
    SYNTAX           CucsEquipmentRackFanModuleDefEntry
    MAX-ACCESS       not-accessible
    STATUS           current
    DESCRIPTION
        "Entry for the cucsEquipmentRackFanModuleDefTable table."
    INDEX { cucsEquipmentRackFanModuleDefInstanceId }
    ::= { cucsEquipmentRackFanModuleDefTable 1 }

CucsEquipmentRackFanModuleDefEntry ::= SEQUENCE {
    cucsEquipmentRackFanModuleDefInstanceId                          CucsManagedObjectId,
    cucsEquipmentRackFanModuleDefDn                                  CucsManagedObjectDn,
    cucsEquipmentRackFanModuleDefRn                                  SnmpAdminString,
    cucsEquipmentRackFanModuleDefDescr                               SnmpAdminString,
    cucsEquipmentRackFanModuleDefFanCapacity                         Gauge32,
    cucsEquipmentRackFanModuleDefIntId                               SnmpAdminString,
    cucsEquipmentRackFanModuleDefName                                SnmpAdminString,
    cucsEquipmentRackFanModuleDefPolicyLevel                         Gauge32,
    cucsEquipmentRackFanModuleDefPolicyOwner                         CucsPolicyPolicyOwner
}

cucsEquipmentRackFanModuleDefInstanceId OBJECT-TYPE
    SYNTAX       CucsManagedObjectId
    MAX-ACCESS   not-accessible
    STATUS       current
    DESCRIPTION
        "Instance identifier of the managed object."
    ::= { cucsEquipmentRackFanModuleDefEntry 1 }

cucsEquipmentRackFanModuleDefDn OBJECT-TYPE
    SYNTAX       CucsManagedObjectDn
    MAX-ACCESS   read-only
    STATUS       current
    DESCRIPTION
        "Cisco UCS equipment:RackFanModuleDef:dn managed object property"
    ::= { cucsEquipmentRackFanModuleDefEntry 2 }

cucsEquipmentRackFanModuleDefRn OBJECT-TYPE
    SYNTAX       SnmpAdminString
    MAX-ACCESS   read-only
    STATUS       current
    DESCRIPTION
        "Cisco UCS equipment:RackFanModuleDef:rn managed object property"
    ::= { cucsEquipmentRackFanModuleDefEntry 3 }

cucsEquipmentRackFanModuleDefDescr OBJECT-TYPE
    SYNTAX       SnmpAdminString
    MAX-ACCESS   read-only
    STATUS       current
    DESCRIPTION
        "Cisco UCS equipment:RackFanModuleDef:descr managed
        object property"
    ::= { cucsEquipmentRackFanModuleDefEntry 4 }

cucsEquipmentRackFanModuleDefFanCapacity OBJECT-TYPE
    SYNTAX       Gauge32
    MAX-ACCESS   read-only
    STATUS       current
    DESCRIPTION
        "Cisco UCS equipment:RackFanModuleDef:fanCapacity
        managed object property"
    ::= { cucsEquipmentRackFanModuleDefEntry 5 }

cucsEquipmentRackFanModuleDefIntId OBJECT-TYPE
    SYNTAX       SnmpAdminString
    MAX-ACCESS   read-only
    STATUS       current
    DESCRIPTION
        "Cisco UCS equipment:RackFanModuleDef:intId managed
        object property"
    ::= { cucsEquipmentRackFanModuleDefEntry 6 }

cucsEquipmentRackFanModuleDefName OBJECT-TYPE
    SYNTAX       SnmpAdminString
    MAX-ACCESS   read-only
    STATUS       current
    DESCRIPTION
        "Cisco UCS equipment:RackFanModuleDef:name managed
        object property"
    ::= { cucsEquipmentRackFanModuleDefEntry 7 }

cucsEquipmentRackFanModuleDefPolicyLevel OBJECT-TYPE
    SYNTAX       Gauge32
    MAX-ACCESS   read-only
    STATUS       current
    DESCRIPTION
        "Cisco UCS equipment:RackFanModuleDef:policyLevel
        managed object property"
    ::= { cucsEquipmentRackFanModuleDefEntry 8 }

cucsEquipmentRackFanModuleDefPolicyOwner OBJECT-TYPE
    SYNTAX       CucsPolicyPolicyOwner
    MAX-ACCESS   read-only
    STATUS       current
    DESCRIPTION
        "Cisco UCS equipment:RackFanModuleDef:policyOwner
        managed object property"
    ::= { cucsEquipmentRackFanModuleDefEntry 9 }

cucsEquipmentRackUnitCapProviderTable OBJECT-TYPE
    SYNTAX           SEQUENCE OF CucsEquipmentRackUnitCapProviderEntry
    MAX-ACCESS       not-accessible
    STATUS           current
    DESCRIPTION
        "Cisco UCS equipment:RackUnitCapProvider managed object table"
    ::= { cucsEquipmentObjects 62 }

cucsEquipmentRackUnitCapProviderEntry OBJECT-TYPE
    SYNTAX           CucsEquipmentRackUnitCapProviderEntry
    MAX-ACCESS       not-accessible
    STATUS           current
    DESCRIPTION
        "Entry for the cucsEquipmentRackUnitCapProviderTable table."
    INDEX { cucsEquipmentRackUnitCapProviderInstanceId }
    ::= { cucsEquipmentRackUnitCapProviderTable 1 }

CucsEquipmentRackUnitCapProviderEntry ::= SEQUENCE {
    cucsEquipmentRackUnitCapProviderInstanceId                       CucsManagedObjectId,
    cucsEquipmentRackUnitCapProviderDn                               CucsManagedObjectDn,
    cucsEquipmentRackUnitCapProviderRn                               SnmpAdminString,
    cucsEquipmentRackUnitCapProviderDeprecated                       TruthValue,
    cucsEquipmentRackUnitCapProviderGencount                         Gauge32,
    cucsEquipmentRackUnitCapProviderMgmtPlaneVer                     SnmpAdminString,
    cucsEquipmentRackUnitCapProviderModel                            SnmpAdminString,
    cucsEquipmentRackUnitCapProviderRevision                         SnmpAdminString,
    cucsEquipmentRackUnitCapProviderVendor                           SnmpAdminString,
    cucsEquipmentRackUnitCapProviderPromCardType                     Gauge32,
    cucsEquipmentRackUnitCapProviderDeleted                          TruthValue,
    cucsEquipmentRackUnitCapProviderMaxLocalDisks                    Gauge32,
    cucsEquipmentRackUnitCapProviderElementLoadFailures              Gauge32,
    cucsEquipmentRackUnitCapProviderElementsLoaded                   Gauge32,
    cucsEquipmentRackUnitCapProviderLoadErrors                       Gauge32,
    cucsEquipmentRackUnitCapProviderLoadWarnings                     Gauge32,
    cucsEquipmentRackUnitCapProviderGeneration                       Gauge32
}

cucsEquipmentRackUnitCapProviderInstanceId OBJECT-TYPE
    SYNTAX       CucsManagedObjectId
    MAX-ACCESS   not-accessible
    STATUS       current
    DESCRIPTION
        "Instance identifier of the managed object."
    ::= { cucsEquipmentRackUnitCapProviderEntry 1 }

cucsEquipmentRackUnitCapProviderDn OBJECT-TYPE
    SYNTAX       CucsManagedObjectDn
    MAX-ACCESS   read-only
    STATUS       current
    DESCRIPTION
        "Cisco UCS equipment:RackUnitCapProvider:dn managed
        object property"
    ::= { cucsEquipmentRackUnitCapProviderEntry 2 }

cucsEquipmentRackUnitCapProviderRn OBJECT-TYPE
    SYNTAX       SnmpAdminString
    MAX-ACCESS   read-only
    STATUS       current
    DESCRIPTION
        "Cisco UCS equipment:RackUnitCapProvider:rn managed
        object property"
    ::= { cucsEquipmentRackUnitCapProviderEntry 3 }

cucsEquipmentRackUnitCapProviderDeprecated OBJECT-TYPE
    SYNTAX       TruthValue
    MAX-ACCESS   read-only
    STATUS       current
    DESCRIPTION
        "Cisco UCS equipment:RackUnitCapProvider:deprecated
        managed object property"
    ::= { cucsEquipmentRackUnitCapProviderEntry 4 }

cucsEquipmentRackUnitCapProviderGencount OBJECT-TYPE
    SYNTAX       Gauge32
    MAX-ACCESS   read-only
    STATUS       current
    DESCRIPTION
        "Cisco UCS equipment:RackUnitCapProvider:gencount
        managed object property"
    ::= { cucsEquipmentRackUnitCapProviderEntry 5 }

cucsEquipmentRackUnitCapProviderMgmtPlaneVer OBJECT-TYPE
    SYNTAX       SnmpAdminString
    MAX-ACCESS   read-only
    STATUS       current
    DESCRIPTION
        "Cisco UCS equipment:RackUnitCapProvider:mgmtPlaneVer
        managed object property"
    ::= { cucsEquipmentRackUnitCapProviderEntry 6 }

cucsEquipmentRackUnitCapProviderModel OBJECT-TYPE
    SYNTAX       SnmpAdminString
    MAX-ACCESS   read-only
    STATUS       current
    DESCRIPTION
        "Cisco UCS equipment:RackUnitCapProvider:model
        managed object property"
    ::= { cucsEquipmentRackUnitCapProviderEntry 7 }

cucsEquipmentRackUnitCapProviderRevision OBJECT-TYPE
    SYNTAX       SnmpAdminString
    MAX-ACCESS   read-only
    STATUS       current
    DESCRIPTION
        "Cisco UCS equipment:RackUnitCapProvider:revision
        managed object property"
    ::= { cucsEquipmentRackUnitCapProviderEntry 8 }

cucsEquipmentRackUnitCapProviderVendor OBJECT-TYPE
    SYNTAX       SnmpAdminString
    MAX-ACCESS   read-only
    STATUS       current
    DESCRIPTION
        "Cisco UCS equipment:RackUnitCapProvider:vendor
        managed object property"
    ::= { cucsEquipmentRackUnitCapProviderEntry 9 }

cucsEquipmentRackUnitCapProviderPromCardType OBJECT-TYPE
    SYNTAX       Gauge32
    MAX-ACCESS   read-only
    STATUS       current
    DESCRIPTION
        "Cisco UCS equipment:RackUnitCapProvider:promCardType
        managed object property"
    ::= { cucsEquipmentRackUnitCapProviderEntry 10 }

cucsEquipmentRackUnitCapProviderDeleted OBJECT-TYPE
    SYNTAX       TruthValue
    MAX-ACCESS   read-only
    STATUS       current
    DESCRIPTION
        "Cisco UCS equipment:RackUnitCapProvider:deleted
        managed object property"
    ::= { cucsEquipmentRackUnitCapProviderEntry 11 }

cucsEquipmentRackUnitCapProviderMaxLocalDisks OBJECT-TYPE
    SYNTAX       Gauge32
    MAX-ACCESS   read-only
    STATUS       current
    DESCRIPTION
        "Cisco UCS equipment:RackUnitCapProvider:maxLocalDisks
        managed object property"
    ::= { cucsEquipmentRackUnitCapProviderEntry 12 }

cucsEquipmentRackUnitCapProviderElementLoadFailures OBJECT-TYPE
    SYNTAX       Gauge32
    MAX-ACCESS   read-only
    STATUS       current
    DESCRIPTION
        "Cisco UCS equipment:RackUnitCapProvider:elementLoadFailures
        managed object property"
    ::= { cucsEquipmentRackUnitCapProviderEntry 13 }

cucsEquipmentRackUnitCapProviderElementsLoaded OBJECT-TYPE
    SYNTAX       Gauge32
    MAX-ACCESS   read-only
    STATUS       current
    DESCRIPTION
        "Cisco UCS equipment:RackUnitCapProvider:elementsLoaded
        managed object property"
    ::= { cucsEquipmentRackUnitCapProviderEntry 14 }

cucsEquipmentRackUnitCapProviderLoadErrors OBJECT-TYPE
    SYNTAX       Gauge32
    MAX-ACCESS   read-only
    STATUS       current
    DESCRIPTION
        "Cisco UCS equipment:RackUnitCapProvider:loadErrors
        managed object property"
    ::= { cucsEquipmentRackUnitCapProviderEntry 15 }

cucsEquipmentRackUnitCapProviderLoadWarnings OBJECT-TYPE
    SYNTAX       Gauge32
    MAX-ACCESS   read-only
    STATUS       current
    DESCRIPTION
        "Cisco UCS equipment:RackUnitCapProvider:loadWarnings
        managed object property"
    ::= { cucsEquipmentRackUnitCapProviderEntry 16 }

cucsEquipmentRackUnitCapProviderGeneration OBJECT-TYPE
    SYNTAX       Gauge32
    MAX-ACCESS   read-only
    STATUS       current
    DESCRIPTION
        "Cisco UCS equipment:RackUnitCapProvider:generation
        managed object property"
    ::= { cucsEquipmentRackUnitCapProviderEntry 17 }

cucsEquipmentRackUnitFanStatsTable OBJECT-TYPE
    SYNTAX           SEQUENCE OF CucsEquipmentRackUnitFanStatsEntry
    MAX-ACCESS       not-accessible
    STATUS           current
    DESCRIPTION
        "Cisco UCS equipment:RackUnitFanStats managed object table"
    ::= { cucsEquipmentObjects 71 }

cucsEquipmentRackUnitFanStatsEntry OBJECT-TYPE
    SYNTAX           CucsEquipmentRackUnitFanStatsEntry
    MAX-ACCESS       not-accessible
    STATUS           current
    DESCRIPTION
        "Entry for the cucsEquipmentRackUnitFanStatsTable table."
    INDEX { cucsEquipmentRackUnitFanStatsInstanceId }
    ::= { cucsEquipmentRackUnitFanStatsTable 1 }

CucsEquipmentRackUnitFanStatsEntry ::= SEQUENCE {
    cucsEquipmentRackUnitFanStatsInstanceId                          CucsManagedObjectId,
    cucsEquipmentRackUnitFanStatsDn                                  CucsManagedObjectDn,
    cucsEquipmentRackUnitFanStatsRn                                  SnmpAdminString,
    cucsEquipmentRackUnitFanStatsIntervals                           Gauge32,
    cucsEquipmentRackUnitFanStatsSpeed                               Gauge32,
    cucsEquipmentRackUnitFanStatsSpeedAvg                            Gauge32,
    cucsEquipmentRackUnitFanStatsSpeedMax                            Gauge32,
    cucsEquipmentRackUnitFanStatsSpeedMin                            Gauge32,
    cucsEquipmentRackUnitFanStatsSuspect                             TruthValue,
    cucsEquipmentRackUnitFanStatsThresholded                         CucsEquipmentRackUnitFanStatsThresholded,
    cucsEquipmentRackUnitFanStatsTimeCollected                       DateAndTime,
    cucsEquipmentRackUnitFanStatsUpdate                              Gauge32
}

cucsEquipmentRackUnitFanStatsInstanceId OBJECT-TYPE
    SYNTAX       CucsManagedObjectId
    MAX-ACCESS   not-accessible
    STATUS       current
    DESCRIPTION
        "Instance identifier of the managed object."
    ::= { cucsEquipmentRackUnitFanStatsEntry 1 }

cucsEquipmentRackUnitFanStatsDn OBJECT-TYPE
    SYNTAX       CucsManagedObjectDn
    MAX-ACCESS   read-only
    STATUS       current
    DESCRIPTION
        "Cisco UCS equipment:RackUnitFanStats:dn managed object property"
    ::= { cucsEquipmentRackUnitFanStatsEntry 2 }

cucsEquipmentRackUnitFanStatsRn OBJECT-TYPE
    SYNTAX       SnmpAdminString
    MAX-ACCESS   read-only
    STATUS       current
    DESCRIPTION
        "Cisco UCS equipment:RackUnitFanStats:rn managed object property"
    ::= { cucsEquipmentRackUnitFanStatsEntry 3 }

cucsEquipmentRackUnitFanStatsIntervals OBJECT-TYPE
    SYNTAX       Gauge32
    MAX-ACCESS   read-only
    STATUS       current
    DESCRIPTION
        "Cisco UCS equipment:RackUnitFanStats:intervals
        managed object property"
    ::= { cucsEquipmentRackUnitFanStatsEntry 4 }

cucsEquipmentRackUnitFanStatsSpeed OBJECT-TYPE
    SYNTAX       Gauge32
    MAX-ACCESS   read-only
    STATUS       current
    DESCRIPTION
        "Cisco UCS equipment:RackUnitFanStats:speed managed
        object property"
    ::= { cucsEquipmentRackUnitFanStatsEntry 5 }

cucsEquipmentRackUnitFanStatsSpeedAvg OBJECT-TYPE
    SYNTAX       Gauge32
    MAX-ACCESS   read-only
    STATUS       current
    DESCRIPTION
        "Cisco UCS equipment:RackUnitFanStats:speedAvg
        managed object property"
    ::= { cucsEquipmentRackUnitFanStatsEntry 6 }

cucsEquipmentRackUnitFanStatsSpeedMax OBJECT-TYPE
    SYNTAX       Gauge32
    MAX-ACCESS   read-only
    STATUS       current
    DESCRIPTION
        "Cisco UCS equipment:RackUnitFanStats:speedMax
        managed object property"
    ::= { cucsEquipmentRackUnitFanStatsEntry 7 }

cucsEquipmentRackUnitFanStatsSpeedMin OBJECT-TYPE
    SYNTAX       Gauge32
    MAX-ACCESS   read-only
    STATUS       current
    DESCRIPTION
        "Cisco UCS equipment:RackUnitFanStats:speedMin
        managed object property"
    ::= { cucsEquipmentRackUnitFanStatsEntry 8 }

cucsEquipmentRackUnitFanStatsSuspect OBJECT-TYPE
    SYNTAX       TruthValue
    MAX-ACCESS   read-only
    STATUS       current
    DESCRIPTION
        "Cisco UCS equipment:RackUnitFanStats:suspect managed
        object property"
    ::= { cucsEquipmentRackUnitFanStatsEntry 9 }

cucsEquipmentRackUnitFanStatsThresholded OBJECT-TYPE
    SYNTAX       CucsEquipmentRackUnitFanStatsThresholded
    MAX-ACCESS   read-only
    STATUS       current
    DESCRIPTION
        "Cisco UCS equipment:RackUnitFanStats:thresholded
        managed object property"
    ::= { cucsEquipmentRackUnitFanStatsEntry 10 }

cucsEquipmentRackUnitFanStatsTimeCollected OBJECT-TYPE
    SYNTAX       DateAndTime
    MAX-ACCESS   read-only
    STATUS       current
    DESCRIPTION
        "Cisco UCS equipment:RackUnitFanStats:timeCollected
        managed object property"
    ::= { cucsEquipmentRackUnitFanStatsEntry 11 }

cucsEquipmentRackUnitFanStatsUpdate OBJECT-TYPE
    SYNTAX       Gauge32
    MAX-ACCESS   read-only
    STATUS       current
    DESCRIPTION
        "Cisco UCS equipment:RackUnitFanStats:update managed
        object property"
    ::= { cucsEquipmentRackUnitFanStatsEntry 12 }

cucsEquipmentRackUnitFanStatsHistTable OBJECT-TYPE
    SYNTAX           SEQUENCE OF CucsEquipmentRackUnitFanStatsHistEntry
    MAX-ACCESS       not-accessible
    STATUS           current
    DESCRIPTION
        "Cisco UCS equipment:RackUnitFanStatsHist managed object table"
    ::= { cucsEquipmentObjects 72 }

cucsEquipmentRackUnitFanStatsHistEntry OBJECT-TYPE
    SYNTAX           CucsEquipmentRackUnitFanStatsHistEntry
    MAX-ACCESS       not-accessible
    STATUS           current
    DESCRIPTION
        "Entry for the cucsEquipmentRackUnitFanStatsHistTable table."
    INDEX { cucsEquipmentRackUnitFanStatsHistInstanceId }
    ::= { cucsEquipmentRackUnitFanStatsHistTable 1 }

CucsEquipmentRackUnitFanStatsHistEntry ::= SEQUENCE {
    cucsEquipmentRackUnitFanStatsHistInstanceId                      CucsManagedObjectId,
    cucsEquipmentRackUnitFanStatsHistDn                              CucsManagedObjectDn,
    cucsEquipmentRackUnitFanStatsHistRn                              SnmpAdminString,
    cucsEquipmentRackUnitFanStatsHistId                              Unsigned64,
    cucsEquipmentRackUnitFanStatsHistMostRecent                      TruthValue,
    cucsEquipmentRackUnitFanStatsHistSpeed                           Gauge32,
    cucsEquipmentRackUnitFanStatsHistSpeedAvg                        Gauge32,
    cucsEquipmentRackUnitFanStatsHistSpeedMax                        Gauge32,
    cucsEquipmentRackUnitFanStatsHistSpeedMin                        Gauge32,
    cucsEquipmentRackUnitFanStatsHistSuspect                         TruthValue,
    cucsEquipmentRackUnitFanStatsHistThresholded                     CucsEquipmentRackUnitFanStatsHistThresholded,
    cucsEquipmentRackUnitFanStatsHistTimeCollected                   DateAndTime
}

cucsEquipmentRackUnitFanStatsHistInstanceId OBJECT-TYPE
    SYNTAX       CucsManagedObjectId
    MAX-ACCESS   not-accessible
    STATUS       current
    DESCRIPTION
        "Instance identifier of the managed object."
    ::= { cucsEquipmentRackUnitFanStatsHistEntry 1 }

cucsEquipmentRackUnitFanStatsHistDn OBJECT-TYPE
    SYNTAX       CucsManagedObjectDn
    MAX-ACCESS   read-only
    STATUS       current
    DESCRIPTION
        "Cisco UCS equipment:RackUnitFanStatsHist:dn managed
        object property"
    ::= { cucsEquipmentRackUnitFanStatsHistEntry 2 }

cucsEquipmentRackUnitFanStatsHistRn OBJECT-TYPE
    SYNTAX       SnmpAdminString
    MAX-ACCESS   read-only
    STATUS       current
    DESCRIPTION
        "Cisco UCS equipment:RackUnitFanStatsHist:rn managed
        object property"
    ::= { cucsEquipmentRackUnitFanStatsHistEntry 3 }

cucsEquipmentRackUnitFanStatsHistId OBJECT-TYPE
    SYNTAX       Unsigned64
    MAX-ACCESS   read-only
    STATUS       current
    DESCRIPTION
        "Cisco UCS equipment:RackUnitFanStatsHist:id managed
        object property"
    ::= { cucsEquipmentRackUnitFanStatsHistEntry 4 }

cucsEquipmentRackUnitFanStatsHistMostRecent OBJECT-TYPE
    SYNTAX       TruthValue
    MAX-ACCESS   read-only
    STATUS       current
    DESCRIPTION
        "Cisco UCS equipment:RackUnitFanStatsHist:mostRecent
        managed object property"
    ::= { cucsEquipmentRackUnitFanStatsHistEntry 5 }

cucsEquipmentRackUnitFanStatsHistSpeed OBJECT-TYPE
    SYNTAX       Gauge32
    MAX-ACCESS   read-only
    STATUS       current
    DESCRIPTION
        "Cisco UCS equipment:RackUnitFanStatsHist:speed
        managed object property"
    ::= { cucsEquipmentRackUnitFanStatsHistEntry 6 }

cucsEquipmentRackUnitFanStatsHistSpeedAvg OBJECT-TYPE
    SYNTAX       Gauge32
    MAX-ACCESS   read-only
    STATUS       current
    DESCRIPTION
        "Cisco UCS equipment:RackUnitFanStatsHist:speedAvg
        managed object property"
    ::= { cucsEquipmentRackUnitFanStatsHistEntry 7 }

cucsEquipmentRackUnitFanStatsHistSpeedMax OBJECT-TYPE
    SYNTAX       Gauge32
    MAX-ACCESS   read-only
    STATUS       current
    DESCRIPTION
        "Cisco UCS equipment:RackUnitFanStatsHist:speedMax
        managed object property"
    ::= { cucsEquipmentRackUnitFanStatsHistEntry 8 }

cucsEquipmentRackUnitFanStatsHistSpeedMin OBJECT-TYPE
    SYNTAX       Gauge32
    MAX-ACCESS   read-only
    STATUS       current
    DESCRIPTION
        "Cisco UCS equipment:RackUnitFanStatsHist:speedMin
        managed object property"
    ::= { cucsEquipmentRackUnitFanStatsHistEntry 9 }

cucsEquipmentRackUnitFanStatsHistSuspect OBJECT-TYPE
    SYNTAX       TruthValue
    MAX-ACCESS   read-only
    STATUS       current
    DESCRIPTION
        "Cisco UCS equipment:RackUnitFanStatsHist:suspect
        managed object property"
    ::= { cucsEquipmentRackUnitFanStatsHistEntry 10 }

cucsEquipmentRackUnitFanStatsHistThresholded OBJECT-TYPE
    SYNTAX       CucsEquipmentRackUnitFanStatsHistThresholded
    MAX-ACCESS   read-only
    STATUS       current
    DESCRIPTION
        "Cisco UCS equipment:RackUnitFanStatsHist:thresholded
        managed object property"
    ::= { cucsEquipmentRackUnitFanStatsHistEntry 11 }

cucsEquipmentRackUnitFanStatsHistTimeCollected OBJECT-TYPE
    SYNTAX       DateAndTime
    MAX-ACCESS   read-only
    STATUS       current
    DESCRIPTION
        "Cisco UCS equipment:RackUnitFanStatsHist:timeCollected
        managed object property"
    ::= { cucsEquipmentRackUnitFanStatsHistEntry 12 }

cucsEquipmentRackUnitPsuStatsTable OBJECT-TYPE
    SYNTAX           SEQUENCE OF CucsEquipmentRackUnitPsuStatsEntry
    MAX-ACCESS       not-accessible
    STATUS           current
    DESCRIPTION
        "Cisco UCS equipment:RackUnitPsuStats managed object table"
    ::= { cucsEquipmentObjects 63 }

cucsEquipmentRackUnitPsuStatsEntry OBJECT-TYPE
    SYNTAX           CucsEquipmentRackUnitPsuStatsEntry
    MAX-ACCESS       not-accessible
    STATUS           current
    DESCRIPTION
        "Entry for the cucsEquipmentRackUnitPsuStatsTable table."
    INDEX { cucsEquipmentRackUnitPsuStatsInstanceId }
    ::= { cucsEquipmentRackUnitPsuStatsTable 1 }

CucsEquipmentRackUnitPsuStatsEntry ::= SEQUENCE {
    cucsEquipmentRackUnitPsuStatsInstanceId                          CucsManagedObjectId,
    cucsEquipmentRackUnitPsuStatsDn                                  CucsManagedObjectDn,
    cucsEquipmentRackUnitPsuStatsRn                                  SnmpAdminString,
    cucsEquipmentRackUnitPsuStatsAmbientTemp                         INTEGER,
    cucsEquipmentRackUnitPsuStatsAmbientTempAvg                      INTEGER,
    cucsEquipmentRackUnitPsuStatsAmbientTempMax                      INTEGER,
    cucsEquipmentRackUnitPsuStatsAmbientTempMin                      INTEGER,
    cucsEquipmentRackUnitPsuStatsInputPower                          INTEGER,
    cucsEquipmentRackUnitPsuStatsInputPowerAvg                       INTEGER,
    cucsEquipmentRackUnitPsuStatsInputPowerMax                       INTEGER,
    cucsEquipmentRackUnitPsuStatsInputPowerMin                       INTEGER,
    cucsEquipmentRackUnitPsuStatsInputVoltage                        INTEGER,
    cucsEquipmentRackUnitPsuStatsInputVoltageAvg                     INTEGER,
    cucsEquipmentRackUnitPsuStatsInputVoltageMax                     INTEGER,
    cucsEquipmentRackUnitPsuStatsInputVoltageMin                     INTEGER,
    cucsEquipmentRackUnitPsuStatsIntervals                           Gauge32,
    cucsEquipmentRackUnitPsuStatsOutputCurrent                       INTEGER,
    cucsEquipmentRackUnitPsuStatsOutputCurrentAvg                    INTEGER,
    cucsEquipmentRackUnitPsuStatsOutputCurrentMax                    INTEGER,
    cucsEquipmentRackUnitPsuStatsOutputCurrentMin                    INTEGER,
    cucsEquipmentRackUnitPsuStatsOutputPower                         INTEGER,
    cucsEquipmentRackUnitPsuStatsOutputPowerAvg                      INTEGER,
    cucsEquipmentRackUnitPsuStatsOutputPowerMax                      INTEGER,
    cucsEquipmentRackUnitPsuStatsOutputPowerMin                      INTEGER,
    cucsEquipmentRackUnitPsuStatsOutputVoltage                       INTEGER,
    cucsEquipmentRackUnitPsuStatsOutputVoltageAvg                    INTEGER,
    cucsEquipmentRackUnitPsuStatsOutputVoltageMax                    INTEGER,
    cucsEquipmentRackUnitPsuStatsOutputVoltageMin                    INTEGER,
    cucsEquipmentRackUnitPsuStatsSuspect                             TruthValue,
    cucsEquipmentRackUnitPsuStatsThresholded                         CucsEquipmentRackUnitPsuStatsThresholded,
    cucsEquipmentRackUnitPsuStatsTimeCollected                       DateAndTime,
    cucsEquipmentRackUnitPsuStatsUpdate                              Gauge32
}

cucsEquipmentRackUnitPsuStatsInstanceId OBJECT-TYPE
    SYNTAX       CucsManagedObjectId
    MAX-ACCESS   not-accessible
    STATUS       current
    DESCRIPTION
        "Instance identifier of the managed object."
    ::= { cucsEquipmentRackUnitPsuStatsEntry 1 }

cucsEquipmentRackUnitPsuStatsDn OBJECT-TYPE
    SYNTAX       CucsManagedObjectDn
    MAX-ACCESS   read-only
    STATUS       current
    DESCRIPTION
        "Cisco UCS equipment:RackUnitPsuStats:dn managed object property"
    ::= { cucsEquipmentRackUnitPsuStatsEntry 2 }

cucsEquipmentRackUnitPsuStatsRn OBJECT-TYPE
    SYNTAX       SnmpAdminString
    MAX-ACCESS   read-only
    STATUS       current
    DESCRIPTION
        "Cisco UCS equipment:RackUnitPsuStats:rn managed object property"
    ::= { cucsEquipmentRackUnitPsuStatsEntry 3 }

cucsEquipmentRackUnitPsuStatsAmbientTemp OBJECT-TYPE
    SYNTAX       INTEGER
    MAX-ACCESS   read-only
    STATUS       current
    DESCRIPTION
        "Cisco UCS equipment:RackUnitPsuStats:ambientTemp
        managed object property"
    ::= { cucsEquipmentRackUnitPsuStatsEntry 4 }

cucsEquipmentRackUnitPsuStatsAmbientTempAvg OBJECT-TYPE
    SYNTAX       INTEGER
    MAX-ACCESS   read-only
    STATUS       current
    DESCRIPTION
        "Cisco UCS equipment:RackUnitPsuStats:ambientTempAvg
        managed object property"
    ::= { cucsEquipmentRackUnitPsuStatsEntry 5 }

cucsEquipmentRackUnitPsuStatsAmbientTempMax OBJECT-TYPE
    SYNTAX       INTEGER
    MAX-ACCESS   read-only
    STATUS       current
    DESCRIPTION
        "Cisco UCS equipment:RackUnitPsuStats:ambientTempMax
        managed object property"
    ::= { cucsEquipmentRackUnitPsuStatsEntry 6 }

cucsEquipmentRackUnitPsuStatsAmbientTempMin OBJECT-TYPE
    SYNTAX       INTEGER
    MAX-ACCESS   read-only
    STATUS       current
    DESCRIPTION
        "Cisco UCS equipment:RackUnitPsuStats:ambientTempMin
        managed object property"
    ::= { cucsEquipmentRackUnitPsuStatsEntry 7 }

cucsEquipmentRackUnitPsuStatsInputPower OBJECT-TYPE
    SYNTAX       INTEGER
    MAX-ACCESS   read-only
    STATUS       current
    DESCRIPTION
        "Cisco UCS equipment:RackUnitPsuStats:inputPower
        managed object property"
    ::= { cucsEquipmentRackUnitPsuStatsEntry 8 }

cucsEquipmentRackUnitPsuStatsInputPowerAvg OBJECT-TYPE
    SYNTAX       INTEGER
    MAX-ACCESS   read-only
    STATUS       current
    DESCRIPTION
        "Cisco UCS equipment:RackUnitPsuStats:inputPowerAvg
        managed object property"
    ::= { cucsEquipmentRackUnitPsuStatsEntry 9 }

cucsEquipmentRackUnitPsuStatsInputPowerMax OBJECT-TYPE
    SYNTAX       INTEGER
    MAX-ACCESS   read-only
    STATUS       current
    DESCRIPTION
        "Cisco UCS equipment:RackUnitPsuStats:inputPowerMax
        managed object property"
    ::= { cucsEquipmentRackUnitPsuStatsEntry 10 }

cucsEquipmentRackUnitPsuStatsInputPowerMin OBJECT-TYPE
    SYNTAX       INTEGER
    MAX-ACCESS   read-only
    STATUS       current
    DESCRIPTION
        "Cisco UCS equipment:RackUnitPsuStats:inputPowerMin
        managed object property"
    ::= { cucsEquipmentRackUnitPsuStatsEntry 11 }

cucsEquipmentRackUnitPsuStatsInputVoltage OBJECT-TYPE
    SYNTAX       INTEGER
    MAX-ACCESS   read-only
    STATUS       current
    DESCRIPTION
        "Cisco UCS equipment:RackUnitPsuStats:inputVoltage
        managed object property"
    ::= { cucsEquipmentRackUnitPsuStatsEntry 12 }

cucsEquipmentRackUnitPsuStatsInputVoltageAvg OBJECT-TYPE
    SYNTAX       INTEGER
    MAX-ACCESS   read-only
    STATUS       current
    DESCRIPTION
        "Cisco UCS equipment:RackUnitPsuStats:inputVoltageAvg
        managed object property"
    ::= { cucsEquipmentRackUnitPsuStatsEntry 13 }

cucsEquipmentRackUnitPsuStatsInputVoltageMax OBJECT-TYPE
    SYNTAX       INTEGER
    MAX-ACCESS   read-only
    STATUS       current
    DESCRIPTION
        "Cisco UCS equipment:RackUnitPsuStats:inputVoltageMax
        managed object property"
    ::= { cucsEquipmentRackUnitPsuStatsEntry 14 }

cucsEquipmentRackUnitPsuStatsInputVoltageMin OBJECT-TYPE
    SYNTAX       INTEGER
    MAX-ACCESS   read-only
    STATUS       current
    DESCRIPTION
        "Cisco UCS equipment:RackUnitPsuStats:inputVoltageMin
        managed object property"
    ::= { cucsEquipmentRackUnitPsuStatsEntry 15 }

cucsEquipmentRackUnitPsuStatsIntervals OBJECT-TYPE
    SYNTAX       Gauge32
    MAX-ACCESS   read-only
    STATUS       current
    DESCRIPTION
        "Cisco UCS equipment:RackUnitPsuStats:intervals
        managed object property"
    ::= { cucsEquipmentRackUnitPsuStatsEntry 16 }

cucsEquipmentRackUnitPsuStatsOutputCurrent OBJECT-TYPE
    SYNTAX       INTEGER
    MAX-ACCESS   read-only
    STATUS       current
    DESCRIPTION
        "Cisco UCS equipment:RackUnitPsuStats:outputCurrent
        managed object property"
    ::= { cucsEquipmentRackUnitPsuStatsEntry 17 }

cucsEquipmentRackUnitPsuStatsOutputCurrentAvg OBJECT-TYPE
    SYNTAX       INTEGER
    MAX-ACCESS   read-only
    STATUS       current
    DESCRIPTION
        "Cisco UCS equipment:RackUnitPsuStats:outputCurrentAvg
        managed object property"
    ::= { cucsEquipmentRackUnitPsuStatsEntry 18 }

cucsEquipmentRackUnitPsuStatsOutputCurrentMax OBJECT-TYPE
    SYNTAX       INTEGER
    MAX-ACCESS   read-only
    STATUS       current
    DESCRIPTION
        "Cisco UCS equipment:RackUnitPsuStats:outputCurrentMax
        managed object property"
    ::= { cucsEquipmentRackUnitPsuStatsEntry 19 }

cucsEquipmentRackUnitPsuStatsOutputCurrentMin OBJECT-TYPE
    SYNTAX       INTEGER
    MAX-ACCESS   read-only
    STATUS       current
    DESCRIPTION
        "Cisco UCS equipment:RackUnitPsuStats:outputCurrentMin
        managed object property"
    ::= { cucsEquipmentRackUnitPsuStatsEntry 20 }

cucsEquipmentRackUnitPsuStatsOutputPower OBJECT-TYPE
    SYNTAX       INTEGER
    MAX-ACCESS   read-only
    STATUS       current
    DESCRIPTION
        "Cisco UCS equipment:RackUnitPsuStats:outputPower
        managed object property"
    ::= { cucsEquipmentRackUnitPsuStatsEntry 21 }

cucsEquipmentRackUnitPsuStatsOutputPowerAvg OBJECT-TYPE
    SYNTAX       INTEGER
    MAX-ACCESS   read-only
    STATUS       current
    DESCRIPTION
        "Cisco UCS equipment:RackUnitPsuStats:outputPowerAvg
        managed object property"
    ::= { cucsEquipmentRackUnitPsuStatsEntry 22 }

cucsEquipmentRackUnitPsuStatsOutputPowerMax OBJECT-TYPE
    SYNTAX       INTEGER
    MAX-ACCESS   read-only
    STATUS       current
    DESCRIPTION
        "Cisco UCS equipment:RackUnitPsuStats:outputPowerMax
        managed object property"
    ::= { cucsEquipmentRackUnitPsuStatsEntry 23 }

cucsEquipmentRackUnitPsuStatsOutputPowerMin OBJECT-TYPE
    SYNTAX       INTEGER
    MAX-ACCESS   read-only
    STATUS       current
    DESCRIPTION
        "Cisco UCS equipment:RackUnitPsuStats:outputPowerMin
        managed object property"
    ::= { cucsEquipmentRackUnitPsuStatsEntry 24 }

cucsEquipmentRackUnitPsuStatsOutputVoltage OBJECT-TYPE
    SYNTAX       INTEGER
    MAX-ACCESS   read-only
    STATUS       current
    DESCRIPTION
        "Cisco UCS equipment:RackUnitPsuStats:outputVoltage
        managed object property"
    ::= { cucsEquipmentRackUnitPsuStatsEntry 25 }

cucsEquipmentRackUnitPsuStatsOutputVoltageAvg OBJECT-TYPE
    SYNTAX       INTEGER
    MAX-ACCESS   read-only
    STATUS       current
    DESCRIPTION
        "Cisco UCS equipment:RackUnitPsuStats:outputVoltageAvg
        managed object property"
    ::= { cucsEquipmentRackUnitPsuStatsEntry 26 }

cucsEquipmentRackUnitPsuStatsOutputVoltageMax OBJECT-TYPE
    SYNTAX       INTEGER
    MAX-ACCESS   read-only
    STATUS       current
    DESCRIPTION
        "Cisco UCS equipment:RackUnitPsuStats:outputVoltageMax
        managed object property"
    ::= { cucsEquipmentRackUnitPsuStatsEntry 27 }

cucsEquipmentRackUnitPsuStatsOutputVoltageMin OBJECT-TYPE
    SYNTAX       INTEGER
    MAX-ACCESS   read-only
    STATUS       current
    DESCRIPTION
        "Cisco UCS equipment:RackUnitPsuStats:outputVoltageMin
        managed object property"
    ::= { cucsEquipmentRackUnitPsuStatsEntry 28 }

cucsEquipmentRackUnitPsuStatsSuspect OBJECT-TYPE
    SYNTAX       TruthValue
    MAX-ACCESS   read-only
    STATUS       current
    DESCRIPTION
        "Cisco UCS equipment:RackUnitPsuStats:suspect managed
        object property"
    ::= { cucsEquipmentRackUnitPsuStatsEntry 29 }

cucsEquipmentRackUnitPsuStatsThresholded OBJECT-TYPE
    SYNTAX       CucsEquipmentRackUnitPsuStatsThresholded
    MAX-ACCESS   read-only
    STATUS       current
    DESCRIPTION
        "Cisco UCS equipment:RackUnitPsuStats:thresholded
        managed object property"
    ::= { cucsEquipmentRackUnitPsuStatsEntry 30 }

cucsEquipmentRackUnitPsuStatsTimeCollected OBJECT-TYPE
    SYNTAX       DateAndTime
    MAX-ACCESS   read-only
    STATUS       current
    DESCRIPTION
        "Cisco UCS equipment:RackUnitPsuStats:timeCollected
        managed object property"
    ::= { cucsEquipmentRackUnitPsuStatsEntry 31 }

cucsEquipmentRackUnitPsuStatsUpdate OBJECT-TYPE
    SYNTAX       Gauge32
    MAX-ACCESS   read-only
    STATUS       current
    DESCRIPTION
        "Cisco UCS equipment:RackUnitPsuStats:update managed
        object property"
    ::= { cucsEquipmentRackUnitPsuStatsEntry 32 }

cucsEquipmentRackUnitPsuStatsHistTable OBJECT-TYPE
    SYNTAX           SEQUENCE OF CucsEquipmentRackUnitPsuStatsHistEntry
    MAX-ACCESS       not-accessible
    STATUS           current
    DESCRIPTION
        "Cisco UCS equipment:RackUnitPsuStatsHist managed object table"
    ::= { cucsEquipmentObjects 64 }

cucsEquipmentRackUnitPsuStatsHistEntry OBJECT-TYPE
    SYNTAX           CucsEquipmentRackUnitPsuStatsHistEntry
    MAX-ACCESS       not-accessible
    STATUS           current
    DESCRIPTION
        "Entry for the cucsEquipmentRackUnitPsuStatsHistTable table."
    INDEX { cucsEquipmentRackUnitPsuStatsHistInstanceId }
    ::= { cucsEquipmentRackUnitPsuStatsHistTable 1 }

CucsEquipmentRackUnitPsuStatsHistEntry ::= SEQUENCE {
    cucsEquipmentRackUnitPsuStatsHistInstanceId                      CucsManagedObjectId,
    cucsEquipmentRackUnitPsuStatsHistDn                              CucsManagedObjectDn,
    cucsEquipmentRackUnitPsuStatsHistRn                              SnmpAdminString,
    cucsEquipmentRackUnitPsuStatsHistAmbientTemp                     INTEGER,
    cucsEquipmentRackUnitPsuStatsHistAmbientTempAvg                  INTEGER,
    cucsEquipmentRackUnitPsuStatsHistAmbientTempMax                  INTEGER,
    cucsEquipmentRackUnitPsuStatsHistAmbientTempMin                  INTEGER,
    cucsEquipmentRackUnitPsuStatsHistId                              Unsigned64,
    cucsEquipmentRackUnitPsuStatsHistInputPower                      INTEGER,
    cucsEquipmentRackUnitPsuStatsHistInputPowerAvg                   INTEGER,
    cucsEquipmentRackUnitPsuStatsHistInputPowerMax                   INTEGER,
    cucsEquipmentRackUnitPsuStatsHistInputPowerMin                   INTEGER,
    cucsEquipmentRackUnitPsuStatsHistInputVoltage                    INTEGER,
    cucsEquipmentRackUnitPsuStatsHistInputVoltageAvg                 INTEGER,
    cucsEquipmentRackUnitPsuStatsHistInputVoltageMax                 INTEGER,
    cucsEquipmentRackUnitPsuStatsHistInputVoltageMin                 INTEGER,
    cucsEquipmentRackUnitPsuStatsHistMostRecent                      TruthValue,
    cucsEquipmentRackUnitPsuStatsHistOutputCurrent                   INTEGER,
    cucsEquipmentRackUnitPsuStatsHistOutputCurrentAvg                INTEGER,
    cucsEquipmentRackUnitPsuStatsHistOutputCurrentMax                INTEGER,
    cucsEquipmentRackUnitPsuStatsHistOutputCurrentMin                INTEGER,
    cucsEquipmentRackUnitPsuStatsHistOutputPower                     INTEGER,
    cucsEquipmentRackUnitPsuStatsHistOutputPowerAvg                  INTEGER,
    cucsEquipmentRackUnitPsuStatsHistOutputPowerMax                  INTEGER,
    cucsEquipmentRackUnitPsuStatsHistOutputPowerMin                  INTEGER,
    cucsEquipmentRackUnitPsuStatsHistOutputVoltage                   INTEGER,
    cucsEquipmentRackUnitPsuStatsHistOutputVoltageAvg                INTEGER,
    cucsEquipmentRackUnitPsuStatsHistOutputVoltageMax                INTEGER,
    cucsEquipmentRackUnitPsuStatsHistOutputVoltageMin                INTEGER,
    cucsEquipmentRackUnitPsuStatsHistSuspect                         TruthValue,
    cucsEquipmentRackUnitPsuStatsHistThresholded                     CucsEquipmentRackUnitPsuStatsHistThresholded,
    cucsEquipmentRackUnitPsuStatsHistTimeCollected                   DateAndTime
}

cucsEquipmentRackUnitPsuStatsHistInstanceId OBJECT-TYPE
    SYNTAX       CucsManagedObjectId
    MAX-ACCESS   not-accessible
    STATUS       current
    DESCRIPTION
        "Instance identifier of the managed object."
    ::= { cucsEquipmentRackUnitPsuStatsHistEntry 1 }

cucsEquipmentRackUnitPsuStatsHistDn OBJECT-TYPE
    SYNTAX       CucsManagedObjectDn
    MAX-ACCESS   read-only
    STATUS       current
    DESCRIPTION
        "Cisco UCS equipment:RackUnitPsuStatsHist:dn managed
        object property"
    ::= { cucsEquipmentRackUnitPsuStatsHistEntry 2 }

cucsEquipmentRackUnitPsuStatsHistRn OBJECT-TYPE
    SYNTAX       SnmpAdminString
    MAX-ACCESS   read-only
    STATUS       current
    DESCRIPTION
        "Cisco UCS equipment:RackUnitPsuStatsHist:rn managed
        object property"
    ::= { cucsEquipmentRackUnitPsuStatsHistEntry 3 }

cucsEquipmentRackUnitPsuStatsHistAmbientTemp OBJECT-TYPE
    SYNTAX       INTEGER
    MAX-ACCESS   read-only
    STATUS       current
    DESCRIPTION
        "Cisco UCS equipment:RackUnitPsuStatsHist:ambientTemp
        managed object property"
    ::= { cucsEquipmentRackUnitPsuStatsHistEntry 4 }

cucsEquipmentRackUnitPsuStatsHistAmbientTempAvg OBJECT-TYPE
    SYNTAX       INTEGER
    MAX-ACCESS   read-only
    STATUS       current
    DESCRIPTION
        "Cisco UCS equipment:RackUnitPsuStatsHist:ambientTempAvg
        managed object property"
    ::= { cucsEquipmentRackUnitPsuStatsHistEntry 5 }

cucsEquipmentRackUnitPsuStatsHistAmbientTempMax OBJECT-TYPE
    SYNTAX       INTEGER
    MAX-ACCESS   read-only
    STATUS       current
    DESCRIPTION
        "Cisco UCS equipment:RackUnitPsuStatsHist:ambientTempMax
        managed object property"
    ::= { cucsEquipmentRackUnitPsuStatsHistEntry 6 }

cucsEquipmentRackUnitPsuStatsHistAmbientTempMin OBJECT-TYPE
    SYNTAX       INTEGER
    MAX-ACCESS   read-only
    STATUS       current
    DESCRIPTION
        "Cisco UCS equipment:RackUnitPsuStatsHist:ambientTempMin
        managed object property"
    ::= { cucsEquipmentRackUnitPsuStatsHistEntry 7 }

cucsEquipmentRackUnitPsuStatsHistId OBJECT-TYPE
    SYNTAX       Unsigned64
    MAX-ACCESS   read-only
    STATUS       current
    DESCRIPTION
        "Cisco UCS equipment:RackUnitPsuStatsHist:id managed
        object property"
    ::= { cucsEquipmentRackUnitPsuStatsHistEntry 8 }

cucsEquipmentRackUnitPsuStatsHistInputPower OBJECT-TYPE
    SYNTAX       INTEGER
    MAX-ACCESS   read-only
    STATUS       current
    DESCRIPTION
        "Cisco UCS equipment:RackUnitPsuStatsHist:inputPower
        managed object property"
    ::= { cucsEquipmentRackUnitPsuStatsHistEntry 9 }

cucsEquipmentRackUnitPsuStatsHistInputPowerAvg OBJECT-TYPE
    SYNTAX       INTEGER
    MAX-ACCESS   read-only
    STATUS       current
    DESCRIPTION
        "Cisco UCS equipment:RackUnitPsuStatsHist:inputPowerAvg
        managed object property"
    ::= { cucsEquipmentRackUnitPsuStatsHistEntry 10 }

cucsEquipmentRackUnitPsuStatsHistInputPowerMax OBJECT-TYPE
    SYNTAX       INTEGER
    MAX-ACCESS   read-only
    STATUS       current
    DESCRIPTION
        "Cisco UCS equipment:RackUnitPsuStatsHist:inputPowerMax
        managed object property"
    ::= { cucsEquipmentRackUnitPsuStatsHistEntry 11 }

cucsEquipmentRackUnitPsuStatsHistInputPowerMin OBJECT-TYPE
    SYNTAX       INTEGER
    MAX-ACCESS   read-only
    STATUS       current
    DESCRIPTION
        "Cisco UCS equipment:RackUnitPsuStatsHist:inputPowerMin
        managed object property"
    ::= { cucsEquipmentRackUnitPsuStatsHistEntry 12 }

cucsEquipmentRackUnitPsuStatsHistInputVoltage OBJECT-TYPE
    SYNTAX       INTEGER
    MAX-ACCESS   read-only
    STATUS       current
    DESCRIPTION
        "Cisco UCS equipment:RackUnitPsuStatsHist:inputVoltage
        managed object property"
    ::= { cucsEquipmentRackUnitPsuStatsHistEntry 13 }

cucsEquipmentRackUnitPsuStatsHistInputVoltageAvg OBJECT-TYPE
    SYNTAX       INTEGER
    MAX-ACCESS   read-only
    STATUS       current
    DESCRIPTION
        "Cisco UCS equipment:RackUnitPsuStatsHist:inputVoltageAvg
        managed object property"
    ::= { cucsEquipmentRackUnitPsuStatsHistEntry 14 }

cucsEquipmentRackUnitPsuStatsHistInputVoltageMax OBJECT-TYPE
    SYNTAX       INTEGER
    MAX-ACCESS   read-only
    STATUS       current
    DESCRIPTION
        "Cisco UCS equipment:RackUnitPsuStatsHist:inputVoltageMax
        managed object property"
    ::= { cucsEquipmentRackUnitPsuStatsHistEntry 15 }

cucsEquipmentRackUnitPsuStatsHistInputVoltageMin OBJECT-TYPE
    SYNTAX       INTEGER
    MAX-ACCESS   read-only
    STATUS       current
    DESCRIPTION
        "Cisco UCS equipment:RackUnitPsuStatsHist:inputVoltageMin
        managed object property"
    ::= { cucsEquipmentRackUnitPsuStatsHistEntry 16 }

cucsEquipmentRackUnitPsuStatsHistMostRecent OBJECT-TYPE
    SYNTAX       TruthValue
    MAX-ACCESS   read-only
    STATUS       current
    DESCRIPTION
        "Cisco UCS equipment:RackUnitPsuStatsHist:mostRecent
        managed object property"
    ::= { cucsEquipmentRackUnitPsuStatsHistEntry 17 }

cucsEquipmentRackUnitPsuStatsHistOutputCurrent OBJECT-TYPE
    SYNTAX       INTEGER
    MAX-ACCESS   read-only
    STATUS       current
    DESCRIPTION
        "Cisco UCS equipment:RackUnitPsuStatsHist:outputCurrent
        managed object property"
    ::= { cucsEquipmentRackUnitPsuStatsHistEntry 18 }

cucsEquipmentRackUnitPsuStatsHistOutputCurrentAvg OBJECT-TYPE
    SYNTAX       INTEGER
    MAX-ACCESS   read-only
    STATUS       current
    DESCRIPTION
        "Cisco UCS equipment:RackUnitPsuStatsHist:outputCurrentAvg
        managed object property"
    ::= { cucsEquipmentRackUnitPsuStatsHistEntry 19 }

cucsEquipmentRackUnitPsuStatsHistOutputCurrentMax OBJECT-TYPE
    SYNTAX       INTEGER
    MAX-ACCESS   read-only
    STATUS       current
    DESCRIPTION
        "Cisco UCS equipment:RackUnitPsuStatsHist:outputCurrentMax
        managed object property"
    ::= { cucsEquipmentRackUnitPsuStatsHistEntry 20 }

cucsEquipmentRackUnitPsuStatsHistOutputCurrentMin OBJECT-TYPE
    SYNTAX       INTEGER
    MAX-ACCESS   read-only
    STATUS       current
    DESCRIPTION
        "Cisco UCS equipment:RackUnitPsuStatsHist:outputCurrentMin
        managed object property"
    ::= { cucsEquipmentRackUnitPsuStatsHistEntry 21 }

cucsEquipmentRackUnitPsuStatsHistOutputPower OBJECT-TYPE
    SYNTAX       INTEGER
    MAX-ACCESS   read-only
    STATUS       current
    DESCRIPTION
        "Cisco UCS equipment:RackUnitPsuStatsHist:outputPower
        managed object property"
    ::= { cucsEquipmentRackUnitPsuStatsHistEntry 22 }

cucsEquipmentRackUnitPsuStatsHistOutputPowerAvg OBJECT-TYPE
    SYNTAX       INTEGER
    MAX-ACCESS   read-only
    STATUS       current
    DESCRIPTION
        "Cisco UCS equipment:RackUnitPsuStatsHist:outputPowerAvg
        managed object property"
    ::= { cucsEquipmentRackUnitPsuStatsHistEntry 23 }

cucsEquipmentRackUnitPsuStatsHistOutputPowerMax OBJECT-TYPE
    SYNTAX       INTEGER
    MAX-ACCESS   read-only
    STATUS       current
    DESCRIPTION
        "Cisco UCS equipment:RackUnitPsuStatsHist:outputPowerMax
        managed object property"
    ::= { cucsEquipmentRackUnitPsuStatsHistEntry 24 }

cucsEquipmentRackUnitPsuStatsHistOutputPowerMin OBJECT-TYPE
    SYNTAX       INTEGER
    MAX-ACCESS   read-only
    STATUS       current
    DESCRIPTION
        "Cisco UCS equipment:RackUnitPsuStatsHist:outputPowerMin
        managed object property"
    ::= { cucsEquipmentRackUnitPsuStatsHistEntry 25 }

cucsEquipmentRackUnitPsuStatsHistOutputVoltage OBJECT-TYPE
    SYNTAX       INTEGER
    MAX-ACCESS   read-only
    STATUS       current
    DESCRIPTION
        "Cisco UCS equipment:RackUnitPsuStatsHist:outputVoltage
        managed object property"
    ::= { cucsEquipmentRackUnitPsuStatsHistEntry 26 }

cucsEquipmentRackUnitPsuStatsHistOutputVoltageAvg OBJECT-TYPE
    SYNTAX       INTEGER
    MAX-ACCESS   read-only
    STATUS       current
    DESCRIPTION
        "Cisco UCS equipment:RackUnitPsuStatsHist:outputVoltageAvg
        managed object property"
    ::= { cucsEquipmentRackUnitPsuStatsHistEntry 27 }

cucsEquipmentRackUnitPsuStatsHistOutputVoltageMax OBJECT-TYPE
    SYNTAX       INTEGER
    MAX-ACCESS   read-only
    STATUS       current
    DESCRIPTION
        "Cisco UCS equipment:RackUnitPsuStatsHist:outputVoltageMax
        managed object property"
    ::= { cucsEquipmentRackUnitPsuStatsHistEntry 28 }

cucsEquipmentRackUnitPsuStatsHistOutputVoltageMin OBJECT-TYPE
    SYNTAX       INTEGER
    MAX-ACCESS   read-only
    STATUS       current
    DESCRIPTION
        "Cisco UCS equipment:RackUnitPsuStatsHist:outputVoltageMin
        managed object property"
    ::= { cucsEquipmentRackUnitPsuStatsHistEntry 29 }

cucsEquipmentRackUnitPsuStatsHistSuspect OBJECT-TYPE
    SYNTAX       TruthValue
    MAX-ACCESS   read-only
    STATUS       current
    DESCRIPTION
        "Cisco UCS equipment:RackUnitPsuStatsHist:suspect
        managed object property"
    ::= { cucsEquipmentRackUnitPsuStatsHistEntry 30 }

cucsEquipmentRackUnitPsuStatsHistThresholded OBJECT-TYPE
    SYNTAX       CucsEquipmentRackUnitPsuStatsHistThresholded
    MAX-ACCESS   read-only
    STATUS       current
    DESCRIPTION
        "Cisco UCS equipment:RackUnitPsuStatsHist:thresholded
        managed object property"
    ::= { cucsEquipmentRackUnitPsuStatsHistEntry 31 }

cucsEquipmentRackUnitPsuStatsHistTimeCollected OBJECT-TYPE
    SYNTAX       DateAndTime
    MAX-ACCESS   read-only
    STATUS       current
    DESCRIPTION
        "Cisco UCS equipment:RackUnitPsuStatsHist:timeCollected
        managed object property"
    ::= { cucsEquipmentRackUnitPsuStatsHistEntry 32 }

cucsEquipmentRaidDefTable OBJECT-TYPE
    SYNTAX           SEQUENCE OF CucsEquipmentRaidDefEntry
    MAX-ACCESS       not-accessible
    STATUS           current
    DESCRIPTION
        "Cisco UCS equipment:RaidDef managed object table"
    ::= { cucsEquipmentObjects 75 }

cucsEquipmentRaidDefEntry OBJECT-TYPE
    SYNTAX           CucsEquipmentRaidDefEntry
    MAX-ACCESS       not-accessible
    STATUS           current
    DESCRIPTION
        "Entry for the cucsEquipmentRaidDefTable table."
    INDEX { cucsEquipmentRaidDefInstanceId }
    ::= { cucsEquipmentRaidDefTable 1 }

CucsEquipmentRaidDefEntry ::= SEQUENCE {
    cucsEquipmentRaidDefInstanceId                                   CucsManagedObjectId,
    cucsEquipmentRaidDefDn                                           CucsManagedObjectDn,
    cucsEquipmentRaidDefRn                                           SnmpAdminString,
    cucsEquipmentRaidDefDescr                                        SnmpAdminString,
    cucsEquipmentRaidDefIntId                                        SnmpAdminString,
    cucsEquipmentRaidDefLevel                                        CucsStorageLocalDiskMode,
    cucsEquipmentRaidDefName                                         SnmpAdminString,
    cucsEquipmentRaidDefPolicyLevel                                  Gauge32,
    cucsEquipmentRaidDefPolicyOwner                                  CucsPolicyPolicyOwner
}

cucsEquipmentRaidDefInstanceId OBJECT-TYPE
    SYNTAX       CucsManagedObjectId
    MAX-ACCESS   not-accessible
    STATUS       current
    DESCRIPTION
        "Instance identifier of the managed object."
    ::= { cucsEquipmentRaidDefEntry 1 }

cucsEquipmentRaidDefDn OBJECT-TYPE
    SYNTAX       CucsManagedObjectDn
    MAX-ACCESS   read-only
    STATUS       current
    DESCRIPTION
        "Cisco UCS equipment:RaidDef:dn managed object property"
    ::= { cucsEquipmentRaidDefEntry 2 }

cucsEquipmentRaidDefRn OBJECT-TYPE
    SYNTAX       SnmpAdminString
    MAX-ACCESS   read-only
    STATUS       current
    DESCRIPTION
        "Cisco UCS equipment:RaidDef:rn managed object property"
    ::= { cucsEquipmentRaidDefEntry 3 }

cucsEquipmentRaidDefDescr OBJECT-TYPE
    SYNTAX       SnmpAdminString
    MAX-ACCESS   read-only
    STATUS       current
    DESCRIPTION
        "Cisco UCS equipment:RaidDef:descr managed object property"
    ::= { cucsEquipmentRaidDefEntry 4 }

cucsEquipmentRaidDefIntId OBJECT-TYPE
    SYNTAX       SnmpAdminString
    MAX-ACCESS   read-only
    STATUS       current
    DESCRIPTION
        "Cisco UCS equipment:RaidDef:intId managed object property"
    ::= { cucsEquipmentRaidDefEntry 5 }

cucsEquipmentRaidDefLevel OBJECT-TYPE
    SYNTAX       CucsStorageLocalDiskMode
    MAX-ACCESS   read-only
    STATUS       current
    DESCRIPTION
        "Cisco UCS equipment:RaidDef:level managed object property"
    ::= { cucsEquipmentRaidDefEntry 6 }

cucsEquipmentRaidDefName OBJECT-TYPE
    SYNTAX       SnmpAdminString
    MAX-ACCESS   read-only
    STATUS       current
    DESCRIPTION
        "Cisco UCS equipment:RaidDef:name managed object property"
    ::= { cucsEquipmentRaidDefEntry 7 }

cucsEquipmentRaidDefPolicyLevel OBJECT-TYPE
    SYNTAX       Gauge32
    MAX-ACCESS   read-only
    STATUS       current
    DESCRIPTION
        "Cisco UCS equipment:RaidDef:policyLevel managed object property"
    ::= { cucsEquipmentRaidDefEntry 8 }

cucsEquipmentRaidDefPolicyOwner OBJECT-TYPE
    SYNTAX       CucsPolicyPolicyOwner
    MAX-ACCESS   read-only
    STATUS       current
    DESCRIPTION
        "Cisco UCS equipment:RaidDef:policyOwner managed object property"
    ::= { cucsEquipmentRaidDefEntry 9 }

cucsEquipmentRequirementTable OBJECT-TYPE
    SYNTAX           SEQUENCE OF CucsEquipmentRequirementEntry
    MAX-ACCESS       not-accessible
    STATUS           current
    DESCRIPTION
        "Cisco UCS equipment:Requirement managed object table"
    ::= { cucsEquipmentObjects 196 }

cucsEquipmentRequirementEntry OBJECT-TYPE
    SYNTAX           CucsEquipmentRequirementEntry
    MAX-ACCESS       not-accessible
    STATUS           current
    DESCRIPTION
        "Entry for the cucsEquipmentRequirementTable table."
    INDEX { cucsEquipmentRequirementInstanceId }
    ::= { cucsEquipmentRequirementTable 1 }

CucsEquipmentRequirementEntry ::= SEQUENCE {
    cucsEquipmentRequirementInstanceId                               CucsManagedObjectId,
    cucsEquipmentRequirementDn                                       CucsManagedObjectDn,
    cucsEquipmentRequirementRn                                       SnmpAdminString,
    cucsEquipmentRequirementAssignedToDn                             SnmpAdminString,
    cucsEquipmentRequirementChassisDn                                SnmpAdminString,
    cucsEquipmentRequirementChassisPoolDn                            SnmpAdminString,
    cucsEquipmentRequirementIssues                                   CucsEquipmentChassisConfigIssues,
    cucsEquipmentRequirementName                                     SnmpAdminString,
    cucsEquipmentRequirementOperName                                 SnmpAdminString,
    cucsEquipmentRequirementOperState                                CucsEquipmentChassisProfileBindingOperState,
    cucsEquipmentRequirementQualifier                                SnmpAdminString,
    cucsEquipmentRequirementRestrictMigration                        TruthValue
}

cucsEquipmentRequirementInstanceId OBJECT-TYPE
    SYNTAX       CucsManagedObjectId
    MAX-ACCESS   not-accessible
    STATUS       current
    DESCRIPTION
        "Instance identifier of the managed object."
    ::= { cucsEquipmentRequirementEntry 1 }

cucsEquipmentRequirementDn OBJECT-TYPE
    SYNTAX       CucsManagedObjectDn
    MAX-ACCESS   read-only
    STATUS       current
    DESCRIPTION
        "Cisco UCS equipment:Requirement:dn managed object property"
    ::= { cucsEquipmentRequirementEntry 2 }

cucsEquipmentRequirementRn OBJECT-TYPE
    SYNTAX       SnmpAdminString
    MAX-ACCESS   read-only
    STATUS       current
    DESCRIPTION
        "Cisco UCS equipment:Requirement:rn managed object property"
    ::= { cucsEquipmentRequirementEntry 3 }

cucsEquipmentRequirementAssignedToDn OBJECT-TYPE
    SYNTAX       SnmpAdminString
    MAX-ACCESS   read-only
    STATUS       current
    DESCRIPTION
        "Cisco UCS equipment:Requirement:assignedToDn managed
        object property"
    ::= { cucsEquipmentRequirementEntry 4 }

cucsEquipmentRequirementChassisDn OBJECT-TYPE
    SYNTAX       SnmpAdminString
    MAX-ACCESS   read-only
    STATUS       current
    DESCRIPTION
        "Cisco UCS equipment:Requirement:chassisDn managed
        object property"
    ::= { cucsEquipmentRequirementEntry 5 }

cucsEquipmentRequirementChassisPoolDn OBJECT-TYPE
    SYNTAX       SnmpAdminString
    MAX-ACCESS   read-only
    STATUS       current
    DESCRIPTION
        "Cisco UCS equipment:Requirement:chassisPoolDn
        managed object property"
    ::= { cucsEquipmentRequirementEntry 6 }

cucsEquipmentRequirementIssues OBJECT-TYPE
    SYNTAX       CucsEquipmentChassisConfigIssues
    MAX-ACCESS   read-only
    STATUS       current
    DESCRIPTION
        "Cisco UCS equipment:Requirement:issues managed object property"
    ::= { cucsEquipmentRequirementEntry 7 }

cucsEquipmentRequirementName OBJECT-TYPE
    SYNTAX       SnmpAdminString
    MAX-ACCESS   read-only
    STATUS       current
    DESCRIPTION
        "Cisco UCS equipment:Requirement:name managed object property"
    ::= { cucsEquipmentRequirementEntry 8 }

cucsEquipmentRequirementOperName OBJECT-TYPE
    SYNTAX       SnmpAdminString
    MAX-ACCESS   read-only
    STATUS       current
    DESCRIPTION
        "Cisco UCS equipment:Requirement:operName managed object property"
    ::= { cucsEquipmentRequirementEntry 9 }

cucsEquipmentRequirementOperState OBJECT-TYPE
    SYNTAX       CucsEquipmentChassisProfileBindingOperState
    MAX-ACCESS   read-only
    STATUS       current
    DESCRIPTION
        "Cisco UCS equipment:Requirement:operState managed
        object property"
    ::= { cucsEquipmentRequirementEntry 10 }

cucsEquipmentRequirementQualifier OBJECT-TYPE
    SYNTAX       SnmpAdminString
    MAX-ACCESS   read-only
    STATUS       current
    DESCRIPTION
        "Cisco UCS equipment:Requirement:qualifier managed
        object property"
    ::= { cucsEquipmentRequirementEntry 11 }

cucsEquipmentRequirementRestrictMigration OBJECT-TYPE
    SYNTAX       TruthValue
    MAX-ACCESS   read-only
    STATUS       current
    DESCRIPTION
        "Cisco UCS equipment:Requirement:restrictMigration
        managed object property"
    ::= { cucsEquipmentRequirementEntry 12 }

cucsEquipmentSecureBootTable OBJECT-TYPE
    SYNTAX           SEQUENCE OF CucsEquipmentSecureBootEntry
    MAX-ACCESS       not-accessible
    STATUS           current
    DESCRIPTION
        "Cisco UCS equipment:SecureBoot managed object table"
    ::= { cucsEquipmentObjects 121 }

cucsEquipmentSecureBootEntry OBJECT-TYPE
    SYNTAX           CucsEquipmentSecureBootEntry
    MAX-ACCESS       not-accessible
    STATUS           current
    DESCRIPTION
        "Entry for the cucsEquipmentSecureBootTable table."
    INDEX { cucsEquipmentSecureBootInstanceId }
    ::= { cucsEquipmentSecureBootTable 1 }

CucsEquipmentSecureBootEntry ::= SEQUENCE {
    cucsEquipmentSecureBootInstanceId                                CucsManagedObjectId,
    cucsEquipmentSecureBootDn                                        CucsManagedObjectDn,
    cucsEquipmentSecureBootRn                                        SnmpAdminString,
    cucsEquipmentSecureBootMinBiosVersion                            SnmpAdminString,
    cucsEquipmentSecureBootMinCimcVersion                            SnmpAdminString,
    cucsEquipmentSecureBootDescr                                     SnmpAdminString,
    cucsEquipmentSecureBootIntId                                     SnmpAdminString,
    cucsEquipmentSecureBootName                                      SnmpAdminString,
    cucsEquipmentSecureBootPolicyLevel                               Gauge32,
    cucsEquipmentSecureBootPolicyOwner                               CucsPolicyPolicyOwner
}

cucsEquipmentSecureBootInstanceId OBJECT-TYPE
    SYNTAX       CucsManagedObjectId
    MAX-ACCESS   not-accessible
    STATUS       current
    DESCRIPTION
        "Instance identifier of the managed object."
    ::= { cucsEquipmentSecureBootEntry 1 }

cucsEquipmentSecureBootDn OBJECT-TYPE
    SYNTAX       CucsManagedObjectDn
    MAX-ACCESS   read-only
    STATUS       current
    DESCRIPTION
        "Cisco UCS equipment:SecureBoot:dn managed object property"
    ::= { cucsEquipmentSecureBootEntry 2 }

cucsEquipmentSecureBootRn OBJECT-TYPE
    SYNTAX       SnmpAdminString
    MAX-ACCESS   read-only
    STATUS       current
    DESCRIPTION
        "Cisco UCS equipment:SecureBoot:rn managed object property"
    ::= { cucsEquipmentSecureBootEntry 3 }

cucsEquipmentSecureBootMinBiosVersion OBJECT-TYPE
    SYNTAX       SnmpAdminString
    MAX-ACCESS   read-only
    STATUS       current
    DESCRIPTION
        "Cisco UCS equipment:SecureBoot:minBiosVersion
        managed object property"
    ::= { cucsEquipmentSecureBootEntry 4 }

cucsEquipmentSecureBootMinCimcVersion OBJECT-TYPE
    SYNTAX       SnmpAdminString
    MAX-ACCESS   read-only
    STATUS       current
    DESCRIPTION
        "Cisco UCS equipment:SecureBoot:minCimcVersion
        managed object property"
    ::= { cucsEquipmentSecureBootEntry 5 }

cucsEquipmentSecureBootDescr OBJECT-TYPE
    SYNTAX       SnmpAdminString
    MAX-ACCESS   read-only
    STATUS       current
    DESCRIPTION
        "Cisco UCS equipment:SecureBoot:descr managed object property"
    ::= { cucsEquipmentSecureBootEntry 6 }

cucsEquipmentSecureBootIntId OBJECT-TYPE
    SYNTAX       SnmpAdminString
    MAX-ACCESS   read-only
    STATUS       current
    DESCRIPTION
        "Cisco UCS equipment:SecureBoot:intId managed object property"
    ::= { cucsEquipmentSecureBootEntry 7 }

cucsEquipmentSecureBootName OBJECT-TYPE
    SYNTAX       SnmpAdminString
    MAX-ACCESS   read-only
    STATUS       current
    DESCRIPTION
        "Cisco UCS equipment:SecureBoot:name managed object property"
    ::= { cucsEquipmentSecureBootEntry 8 }

cucsEquipmentSecureBootPolicyLevel OBJECT-TYPE
    SYNTAX       Gauge32
    MAX-ACCESS   read-only
    STATUS       current
    DESCRIPTION
        "Cisco UCS equipment:SecureBoot:policyLevel managed
        object property"
    ::= { cucsEquipmentSecureBootEntry 9 }

cucsEquipmentSecureBootPolicyOwner OBJECT-TYPE
    SYNTAX       CucsPolicyPolicyOwner
    MAX-ACCESS   read-only
    STATUS       current
    DESCRIPTION
        "Cisco UCS equipment:SecureBoot:policyOwner managed
        object property"
    ::= { cucsEquipmentSecureBootEntry 10 }

cucsEquipmentSecurityUnitCapProviderTable OBJECT-TYPE
    SYNTAX           SEQUENCE OF CucsEquipmentSecurityUnitCapProviderEntry
    MAX-ACCESS       not-accessible
    STATUS           current
    DESCRIPTION
        "Cisco UCS equipment:SecurityUnitCapProvider managed object table"
    ::= { cucsEquipmentObjects 168 }

cucsEquipmentSecurityUnitCapProviderEntry OBJECT-TYPE
    SYNTAX           CucsEquipmentSecurityUnitCapProviderEntry
    MAX-ACCESS       not-accessible
    STATUS           current
    DESCRIPTION
        "Entry for the cucsEquipmentSecurityUnitCapProviderTable table."
    INDEX { cucsEquipmentSecurityUnitCapProviderInstanceId }
    ::= { cucsEquipmentSecurityUnitCapProviderTable 1 }

CucsEquipmentSecurityUnitCapProviderEntry ::= SEQUENCE {
    cucsEquipmentSecurityUnitCapProviderInstanceId                   CucsManagedObjectId,
    cucsEquipmentSecurityUnitCapProviderDn                           CucsManagedObjectDn,
    cucsEquipmentSecurityUnitCapProviderRn                           SnmpAdminString,
    cucsEquipmentSecurityUnitCapProviderDeleted                      TruthValue,
    cucsEquipmentSecurityUnitCapProviderDeprecated                   TruthValue,
    cucsEquipmentSecurityUnitCapProviderElementLoadFailures          Gauge32,
    cucsEquipmentSecurityUnitCapProviderElementsLoaded               Gauge32,
    cucsEquipmentSecurityUnitCapProviderGencount                     Gauge32,
    cucsEquipmentSecurityUnitCapProviderLoadErrors                   Gauge32,
    cucsEquipmentSecurityUnitCapProviderLoadWarnings                 Gauge32,
    cucsEquipmentSecurityUnitCapProviderMgmtPlaneVer                 SnmpAdminString,
    cucsEquipmentSecurityUnitCapProviderModel                        SnmpAdminString,
    cucsEquipmentSecurityUnitCapProviderPromCardType                 Gauge32,
    cucsEquipmentSecurityUnitCapProviderRevision                     SnmpAdminString,
    cucsEquipmentSecurityUnitCapProviderVendor                       SnmpAdminString
}

cucsEquipmentSecurityUnitCapProviderInstanceId OBJECT-TYPE
    SYNTAX       CucsManagedObjectId
    MAX-ACCESS   not-accessible
    STATUS       current
    DESCRIPTION
        "Instance identifier of the managed object."
    ::= { cucsEquipmentSecurityUnitCapProviderEntry 1 }

cucsEquipmentSecurityUnitCapProviderDn OBJECT-TYPE
    SYNTAX       CucsManagedObjectDn
    MAX-ACCESS   read-only
    STATUS       current
    DESCRIPTION
        "Cisco UCS equipment:SecurityUnitCapProvider:dn
        managed object property"
    ::= { cucsEquipmentSecurityUnitCapProviderEntry 2 }

cucsEquipmentSecurityUnitCapProviderRn OBJECT-TYPE
    SYNTAX       SnmpAdminString
    MAX-ACCESS   read-only
    STATUS       current
    DESCRIPTION
        "Cisco UCS equipment:SecurityUnitCapProvider:rn
        managed object property"
    ::= { cucsEquipmentSecurityUnitCapProviderEntry 3 }

cucsEquipmentSecurityUnitCapProviderDeleted OBJECT-TYPE
    SYNTAX       TruthValue
    MAX-ACCESS   read-only
    STATUS       current
    DESCRIPTION
        "Cisco UCS equipment:SecurityUnitCapProvider:deleted
        managed object property"
    ::= { cucsEquipmentSecurityUnitCapProviderEntry 4 }

cucsEquipmentSecurityUnitCapProviderDeprecated OBJECT-TYPE
    SYNTAX       TruthValue
    MAX-ACCESS   read-only
    STATUS       current
    DESCRIPTION
        "Cisco UCS equipment:SecurityUnitCapProvider:deprecated
        managed object property"
    ::= { cucsEquipmentSecurityUnitCapProviderEntry 5 }

cucsEquipmentSecurityUnitCapProviderElementLoadFailures OBJECT-TYPE
    SYNTAX       Gauge32
    MAX-ACCESS   read-only
    STATUS       current
    DESCRIPTION
        "Cisco UCS equipment:SecurityUnitCapProvider:elementLoadFailures
        managed object property"
    ::= { cucsEquipmentSecurityUnitCapProviderEntry 6 }

cucsEquipmentSecurityUnitCapProviderElementsLoaded OBJECT-TYPE
    SYNTAX       Gauge32
    MAX-ACCESS   read-only
    STATUS       current
    DESCRIPTION
        "Cisco UCS equipment:SecurityUnitCapProvider:elementsLoaded
        managed object property"
    ::= { cucsEquipmentSecurityUnitCapProviderEntry 7 }

cucsEquipmentSecurityUnitCapProviderGencount OBJECT-TYPE
    SYNTAX       Gauge32
    MAX-ACCESS   read-only
    STATUS       current
    DESCRIPTION
        "Cisco UCS equipment:SecurityUnitCapProvider:gencount
        managed object property"
    ::= { cucsEquipmentSecurityUnitCapProviderEntry 8 }

cucsEquipmentSecurityUnitCapProviderLoadErrors OBJECT-TYPE
    SYNTAX       Gauge32
    MAX-ACCESS   read-only
    STATUS       current
    DESCRIPTION
        "Cisco UCS equipment:SecurityUnitCapProvider:loadErrors
        managed object property"
    ::= { cucsEquipmentSecurityUnitCapProviderEntry 9 }

cucsEquipmentSecurityUnitCapProviderLoadWarnings OBJECT-TYPE
    SYNTAX       Gauge32
    MAX-ACCESS   read-only
    STATUS       current
    DESCRIPTION
        "Cisco UCS equipment:SecurityUnitCapProvider:loadWarnings
        managed object property"
    ::= { cucsEquipmentSecurityUnitCapProviderEntry 10 }

cucsEquipmentSecurityUnitCapProviderMgmtPlaneVer OBJECT-TYPE
    SYNTAX       SnmpAdminString
    MAX-ACCESS   read-only
    STATUS       current
    DESCRIPTION
        "Cisco UCS equipment:SecurityUnitCapProvider:mgmtPlaneVer
        managed object property"
    ::= { cucsEquipmentSecurityUnitCapProviderEntry 11 }

cucsEquipmentSecurityUnitCapProviderModel OBJECT-TYPE
    SYNTAX       SnmpAdminString
    MAX-ACCESS   read-only
    STATUS       current
    DESCRIPTION
        "Cisco UCS equipment:SecurityUnitCapProvider:model
        managed object property"
    ::= { cucsEquipmentSecurityUnitCapProviderEntry 12 }

cucsEquipmentSecurityUnitCapProviderPromCardType OBJECT-TYPE
    SYNTAX       Gauge32
    MAX-ACCESS   read-only
    STATUS       current
    DESCRIPTION
        "Cisco UCS equipment:SecurityUnitCapProvider:promCardType
        managed object property"
    ::= { cucsEquipmentSecurityUnitCapProviderEntry 13 }

cucsEquipmentSecurityUnitCapProviderRevision OBJECT-TYPE
    SYNTAX       SnmpAdminString
    MAX-ACCESS   read-only
    STATUS       current
    DESCRIPTION
        "Cisco UCS equipment:SecurityUnitCapProvider:revision
        managed object property"
    ::= { cucsEquipmentSecurityUnitCapProviderEntry 14 }

cucsEquipmentSecurityUnitCapProviderVendor OBJECT-TYPE
    SYNTAX       SnmpAdminString
    MAX-ACCESS   read-only
    STATUS       current
    DESCRIPTION
        "Cisco UCS equipment:SecurityUnitCapProvider:vendor
        managed object property"
    ::= { cucsEquipmentSecurityUnitCapProviderEntry 15 }

cucsEquipmentServerCorrectUuidBehaviorTable OBJECT-TYPE
    SYNTAX           SEQUENCE OF CucsEquipmentServerCorrectUuidBehaviorEntry
    MAX-ACCESS       not-accessible
    STATUS           current
    DESCRIPTION
        "Cisco UCS equipment:ServerCorrectUuidBehavior
        managed object table"
    ::= { cucsEquipmentObjects 176 }

cucsEquipmentServerCorrectUuidBehaviorEntry OBJECT-TYPE
    SYNTAX           CucsEquipmentServerCorrectUuidBehaviorEntry
    MAX-ACCESS       not-accessible
    STATUS           current
    DESCRIPTION
        "Entry for the cucsEquipmentServerCorrectUuidBehaviorTable table."
    INDEX { cucsEquipmentServerCorrectUuidBehaviorInstanceId }
    ::= { cucsEquipmentServerCorrectUuidBehaviorTable 1 }

CucsEquipmentServerCorrectUuidBehaviorEntry ::= SEQUENCE {
    cucsEquipmentServerCorrectUuidBehaviorInstanceId                 CucsManagedObjectId,
    cucsEquipmentServerCorrectUuidBehaviorDn                         CucsManagedObjectDn,
    cucsEquipmentServerCorrectUuidBehaviorRn                         SnmpAdminString
}

cucsEquipmentServerCorrectUuidBehaviorInstanceId OBJECT-TYPE
    SYNTAX       CucsManagedObjectId
    MAX-ACCESS   not-accessible
    STATUS       current
    DESCRIPTION
        "Instance identifier of the managed object."
    ::= { cucsEquipmentServerCorrectUuidBehaviorEntry 1 }

cucsEquipmentServerCorrectUuidBehaviorDn OBJECT-TYPE
    SYNTAX       CucsManagedObjectDn
    MAX-ACCESS   read-only
    STATUS       current
    DESCRIPTION
        "Cisco UCS equipment:ServerCorrectUuidBehavior:dn
        managed object property"
    ::= { cucsEquipmentServerCorrectUuidBehaviorEntry 2 }

cucsEquipmentServerCorrectUuidBehaviorRn OBJECT-TYPE
    SYNTAX       SnmpAdminString
    MAX-ACCESS   read-only
    STATUS       current
    DESCRIPTION
        "Cisco UCS equipment:ServerCorrectUuidBehavior:rn
        managed object property"
    ::= { cucsEquipmentServerCorrectUuidBehaviorEntry 3 }

cucsEquipmentServerFeatureCapTable OBJECT-TYPE
    SYNTAX           SEQUENCE OF CucsEquipmentServerFeatureCapEntry
    MAX-ACCESS       not-accessible
    STATUS           current
    DESCRIPTION
        "Cisco UCS equipment:ServerFeatureCap managed object table"
    ::= { cucsEquipmentObjects 102 }

cucsEquipmentServerFeatureCapEntry OBJECT-TYPE
    SYNTAX           CucsEquipmentServerFeatureCapEntry
    MAX-ACCESS       not-accessible
    STATUS           current
    DESCRIPTION
        "Entry for the cucsEquipmentServerFeatureCapTable table."
    INDEX { cucsEquipmentServerFeatureCapInstanceId }
    ::= { cucsEquipmentServerFeatureCapTable 1 }

CucsEquipmentServerFeatureCapEntry ::= SEQUENCE {
    cucsEquipmentServerFeatureCapInstanceId                          CucsManagedObjectId,
    cucsEquipmentServerFeatureCapDn                                  CucsManagedObjectDn,
    cucsEquipmentServerFeatureCapRn                                  SnmpAdminString,
    cucsEquipmentServerFeatureCapCmosResetSupported                  TruthValue,
    cucsEquipmentServerFeatureCapMaxVirtualDrivesPerServer           Gauge32,
    cucsEquipmentServerFeatureCapStorageJbodModeSupported            TruthValue,
    cucsEquipmentServerFeatureCapNumberOfServerUnits                 Gauge32,
    cucsEquipmentServerFeatureCapAdaptorModel                        SnmpAdminString,
    cucsEquipmentServerFeatureCapMaxVirtualEthIfPerServer            Gauge32
}

cucsEquipmentServerFeatureCapInstanceId OBJECT-TYPE
    SYNTAX       CucsManagedObjectId
    MAX-ACCESS   not-accessible
    STATUS       current
    DESCRIPTION
        "Instance identifier of the managed object."
    ::= { cucsEquipmentServerFeatureCapEntry 1 }

cucsEquipmentServerFeatureCapDn OBJECT-TYPE
    SYNTAX       CucsManagedObjectDn
    MAX-ACCESS   read-only
    STATUS       current
    DESCRIPTION
        "Cisco UCS equipment:ServerFeatureCap:dn managed object property"
    ::= { cucsEquipmentServerFeatureCapEntry 2 }

cucsEquipmentServerFeatureCapRn OBJECT-TYPE
    SYNTAX       SnmpAdminString
    MAX-ACCESS   read-only
    STATUS       current
    DESCRIPTION
        "Cisco UCS equipment:ServerFeatureCap:rn managed object property"
    ::= { cucsEquipmentServerFeatureCapEntry 3 }

cucsEquipmentServerFeatureCapCmosResetSupported OBJECT-TYPE
    SYNTAX       TruthValue
    MAX-ACCESS   read-only
    STATUS       current
    DESCRIPTION
        "Cisco UCS equipment:ServerFeatureCap:cmosResetSupported
        managed object property"
    ::= { cucsEquipmentServerFeatureCapEntry 4 }

cucsEquipmentServerFeatureCapMaxVirtualDrivesPerServer OBJECT-TYPE
    SYNTAX       Gauge32
    MAX-ACCESS   read-only
    STATUS       current
    DESCRIPTION
        "Cisco UCS equipment:ServerFeatureCap:maxVirtualDrivesPerServer
        managed object property"
    ::= { cucsEquipmentServerFeatureCapEntry 5 }

cucsEquipmentServerFeatureCapStorageJbodModeSupported OBJECT-TYPE
    SYNTAX       TruthValue
    MAX-ACCESS   read-only
    STATUS       current
    DESCRIPTION
        "Cisco UCS equipment:ServerFeatureCap:storageJbodModeSupported
        managed object property"
    ::= { cucsEquipmentServerFeatureCapEntry 6 }

cucsEquipmentServerFeatureCapNumberOfServerUnits OBJECT-TYPE
    SYNTAX       Gauge32
    MAX-ACCESS   read-only
    STATUS       current
    DESCRIPTION
        "Cisco UCS equipment:ServerFeatureCap:numberOfServerUnits
        managed object property"
    ::= { cucsEquipmentServerFeatureCapEntry 7 }

cucsEquipmentServerFeatureCapAdaptorModel OBJECT-TYPE
    SYNTAX       SnmpAdminString
    MAX-ACCESS   read-only
    STATUS       current
    DESCRIPTION
        "Cisco UCS equipment:ServerFeatureCap:adaptorModel
        managed object property"
    ::= { cucsEquipmentServerFeatureCapEntry 8 }

cucsEquipmentServerFeatureCapMaxVirtualEthIfPerServer OBJECT-TYPE
    SYNTAX       Gauge32
    MAX-ACCESS   read-only
    STATUS       current
    DESCRIPTION
        "Cisco UCS equipment:ServerFeatureCap:maxVirtualEthIfPerServer
        managed object property"
    ::= { cucsEquipmentServerFeatureCapEntry 9 }

cucsEquipmentServerPortCapProviderTable OBJECT-TYPE
    SYNTAX           SEQUENCE OF CucsEquipmentServerPortCapProviderEntry
    MAX-ACCESS       not-accessible
    STATUS           current
    DESCRIPTION
        "Cisco UCS equipment:ServerPortCapProvider managed object table"
    ::= { cucsEquipmentObjects 169 }

cucsEquipmentServerPortCapProviderEntry OBJECT-TYPE
    SYNTAX           CucsEquipmentServerPortCapProviderEntry
    MAX-ACCESS       not-accessible
    STATUS           current
    DESCRIPTION
        "Entry for the cucsEquipmentServerPortCapProviderTable table."
    INDEX { cucsEquipmentServerPortCapProviderInstanceId }
    ::= { cucsEquipmentServerPortCapProviderTable 1 }

CucsEquipmentServerPortCapProviderEntry ::= SEQUENCE {
    cucsEquipmentServerPortCapProviderInstanceId                     CucsManagedObjectId,
    cucsEquipmentServerPortCapProviderDn                             CucsManagedObjectDn,
    cucsEquipmentServerPortCapProviderRn                             SnmpAdminString,
    cucsEquipmentServerPortCapProviderDescr                          SnmpAdminString,
    cucsEquipmentServerPortCapProviderEndPortId                      Gauge32,
    cucsEquipmentServerPortCapProviderIntId                          SnmpAdminString,
    cucsEquipmentServerPortCapProviderName                           SnmpAdminString,
    cucsEquipmentServerPortCapProviderPolicyLevel                    Gauge32,
    cucsEquipmentServerPortCapProviderPolicyOwner                    CucsPolicyPolicyOwner,
    cucsEquipmentServerPortCapProviderStartPortId                    Gauge32
}

cucsEquipmentServerPortCapProviderInstanceId OBJECT-TYPE
    SYNTAX       CucsManagedObjectId
    MAX-ACCESS   not-accessible
    STATUS       current
    DESCRIPTION
        "Instance identifier of the managed object."
    ::= { cucsEquipmentServerPortCapProviderEntry 1 }

cucsEquipmentServerPortCapProviderDn OBJECT-TYPE
    SYNTAX       CucsManagedObjectDn
    MAX-ACCESS   read-only
    STATUS       current
    DESCRIPTION
        "Cisco UCS equipment:ServerPortCapProvider:dn managed
        object property"
    ::= { cucsEquipmentServerPortCapProviderEntry 2 }

cucsEquipmentServerPortCapProviderRn OBJECT-TYPE
    SYNTAX       SnmpAdminString
    MAX-ACCESS   read-only
    STATUS       current
    DESCRIPTION
        "Cisco UCS equipment:ServerPortCapProvider:rn managed
        object property"
    ::= { cucsEquipmentServerPortCapProviderEntry 3 }

cucsEquipmentServerPortCapProviderDescr OBJECT-TYPE
    SYNTAX       SnmpAdminString
    MAX-ACCESS   read-only
    STATUS       current
    DESCRIPTION
        "Cisco UCS equipment:ServerPortCapProvider:descr
        managed object property"
    ::= { cucsEquipmentServerPortCapProviderEntry 4 }

cucsEquipmentServerPortCapProviderEndPortId OBJECT-TYPE
    SYNTAX       Gauge32
    MAX-ACCESS   read-only
    STATUS       current
    DESCRIPTION
        "Cisco UCS equipment:ServerPortCapProvider:endPortId
        managed object property"
    ::= { cucsEquipmentServerPortCapProviderEntry 5 }

cucsEquipmentServerPortCapProviderIntId OBJECT-TYPE
    SYNTAX       SnmpAdminString
    MAX-ACCESS   read-only
    STATUS       current
    DESCRIPTION
        "Cisco UCS equipment:ServerPortCapProvider:intId
        managed object property"
    ::= { cucsEquipmentServerPortCapProviderEntry 6 }

cucsEquipmentServerPortCapProviderName OBJECT-TYPE
    SYNTAX       SnmpAdminString
    MAX-ACCESS   read-only
    STATUS       current
    DESCRIPTION
        "Cisco UCS equipment:ServerPortCapProvider:name
        managed object property"
    ::= { cucsEquipmentServerPortCapProviderEntry 7 }

cucsEquipmentServerPortCapProviderPolicyLevel OBJECT-TYPE
    SYNTAX       Gauge32
    MAX-ACCESS   read-only
    STATUS       current
    DESCRIPTION
        "Cisco UCS equipment:ServerPortCapProvider:policyLevel
        managed object property"
    ::= { cucsEquipmentServerPortCapProviderEntry 8 }

cucsEquipmentServerPortCapProviderPolicyOwner OBJECT-TYPE
    SYNTAX       CucsPolicyPolicyOwner
    MAX-ACCESS   read-only
    STATUS       current
    DESCRIPTION
        "Cisco UCS equipment:ServerPortCapProvider:policyOwner
        managed object property"
    ::= { cucsEquipmentServerPortCapProviderEntry 9 }

cucsEquipmentServerPortCapProviderStartPortId OBJECT-TYPE
    SYNTAX       Gauge32
    MAX-ACCESS   read-only
    STATUS       current
    DESCRIPTION
        "Cisco UCS equipment:ServerPortCapProvider:startPortId
        managed object property"
    ::= { cucsEquipmentServerPortCapProviderEntry 10 }

cucsEquipmentServerUnitCapProviderTable OBJECT-TYPE
    SYNTAX           SEQUENCE OF CucsEquipmentServerUnitCapProviderEntry
    MAX-ACCESS       not-accessible
    STATUS           current
    DESCRIPTION
        "Cisco UCS equipment:ServerUnitCapProvider managed object table"
    ::= { cucsEquipmentObjects 151 }

cucsEquipmentServerUnitCapProviderEntry OBJECT-TYPE
    SYNTAX           CucsEquipmentServerUnitCapProviderEntry
    MAX-ACCESS       not-accessible
    STATUS           current
    DESCRIPTION
        "Entry for the cucsEquipmentServerUnitCapProviderTable table."
    INDEX { cucsEquipmentServerUnitCapProviderInstanceId }
    ::= { cucsEquipmentServerUnitCapProviderTable 1 }

CucsEquipmentServerUnitCapProviderEntry ::= SEQUENCE {
    cucsEquipmentServerUnitCapProviderInstanceId                     CucsManagedObjectId,
    cucsEquipmentServerUnitCapProviderDn                             CucsManagedObjectDn,
    cucsEquipmentServerUnitCapProviderRn                             SnmpAdminString,
    cucsEquipmentServerUnitCapProviderDeleted                        TruthValue,
    cucsEquipmentServerUnitCapProviderDeprecated                     TruthValue,
    cucsEquipmentServerUnitCapProviderElementLoadFailures            Gauge32,
    cucsEquipmentServerUnitCapProviderElementsLoaded                 Gauge32,
    cucsEquipmentServerUnitCapProviderGencount                       Gauge32,
    cucsEquipmentServerUnitCapProviderLoadErrors                     Gauge32,
    cucsEquipmentServerUnitCapProviderLoadWarnings                   Gauge32,
    cucsEquipmentServerUnitCapProviderMaxLocalDisks                  Gauge32,
    cucsEquipmentServerUnitCapProviderMgmtPlaneVer                   SnmpAdminString,
    cucsEquipmentServerUnitCapProviderModel                          SnmpAdminString,
    cucsEquipmentServerUnitCapProviderPromCardType                   Gauge32,
    cucsEquipmentServerUnitCapProviderRevision                       SnmpAdminString,
    cucsEquipmentServerUnitCapProviderVendor                         SnmpAdminString
}

cucsEquipmentServerUnitCapProviderInstanceId OBJECT-TYPE
    SYNTAX       CucsManagedObjectId
    MAX-ACCESS   not-accessible
    STATUS       current
    DESCRIPTION
        "Instance identifier of the managed object."
    ::= { cucsEquipmentServerUnitCapProviderEntry 1 }

cucsEquipmentServerUnitCapProviderDn OBJECT-TYPE
    SYNTAX       CucsManagedObjectDn
    MAX-ACCESS   read-only
    STATUS       current
    DESCRIPTION
        "Cisco UCS equipment:ServerUnitCapProvider:dn managed
        object property"
    ::= { cucsEquipmentServerUnitCapProviderEntry 2 }

cucsEquipmentServerUnitCapProviderRn OBJECT-TYPE
    SYNTAX       SnmpAdminString
    MAX-ACCESS   read-only
    STATUS       current
    DESCRIPTION
        "Cisco UCS equipment:ServerUnitCapProvider:rn managed
        object property"
    ::= { cucsEquipmentServerUnitCapProviderEntry 3 }

cucsEquipmentServerUnitCapProviderDeleted OBJECT-TYPE
    SYNTAX       TruthValue
    MAX-ACCESS   read-only
    STATUS       current
    DESCRIPTION
        "Cisco UCS equipment:ServerUnitCapProvider:deleted
        managed object property"
    ::= { cucsEquipmentServerUnitCapProviderEntry 4 }

cucsEquipmentServerUnitCapProviderDeprecated OBJECT-TYPE
    SYNTAX       TruthValue
    MAX-ACCESS   read-only
    STATUS       current
    DESCRIPTION
        "Cisco UCS equipment:ServerUnitCapProvider:deprecated
        managed object property"
    ::= { cucsEquipmentServerUnitCapProviderEntry 5 }

cucsEquipmentServerUnitCapProviderElementLoadFailures OBJECT-TYPE
    SYNTAX       Gauge32
    MAX-ACCESS   read-only
    STATUS       current
    DESCRIPTION
        "Cisco UCS equipment:ServerUnitCapProvider:elementLoadFailures
        managed object property"
    ::= { cucsEquipmentServerUnitCapProviderEntry 6 }

cucsEquipmentServerUnitCapProviderElementsLoaded OBJECT-TYPE
    SYNTAX       Gauge32
    MAX-ACCESS   read-only
    STATUS       current
    DESCRIPTION
        "Cisco UCS equipment:ServerUnitCapProvider:elementsLoaded
        managed object property"
    ::= { cucsEquipmentServerUnitCapProviderEntry 7 }

cucsEquipmentServerUnitCapProviderGencount OBJECT-TYPE
    SYNTAX       Gauge32
    MAX-ACCESS   read-only
    STATUS       current
    DESCRIPTION
        "Cisco UCS equipment:ServerUnitCapProvider:gencount
        managed object property"
    ::= { cucsEquipmentServerUnitCapProviderEntry 8 }

cucsEquipmentServerUnitCapProviderLoadErrors OBJECT-TYPE
    SYNTAX       Gauge32
    MAX-ACCESS   read-only
    STATUS       current
    DESCRIPTION
        "Cisco UCS equipment:ServerUnitCapProvider:loadErrors
        managed object property"
    ::= { cucsEquipmentServerUnitCapProviderEntry 9 }

cucsEquipmentServerUnitCapProviderLoadWarnings OBJECT-TYPE
    SYNTAX       Gauge32
    MAX-ACCESS   read-only
    STATUS       current
    DESCRIPTION
        "Cisco UCS equipment:ServerUnitCapProvider:loadWarnings
        managed object property"
    ::= { cucsEquipmentServerUnitCapProviderEntry 10 }

cucsEquipmentServerUnitCapProviderMaxLocalDisks OBJECT-TYPE
    SYNTAX       Gauge32
    MAX-ACCESS   read-only
    STATUS       current
    DESCRIPTION
        "Cisco UCS equipment:ServerUnitCapProvider:maxLocalDisks
        managed object property"
    ::= { cucsEquipmentServerUnitCapProviderEntry 11 }

cucsEquipmentServerUnitCapProviderMgmtPlaneVer OBJECT-TYPE
    SYNTAX       SnmpAdminString
    MAX-ACCESS   read-only
    STATUS       current
    DESCRIPTION
        "Cisco UCS equipment:ServerUnitCapProvider:mgmtPlaneVer
        managed object property"
    ::= { cucsEquipmentServerUnitCapProviderEntry 12 }

cucsEquipmentServerUnitCapProviderModel OBJECT-TYPE
    SYNTAX       SnmpAdminString
    MAX-ACCESS   read-only
    STATUS       current
    DESCRIPTION
        "Cisco UCS equipment:ServerUnitCapProvider:model
        managed object property"
    ::= { cucsEquipmentServerUnitCapProviderEntry 13 }

cucsEquipmentServerUnitCapProviderPromCardType OBJECT-TYPE
    SYNTAX       Gauge32
    MAX-ACCESS   read-only
    STATUS       current
    DESCRIPTION
        "Cisco UCS equipment:ServerUnitCapProvider:promCardType
        managed object property"
    ::= { cucsEquipmentServerUnitCapProviderEntry 14 }

cucsEquipmentServerUnitCapProviderRevision OBJECT-TYPE
    SYNTAX       SnmpAdminString
    MAX-ACCESS   read-only
    STATUS       current
    DESCRIPTION
        "Cisco UCS equipment:ServerUnitCapProvider:revision
        managed object property"
    ::= { cucsEquipmentServerUnitCapProviderEntry 15 }

cucsEquipmentServerUnitCapProviderVendor OBJECT-TYPE
    SYNTAX       SnmpAdminString
    MAX-ACCESS   read-only
    STATUS       current
    DESCRIPTION
        "Cisco UCS equipment:ServerUnitCapProvider:vendor
        managed object property"
    ::= { cucsEquipmentServerUnitCapProviderEntry 16 }

cucsEquipmentServiceDefTable OBJECT-TYPE
    SYNTAX           SEQUENCE OF CucsEquipmentServiceDefEntry
    MAX-ACCESS       not-accessible
    STATUS           current
    DESCRIPTION
        "Cisco UCS equipment:ServiceDef managed object table"
    ::= { cucsEquipmentObjects 65 }

cucsEquipmentServiceDefEntry OBJECT-TYPE
    SYNTAX           CucsEquipmentServiceDefEntry
    MAX-ACCESS       not-accessible
    STATUS           current
    DESCRIPTION
        "Entry for the cucsEquipmentServiceDefTable table."
    INDEX { cucsEquipmentServiceDefInstanceId }
    ::= { cucsEquipmentServiceDefTable 1 }

CucsEquipmentServiceDefEntry ::= SEQUENCE {
    cucsEquipmentServiceDefInstanceId                                CucsManagedObjectId,
    cucsEquipmentServiceDefDn                                        CucsManagedObjectDn,
    cucsEquipmentServiceDefRn                                        SnmpAdminString,
    cucsEquipmentServiceDefCanBeFRUed                                TruthValue,
    cucsEquipmentServiceDefDescr                                     SnmpAdminString,
    cucsEquipmentServiceDefIntId                                     SnmpAdminString,
    cucsEquipmentServiceDefName                                      SnmpAdminString,
    cucsEquipmentServiceDefRemovalConditions                         CucsEquipmentRemovalConditions,
    cucsEquipmentServiceDefServicePhilosophy                         SnmpAdminString,
    cucsEquipmentServiceDefPolicyLevel                               Gauge32,
    cucsEquipmentServiceDefPolicyOwner                               CucsPolicyPolicyOwner
}

cucsEquipmentServiceDefInstanceId OBJECT-TYPE
    SYNTAX       CucsManagedObjectId
    MAX-ACCESS   not-accessible
    STATUS       current
    DESCRIPTION
        "Instance identifier of the managed object."
    ::= { cucsEquipmentServiceDefEntry 1 }

cucsEquipmentServiceDefDn OBJECT-TYPE
    SYNTAX       CucsManagedObjectDn
    MAX-ACCESS   read-only
    STATUS       current
    DESCRIPTION
        "Cisco UCS equipment:ServiceDef:dn managed object property"
    ::= { cucsEquipmentServiceDefEntry 2 }

cucsEquipmentServiceDefRn OBJECT-TYPE
    SYNTAX       SnmpAdminString
    MAX-ACCESS   read-only
    STATUS       current
    DESCRIPTION
        "Cisco UCS equipment:ServiceDef:rn managed object property"
    ::= { cucsEquipmentServiceDefEntry 3 }

cucsEquipmentServiceDefCanBeFRUed OBJECT-TYPE
    SYNTAX       TruthValue
    MAX-ACCESS   read-only
    STATUS       current
    DESCRIPTION
        "Cisco UCS equipment:ServiceDef:canBeFRUed managed
        object property"
    ::= { cucsEquipmentServiceDefEntry 4 }

cucsEquipmentServiceDefDescr OBJECT-TYPE
    SYNTAX       SnmpAdminString
    MAX-ACCESS   read-only
    STATUS       current
    DESCRIPTION
        "Cisco UCS equipment:ServiceDef:descr managed object property"
    ::= { cucsEquipmentServiceDefEntry 5 }

cucsEquipmentServiceDefIntId OBJECT-TYPE
    SYNTAX       SnmpAdminString
    MAX-ACCESS   read-only
    STATUS       current
    DESCRIPTION
        "Cisco UCS equipment:ServiceDef:intId managed object property"
    ::= { cucsEquipmentServiceDefEntry 6 }

cucsEquipmentServiceDefName OBJECT-TYPE
    SYNTAX       SnmpAdminString
    MAX-ACCESS   read-only
    STATUS       current
    DESCRIPTION
        "Cisco UCS equipment:ServiceDef:name managed object property"
    ::= { cucsEquipmentServiceDefEntry 7 }

cucsEquipmentServiceDefRemovalConditions OBJECT-TYPE
    SYNTAX       CucsEquipmentRemovalConditions
    MAX-ACCESS   read-only
    STATUS       current
    DESCRIPTION
        "Cisco UCS equipment:ServiceDef:removalConditions
        managed object property"
    ::= { cucsEquipmentServiceDefEntry 8 }

cucsEquipmentServiceDefServicePhilosophy OBJECT-TYPE
    SYNTAX       SnmpAdminString
    MAX-ACCESS   read-only
    STATUS       current
    DESCRIPTION
        "Cisco UCS equipment:ServiceDef:servicePhilosophy
        managed object property"
    ::= { cucsEquipmentServiceDefEntry 9 }

cucsEquipmentServiceDefPolicyLevel OBJECT-TYPE
    SYNTAX       Gauge32
    MAX-ACCESS   read-only
    STATUS       current
    DESCRIPTION
        "Cisco UCS equipment:ServiceDef:policyLevel managed
        object property"
    ::= { cucsEquipmentServiceDefEntry 10 }

cucsEquipmentServiceDefPolicyOwner OBJECT-TYPE
    SYNTAX       CucsPolicyPolicyOwner
    MAX-ACCESS   read-only
    STATUS       current
    DESCRIPTION
        "Cisco UCS equipment:ServiceDef:policyOwner managed
        object property"
    ::= { cucsEquipmentServiceDefEntry 11 }

cucsEquipmentSharedIOModuleTable OBJECT-TYPE
    SYNTAX           SEQUENCE OF CucsEquipmentSharedIOModuleEntry
    MAX-ACCESS       not-accessible
    STATUS           current
    DESCRIPTION
        "Cisco UCS equipment:SharedIOModule managed object table"
    ::= { cucsEquipmentObjects 152 }

cucsEquipmentSharedIOModuleEntry OBJECT-TYPE
    SYNTAX           CucsEquipmentSharedIOModuleEntry
    MAX-ACCESS       not-accessible
    STATUS           current
    DESCRIPTION
        "Entry for the cucsEquipmentSharedIOModuleTable table."
    INDEX { cucsEquipmentSharedIOModuleInstanceId }
    ::= { cucsEquipmentSharedIOModuleTable 1 }

CucsEquipmentSharedIOModuleEntry ::= SEQUENCE {
    cucsEquipmentSharedIOModuleInstanceId                            CucsManagedObjectId,
    cucsEquipmentSharedIOModuleDn                                    CucsManagedObjectDn,
    cucsEquipmentSharedIOModuleRn                                    SnmpAdminString,
    cucsEquipmentSharedIOModuleAdminPowerState                       CucsEquipmentAdminPowerState,
    cucsEquipmentSharedIOModuleBaseAddr                              InetAddressIPv4,
    cucsEquipmentSharedIOModuleChassisId                             Gauge32,
    cucsEquipmentSharedIOModuleCheckPoint                            CucsComputeCheckPoint,
    cucsEquipmentSharedIOModuleConfigState                           CucsEquipmentChassisConfigState,
    cucsEquipmentSharedIOModuleDiscovery                             CucsEquipmentDiscoveryState,
    cucsEquipmentSharedIOModuleFeOfflineTs                           Unsigned64,
    cucsEquipmentSharedIOModuleFeReadyTs                             Unsigned64,
    cucsEquipmentSharedIOModuleFltAggr                               Unsigned64,
    cucsEquipmentSharedIOModuleId                                    CucsEquipmentSharedIOModuleId,
    cucsEquipmentSharedIOModuleLcName                                SnmpAdminString,
    cucsEquipmentSharedIOModuleLcTs                                  DateAndTime,
    cucsEquipmentSharedIOModuleMacOfSharedIOMA                       MacAddress,
    cucsEquipmentSharedIOModuleMacOfSharedIOMB                       MacAddress,
    cucsEquipmentSharedIOModuleManagingInstance                      CucsNetworkSwitchId,
    cucsEquipmentSharedIOModuleMfgTime                               DateAndTime,
    cucsEquipmentSharedIOModuleModel                                 SnmpAdminString,
    cucsEquipmentSharedIOModuleOperQualifier                         CucsEquipmentIOCardIssues,
    cucsEquipmentSharedIOModuleOperQualifierReason                   SnmpAdminString,
    cucsEquipmentSharedIOModuleOperState                             CucsEquipmentOperability,
    cucsEquipmentSharedIOModuleOperability                           CucsEquipmentOperability,
    cucsEquipmentSharedIOModulePartNumber                            SnmpAdminString,
    cucsEquipmentSharedIOModulePeerDn                                SnmpAdminString,
    cucsEquipmentSharedIOModulePerf                                  CucsEquipmentSensorThresholdStatus,
    cucsEquipmentSharedIOModulePower                                 CucsEquipmentPowerState,
    cucsEquipmentSharedIOModulePresence                              CucsEquipmentPresence,
    cucsEquipmentSharedIOModuleReachability                          CucsAdaptorReachability,
    cucsEquipmentSharedIOModuleRevision                              SnmpAdminString,
    cucsEquipmentSharedIOModuleSerial                                SnmpAdminString,
    cucsEquipmentSharedIOModuleThermal                               CucsEquipmentSensorThresholdStatus,
    cucsEquipmentSharedIOModuleUpgradeStatus                         CucsMgmtUpgradeStatus,
    cucsEquipmentSharedIOModuleUsrLbl                                SnmpAdminString,
    cucsEquipmentSharedIOModuleVendor                                SnmpAdminString,
    cucsEquipmentSharedIOModuleVid                                   SnmpAdminString,
    cucsEquipmentSharedIOModuleVoltage                               CucsEquipmentSensorThresholdStatus,
    cucsEquipmentSharedIOModuleAssetTag                              SnmpAdminString
}

cucsEquipmentSharedIOModuleInstanceId OBJECT-TYPE
    SYNTAX       CucsManagedObjectId
    MAX-ACCESS   not-accessible
    STATUS       current
    DESCRIPTION
        "Instance identifier of the managed object."
    ::= { cucsEquipmentSharedIOModuleEntry 1 }

cucsEquipmentSharedIOModuleDn OBJECT-TYPE
    SYNTAX       CucsManagedObjectDn
    MAX-ACCESS   read-only
    STATUS       current
    DESCRIPTION
        "Cisco UCS equipment:SharedIOModule:dn managed object property"
    ::= { cucsEquipmentSharedIOModuleEntry 2 }

cucsEquipmentSharedIOModuleRn OBJECT-TYPE
    SYNTAX       SnmpAdminString
    MAX-ACCESS   read-only
    STATUS       current
    DESCRIPTION
        "Cisco UCS equipment:SharedIOModule:rn managed object property"
    ::= { cucsEquipmentSharedIOModuleEntry 3 }

cucsEquipmentSharedIOModuleAdminPowerState OBJECT-TYPE
    SYNTAX       CucsEquipmentAdminPowerState
    MAX-ACCESS   read-only
    STATUS       current
    DESCRIPTION
        "Cisco UCS equipment:SharedIOModule:adminPowerState
        managed object property"
    ::= { cucsEquipmentSharedIOModuleEntry 4 }

cucsEquipmentSharedIOModuleBaseAddr OBJECT-TYPE
    SYNTAX       InetAddressIPv4
    MAX-ACCESS   read-only
    STATUS       current
    DESCRIPTION
        "Cisco UCS equipment:SharedIOModule:baseAddr managed
        object property"
    ::= { cucsEquipmentSharedIOModuleEntry 5 }

cucsEquipmentSharedIOModuleChassisId OBJECT-TYPE
    SYNTAX       Gauge32
    MAX-ACCESS   read-only
    STATUS       current
    DESCRIPTION
        "Cisco UCS equipment:SharedIOModule:chassisId managed
        object property"
    ::= { cucsEquipmentSharedIOModuleEntry 6 }

cucsEquipmentSharedIOModuleCheckPoint OBJECT-TYPE
    SYNTAX       CucsComputeCheckPoint
    MAX-ACCESS   read-only
    STATUS       current
    DESCRIPTION
        "Cisco UCS equipment:SharedIOModule:checkPoint
        managed object property"
    ::= { cucsEquipmentSharedIOModuleEntry 7 }

cucsEquipmentSharedIOModuleConfigState OBJECT-TYPE
    SYNTAX       CucsEquipmentChassisConfigState
    MAX-ACCESS   read-only
    STATUS       current
    DESCRIPTION
        "Cisco UCS equipment:SharedIOModule:configState
        managed object property"
    ::= { cucsEquipmentSharedIOModuleEntry 8 }

cucsEquipmentSharedIOModuleDiscovery OBJECT-TYPE
    SYNTAX       CucsEquipmentDiscoveryState
    MAX-ACCESS   read-only
    STATUS       current
    DESCRIPTION
        "Cisco UCS equipment:SharedIOModule:discovery managed
        object property"
    ::= { cucsEquipmentSharedIOModuleEntry 9 }

cucsEquipmentSharedIOModuleFeOfflineTs OBJECT-TYPE
    SYNTAX       Unsigned64
    MAX-ACCESS   read-only
    STATUS       current
    DESCRIPTION
        "Cisco UCS equipment:SharedIOModule:feOfflineTs
        managed object property"
    ::= { cucsEquipmentSharedIOModuleEntry 10 }

cucsEquipmentSharedIOModuleFeReadyTs OBJECT-TYPE
    SYNTAX       Unsigned64
    MAX-ACCESS   read-only
    STATUS       current
    DESCRIPTION
        "Cisco UCS equipment:SharedIOModule:feReadyTs managed
        object property"
    ::= { cucsEquipmentSharedIOModuleEntry 11 }

cucsEquipmentSharedIOModuleFltAggr OBJECT-TYPE
    SYNTAX       Unsigned64
    MAX-ACCESS   read-only
    STATUS       current
    DESCRIPTION
        "Cisco UCS equipment:SharedIOModule:fltAggr managed
        object property"
    ::= { cucsEquipmentSharedIOModuleEntry 12 }

cucsEquipmentSharedIOModuleId OBJECT-TYPE
    SYNTAX       CucsEquipmentSharedIOModuleId
    MAX-ACCESS   read-only
    STATUS       current
    DESCRIPTION
        "Cisco UCS equipment:SharedIOModule:id managed object property"
    ::= { cucsEquipmentSharedIOModuleEntry 13 }

cucsEquipmentSharedIOModuleLcName OBJECT-TYPE
    SYNTAX       SnmpAdminString
    MAX-ACCESS   read-only
    STATUS       current
    DESCRIPTION
        "Cisco UCS equipment:SharedIOModule:lcName managed
        object property"
    ::= { cucsEquipmentSharedIOModuleEntry 14 }

cucsEquipmentSharedIOModuleLcTs OBJECT-TYPE
    SYNTAX       DateAndTime
    MAX-ACCESS   read-only
    STATUS       current
    DESCRIPTION
        "Cisco UCS equipment:SharedIOModule:lcTs managed object property"
    ::= { cucsEquipmentSharedIOModuleEntry 15 }

cucsEquipmentSharedIOModuleMacOfSharedIOMA OBJECT-TYPE
    SYNTAX       MacAddress
    MAX-ACCESS   read-only
    STATUS       current
    DESCRIPTION
        "Cisco UCS equipment:SharedIOModule:macOfSharedIOMA
        managed object property"
    ::= { cucsEquipmentSharedIOModuleEntry 16 }

cucsEquipmentSharedIOModuleMacOfSharedIOMB OBJECT-TYPE
    SYNTAX       MacAddress
    MAX-ACCESS   read-only
    STATUS       current
    DESCRIPTION
        "Cisco UCS equipment:SharedIOModule:macOfSharedIOMB
        managed object property"
    ::= { cucsEquipmentSharedIOModuleEntry 17 }

cucsEquipmentSharedIOModuleManagingInstance OBJECT-TYPE
    SYNTAX       CucsNetworkSwitchId
    MAX-ACCESS   read-only
    STATUS       current
    DESCRIPTION
        "Cisco UCS equipment:SharedIOModule:managingInstance
        managed object property"
    ::= { cucsEquipmentSharedIOModuleEntry 18 }

cucsEquipmentSharedIOModuleMfgTime OBJECT-TYPE
    SYNTAX       DateAndTime
    MAX-ACCESS   read-only
    STATUS       current
    DESCRIPTION
        "Cisco UCS equipment:SharedIOModule:mfgTime managed
        object property"
    ::= { cucsEquipmentSharedIOModuleEntry 19 }

cucsEquipmentSharedIOModuleModel OBJECT-TYPE
    SYNTAX       SnmpAdminString
    MAX-ACCESS   read-only
    STATUS       current
    DESCRIPTION
        "Cisco UCS equipment:SharedIOModule:model managed object property"
    ::= { cucsEquipmentSharedIOModuleEntry 20 }

cucsEquipmentSharedIOModuleOperQualifier OBJECT-TYPE
    SYNTAX       CucsEquipmentIOCardIssues
    MAX-ACCESS   read-only
    STATUS       current
    DESCRIPTION
        "Cisco UCS equipment:SharedIOModule:operQualifier
        managed object property"
    ::= { cucsEquipmentSharedIOModuleEntry 21 }

cucsEquipmentSharedIOModuleOperQualifierReason OBJECT-TYPE
    SYNTAX       SnmpAdminString
    MAX-ACCESS   read-only
    STATUS       current
    DESCRIPTION
        "Cisco UCS equipment:SharedIOModule:operQualifierReason
        managed object property"
    ::= { cucsEquipmentSharedIOModuleEntry 22 }

cucsEquipmentSharedIOModuleOperState OBJECT-TYPE
    SYNTAX       CucsEquipmentOperability
    MAX-ACCESS   read-only
    STATUS       current
    DESCRIPTION
        "Cisco UCS equipment:SharedIOModule:operState managed
        object property"
    ::= { cucsEquipmentSharedIOModuleEntry 23 }

cucsEquipmentSharedIOModuleOperability OBJECT-TYPE
    SYNTAX       CucsEquipmentOperability
    MAX-ACCESS   read-only
    STATUS       current
    DESCRIPTION
        "Cisco UCS equipment:SharedIOModule:operability
        managed object property"
    ::= { cucsEquipmentSharedIOModuleEntry 24 }

cucsEquipmentSharedIOModulePartNumber OBJECT-TYPE
    SYNTAX       SnmpAdminString
    MAX-ACCESS   read-only
    STATUS       current
    DESCRIPTION
        "Cisco UCS equipment:SharedIOModule:partNumber
        managed object property"
    ::= { cucsEquipmentSharedIOModuleEntry 25 }

cucsEquipmentSharedIOModulePeerDn OBJECT-TYPE
    SYNTAX       SnmpAdminString
    MAX-ACCESS   read-only
    STATUS       current
    DESCRIPTION
        "Cisco UCS equipment:SharedIOModule:peerDn managed
        object property"
    ::= { cucsEquipmentSharedIOModuleEntry 26 }

cucsEquipmentSharedIOModulePerf OBJECT-TYPE
    SYNTAX       CucsEquipmentSensorThresholdStatus
    MAX-ACCESS   read-only
    STATUS       current
    DESCRIPTION
        "Cisco UCS equipment:SharedIOModule:perf managed object property"
    ::= { cucsEquipmentSharedIOModuleEntry 27 }

cucsEquipmentSharedIOModulePower OBJECT-TYPE
    SYNTAX       CucsEquipmentPowerState
    MAX-ACCESS   read-only
    STATUS       current
    DESCRIPTION
        "Cisco UCS equipment:SharedIOModule:power managed object property"
    ::= { cucsEquipmentSharedIOModuleEntry 28 }

cucsEquipmentSharedIOModulePresence OBJECT-TYPE
    SYNTAX       CucsEquipmentPresence
    MAX-ACCESS   read-only
    STATUS       current
    DESCRIPTION
        "Cisco UCS equipment:SharedIOModule:presence managed
        object property"
    ::= { cucsEquipmentSharedIOModuleEntry 29 }

cucsEquipmentSharedIOModuleReachability OBJECT-TYPE
    SYNTAX       CucsAdaptorReachability
    MAX-ACCESS   read-only
    STATUS       current
    DESCRIPTION
        "Cisco UCS equipment:SharedIOModule:reachability
        managed object property"
    ::= { cucsEquipmentSharedIOModuleEntry 30 }

cucsEquipmentSharedIOModuleRevision OBJECT-TYPE
    SYNTAX       SnmpAdminString
    MAX-ACCESS   read-only
    STATUS       current
    DESCRIPTION
        "Cisco UCS equipment:SharedIOModule:revision managed
        object property"
    ::= { cucsEquipmentSharedIOModuleEntry 31 }

cucsEquipmentSharedIOModuleSerial OBJECT-TYPE
    SYNTAX       SnmpAdminString
    MAX-ACCESS   read-only
    STATUS       current
    DESCRIPTION
        "Cisco UCS equipment:SharedIOModule:serial managed
        object property"
    ::= { cucsEquipmentSharedIOModuleEntry 32 }

cucsEquipmentSharedIOModuleThermal OBJECT-TYPE
    SYNTAX       CucsEquipmentSensorThresholdStatus
    MAX-ACCESS   read-only
    STATUS       current
    DESCRIPTION
        "Cisco UCS equipment:SharedIOModule:thermal managed
        object property"
    ::= { cucsEquipmentSharedIOModuleEntry 33 }

cucsEquipmentSharedIOModuleUpgradeStatus OBJECT-TYPE
    SYNTAX       CucsMgmtUpgradeStatus
    MAX-ACCESS   read-only
    STATUS       current
    DESCRIPTION
        "Cisco UCS equipment:SharedIOModule:upgradeStatus
        managed object property"
    ::= { cucsEquipmentSharedIOModuleEntry 34 }

cucsEquipmentSharedIOModuleUsrLbl OBJECT-TYPE
    SYNTAX       SnmpAdminString
    MAX-ACCESS   read-only
    STATUS       current
    DESCRIPTION
        "Cisco UCS equipment:SharedIOModule:usrLbl managed
        object property"
    ::= { cucsEquipmentSharedIOModuleEntry 35 }

cucsEquipmentSharedIOModuleVendor OBJECT-TYPE
    SYNTAX       SnmpAdminString
    MAX-ACCESS   read-only
    STATUS       current
    DESCRIPTION
        "Cisco UCS equipment:SharedIOModule:vendor managed
        object property"
    ::= { cucsEquipmentSharedIOModuleEntry 36 }

cucsEquipmentSharedIOModuleVid OBJECT-TYPE
    SYNTAX       SnmpAdminString
    MAX-ACCESS   read-only
    STATUS       current
    DESCRIPTION
        "Cisco UCS equipment:SharedIOModule:vid managed object property"
    ::= { cucsEquipmentSharedIOModuleEntry 37 }

cucsEquipmentSharedIOModuleVoltage OBJECT-TYPE
    SYNTAX       CucsEquipmentSensorThresholdStatus
    MAX-ACCESS   read-only
    STATUS       current
    DESCRIPTION
        "Cisco UCS equipment:SharedIOModule:voltage managed
        object property"
    ::= { cucsEquipmentSharedIOModuleEntry 38 }

cucsEquipmentSharedIOModuleAssetTag OBJECT-TYPE
    SYNTAX       SnmpAdminString
    MAX-ACCESS   read-only
    STATUS       current
    DESCRIPTION
        "Cisco UCS equipment:SharedIOModule:assetTag managed
        object property"
    ::= { cucsEquipmentSharedIOModuleEntry 39 }

cucsEquipmentSiocTempStatsTable OBJECT-TYPE
    SYNTAX           SEQUENCE OF CucsEquipmentSiocTempStatsEntry
    MAX-ACCESS       not-accessible
    STATUS           current
    DESCRIPTION
        "Cisco UCS equipment:SiocTempStats managed object table"
    ::= { cucsEquipmentObjects 197 }

cucsEquipmentSiocTempStatsEntry OBJECT-TYPE
    SYNTAX           CucsEquipmentSiocTempStatsEntry
    MAX-ACCESS       not-accessible
    STATUS           current
    DESCRIPTION
        "Entry for the cucsEquipmentSiocTempStatsTable table."
    INDEX { cucsEquipmentSiocTempStatsInstanceId }
    ::= { cucsEquipmentSiocTempStatsTable 1 }

CucsEquipmentSiocTempStatsEntry ::= SEQUENCE {
    cucsEquipmentSiocTempStatsInstanceId                             CucsManagedObjectId,
    cucsEquipmentSiocTempStatsDn                                     CucsManagedObjectDn,
    cucsEquipmentSiocTempStatsRn                                     SnmpAdminString,
    cucsEquipmentSiocTempStatsCmcTemp                                INTEGER,
    cucsEquipmentSiocTempStatsCmcTempAvg                             INTEGER,
    cucsEquipmentSiocTempStatsCmcTempMax                             INTEGER,
    cucsEquipmentSiocTempStatsCmcTempMin                             INTEGER,
    cucsEquipmentSiocTempStatsFrontTemp                              INTEGER,
    cucsEquipmentSiocTempStatsFrontTempAvg                           INTEGER,
    cucsEquipmentSiocTempStatsFrontTempMax                           INTEGER,
    cucsEquipmentSiocTempStatsFrontTempMin                           INTEGER,
    cucsEquipmentSiocTempStatsIntervals                              Gauge32,
    cucsEquipmentSiocTempStatsMidTemp                                INTEGER,
    cucsEquipmentSiocTempStatsMidTempAvg                             INTEGER,
    cucsEquipmentSiocTempStatsMidTempMax                             INTEGER,
    cucsEquipmentSiocTempStatsMidTempMin                             INTEGER,
    cucsEquipmentSiocTempStatsRearTemp                               INTEGER,
    cucsEquipmentSiocTempStatsRearTempAvg                            INTEGER,
    cucsEquipmentSiocTempStatsRearTempMax                            INTEGER,
    cucsEquipmentSiocTempStatsRearTempMin                            INTEGER,
    cucsEquipmentSiocTempStatsSuspect                                TruthValue,
    cucsEquipmentSiocTempStatsThresholded                            CucsEquipmentSiocTempStatsThresholded,
    cucsEquipmentSiocTempStatsTimeCollected                          DateAndTime,
    cucsEquipmentSiocTempStatsUpdate                                 Gauge32,
    cucsEquipmentSiocTempStatsVicTemp                                INTEGER,
    cucsEquipmentSiocTempStatsVicTempAvg                             INTEGER,
    cucsEquipmentSiocTempStatsVicTempMax                             INTEGER,
    cucsEquipmentSiocTempStatsVicTempMin                             INTEGER
}

cucsEquipmentSiocTempStatsInstanceId OBJECT-TYPE
    SYNTAX       CucsManagedObjectId
    MAX-ACCESS   not-accessible
    STATUS       current
    DESCRIPTION
        "Instance identifier of the managed object."
    ::= { cucsEquipmentSiocTempStatsEntry 1 }

cucsEquipmentSiocTempStatsDn OBJECT-TYPE
    SYNTAX       CucsManagedObjectDn
    MAX-ACCESS   read-only
    STATUS       current
    DESCRIPTION
        "Cisco UCS equipment:SiocTempStats:dn managed object property"
    ::= { cucsEquipmentSiocTempStatsEntry 2 }

cucsEquipmentSiocTempStatsRn OBJECT-TYPE
    SYNTAX       SnmpAdminString
    MAX-ACCESS   read-only
    STATUS       current
    DESCRIPTION
        "Cisco UCS equipment:SiocTempStats:rn managed object property"
    ::= { cucsEquipmentSiocTempStatsEntry 3 }

cucsEquipmentSiocTempStatsCmcTemp OBJECT-TYPE
    SYNTAX       INTEGER
    MAX-ACCESS   read-only
    STATUS       current
    DESCRIPTION
        "Cisco UCS equipment:SiocTempStats:cmcTemp managed
        object property"
    ::= { cucsEquipmentSiocTempStatsEntry 4 }

cucsEquipmentSiocTempStatsCmcTempAvg OBJECT-TYPE
    SYNTAX       INTEGER
    MAX-ACCESS   read-only
    STATUS       current
    DESCRIPTION
        "Cisco UCS equipment:SiocTempStats:cmcTempAvg managed
        object property"
    ::= { cucsEquipmentSiocTempStatsEntry 5 }

cucsEquipmentSiocTempStatsCmcTempMax OBJECT-TYPE
    SYNTAX       INTEGER
    MAX-ACCESS   read-only
    STATUS       current
    DESCRIPTION
        "Cisco UCS equipment:SiocTempStats:cmcTempMax managed
        object property"
    ::= { cucsEquipmentSiocTempStatsEntry 6 }

cucsEquipmentSiocTempStatsCmcTempMin OBJECT-TYPE
    SYNTAX       INTEGER
    MAX-ACCESS   read-only
    STATUS       current
    DESCRIPTION
        "Cisco UCS equipment:SiocTempStats:cmcTempMin managed
        object property"
    ::= { cucsEquipmentSiocTempStatsEntry 7 }

cucsEquipmentSiocTempStatsFrontTemp OBJECT-TYPE
    SYNTAX       INTEGER
    MAX-ACCESS   read-only
    STATUS       current
    DESCRIPTION
        "Cisco UCS equipment:SiocTempStats:frontTemp managed
        object property"
    ::= { cucsEquipmentSiocTempStatsEntry 8 }

cucsEquipmentSiocTempStatsFrontTempAvg OBJECT-TYPE
    SYNTAX       INTEGER
    MAX-ACCESS   read-only
    STATUS       current
    DESCRIPTION
        "Cisco UCS equipment:SiocTempStats:frontTempAvg
        managed object property"
    ::= { cucsEquipmentSiocTempStatsEntry 9 }

cucsEquipmentSiocTempStatsFrontTempMax OBJECT-TYPE
    SYNTAX       INTEGER
    MAX-ACCESS   read-only
    STATUS       current
    DESCRIPTION
        "Cisco UCS equipment:SiocTempStats:frontTempMax
        managed object property"
    ::= { cucsEquipmentSiocTempStatsEntry 10 }

cucsEquipmentSiocTempStatsFrontTempMin OBJECT-TYPE
    SYNTAX       INTEGER
    MAX-ACCESS   read-only
    STATUS       current
    DESCRIPTION
        "Cisco UCS equipment:SiocTempStats:frontTempMin
        managed object property"
    ::= { cucsEquipmentSiocTempStatsEntry 11 }

cucsEquipmentSiocTempStatsIntervals OBJECT-TYPE
    SYNTAX       Gauge32
    MAX-ACCESS   read-only
    STATUS       current
    DESCRIPTION
        "Cisco UCS equipment:SiocTempStats:intervals managed
        object property"
    ::= { cucsEquipmentSiocTempStatsEntry 12 }

cucsEquipmentSiocTempStatsMidTemp OBJECT-TYPE
    SYNTAX       INTEGER
    MAX-ACCESS   read-only
    STATUS       current
    DESCRIPTION
        "Cisco UCS equipment:SiocTempStats:midTemp managed
        object property"
    ::= { cucsEquipmentSiocTempStatsEntry 13 }

cucsEquipmentSiocTempStatsMidTempAvg OBJECT-TYPE
    SYNTAX       INTEGER
    MAX-ACCESS   read-only
    STATUS       current
    DESCRIPTION
        "Cisco UCS equipment:SiocTempStats:midTempAvg managed
        object property"
    ::= { cucsEquipmentSiocTempStatsEntry 14 }

cucsEquipmentSiocTempStatsMidTempMax OBJECT-TYPE
    SYNTAX       INTEGER
    MAX-ACCESS   read-only
    STATUS       current
    DESCRIPTION
        "Cisco UCS equipment:SiocTempStats:midTempMax managed
        object property"
    ::= { cucsEquipmentSiocTempStatsEntry 15 }

cucsEquipmentSiocTempStatsMidTempMin OBJECT-TYPE
    SYNTAX       INTEGER
    MAX-ACCESS   read-only
    STATUS       current
    DESCRIPTION
        "Cisco UCS equipment:SiocTempStats:midTempMin managed
        object property"
    ::= { cucsEquipmentSiocTempStatsEntry 16 }

cucsEquipmentSiocTempStatsRearTemp OBJECT-TYPE
    SYNTAX       INTEGER
    MAX-ACCESS   read-only
    STATUS       current
    DESCRIPTION
        "Cisco UCS equipment:SiocTempStats:rearTemp managed
        object property"
    ::= { cucsEquipmentSiocTempStatsEntry 18 }

cucsEquipmentSiocTempStatsRearTempAvg OBJECT-TYPE
    SYNTAX       INTEGER
    MAX-ACCESS   read-only
    STATUS       current
    DESCRIPTION
        "Cisco UCS equipment:SiocTempStats:rearTempAvg
        managed object property"
    ::= { cucsEquipmentSiocTempStatsEntry 19 }

cucsEquipmentSiocTempStatsRearTempMax OBJECT-TYPE
    SYNTAX       INTEGER
    MAX-ACCESS   read-only
    STATUS       current
    DESCRIPTION
        "Cisco UCS equipment:SiocTempStats:rearTempMax
        managed object property"
    ::= { cucsEquipmentSiocTempStatsEntry 20 }

cucsEquipmentSiocTempStatsRearTempMin OBJECT-TYPE
    SYNTAX       INTEGER
    MAX-ACCESS   read-only
    STATUS       current
    DESCRIPTION
        "Cisco UCS equipment:SiocTempStats:rearTempMin
        managed object property"
    ::= { cucsEquipmentSiocTempStatsEntry 21 }

cucsEquipmentSiocTempStatsSuspect OBJECT-TYPE
    SYNTAX       TruthValue
    MAX-ACCESS   read-only
    STATUS       current
    DESCRIPTION
        "Cisco UCS equipment:SiocTempStats:suspect managed
        object property"
    ::= { cucsEquipmentSiocTempStatsEntry 23 }

cucsEquipmentSiocTempStatsThresholded OBJECT-TYPE
    SYNTAX       CucsEquipmentSiocTempStatsThresholded
    MAX-ACCESS   read-only
    STATUS       current
    DESCRIPTION
        "Cisco UCS equipment:SiocTempStats:thresholded
        managed object property"
    ::= { cucsEquipmentSiocTempStatsEntry 24 }

cucsEquipmentSiocTempStatsTimeCollected OBJECT-TYPE
    SYNTAX       DateAndTime
    MAX-ACCESS   read-only
    STATUS       current
    DESCRIPTION
        "Cisco UCS equipment:SiocTempStats:timeCollected
        managed object property"
    ::= { cucsEquipmentSiocTempStatsEntry 25 }

cucsEquipmentSiocTempStatsUpdate OBJECT-TYPE
    SYNTAX       Gauge32
    MAX-ACCESS   read-only
    STATUS       current
    DESCRIPTION
        "Cisco UCS equipment:SiocTempStats:update managed object property"
    ::= { cucsEquipmentSiocTempStatsEntry 26 }

cucsEquipmentSiocTempStatsVicTemp OBJECT-TYPE
    SYNTAX       INTEGER
    MAX-ACCESS   read-only
    STATUS       current
    DESCRIPTION
        "Cisco UCS equipment:SiocTempStats:vicTemp managed
        object property"
    ::= { cucsEquipmentSiocTempStatsEntry 27 }

cucsEquipmentSiocTempStatsVicTempAvg OBJECT-TYPE
    SYNTAX       INTEGER
    MAX-ACCESS   read-only
    STATUS       current
    DESCRIPTION
        "Cisco UCS equipment:SiocTempStats:vicTempAvg managed
        object property"
    ::= { cucsEquipmentSiocTempStatsEntry 28 }

cucsEquipmentSiocTempStatsVicTempMax OBJECT-TYPE
    SYNTAX       INTEGER
    MAX-ACCESS   read-only
    STATUS       current
    DESCRIPTION
        "Cisco UCS equipment:SiocTempStats:vicTempMax managed
        object property"
    ::= { cucsEquipmentSiocTempStatsEntry 29 }

cucsEquipmentSiocTempStatsVicTempMin OBJECT-TYPE
    SYNTAX       INTEGER
    MAX-ACCESS   read-only
    STATUS       current
    DESCRIPTION
        "Cisco UCS equipment:SiocTempStats:vicTempMin managed
        object property"
    ::= { cucsEquipmentSiocTempStatsEntry 30 }

cucsEquipmentSiocTempStatsHistTable OBJECT-TYPE
    SYNTAX           SEQUENCE OF CucsEquipmentSiocTempStatsHistEntry
    MAX-ACCESS       not-accessible
    STATUS           current
    DESCRIPTION
        "Cisco UCS equipment:SiocTempStatsHist managed object table"
    ::= { cucsEquipmentObjects 198 }

cucsEquipmentSiocTempStatsHistEntry OBJECT-TYPE
    SYNTAX           CucsEquipmentSiocTempStatsHistEntry
    MAX-ACCESS       not-accessible
    STATUS           current
    DESCRIPTION
        "Entry for the cucsEquipmentSiocTempStatsHistTable table."
    INDEX { cucsEquipmentSiocTempStatsHistInstanceId }
    ::= { cucsEquipmentSiocTempStatsHistTable 1 }

CucsEquipmentSiocTempStatsHistEntry ::= SEQUENCE {
    cucsEquipmentSiocTempStatsHistInstanceId                         CucsManagedObjectId,
    cucsEquipmentSiocTempStatsHistDn                                 CucsManagedObjectDn,
    cucsEquipmentSiocTempStatsHistRn                                 SnmpAdminString,
    cucsEquipmentSiocTempStatsHistCmcTemp                            INTEGER,
    cucsEquipmentSiocTempStatsHistCmcTempAvg                         INTEGER,
    cucsEquipmentSiocTempStatsHistCmcTempMax                         INTEGER,
    cucsEquipmentSiocTempStatsHistCmcTempMin                         INTEGER,
    cucsEquipmentSiocTempStatsHistFrontTemp                          INTEGER,
    cucsEquipmentSiocTempStatsHistFrontTempAvg                       INTEGER,
    cucsEquipmentSiocTempStatsHistFrontTempMax                       INTEGER,
    cucsEquipmentSiocTempStatsHistFrontTempMin                       INTEGER,
    cucsEquipmentSiocTempStatsHistId                                 Unsigned64,
    cucsEquipmentSiocTempStatsHistMidTemp                            INTEGER,
    cucsEquipmentSiocTempStatsHistMidTempAvg                         INTEGER,
    cucsEquipmentSiocTempStatsHistMidTempMax                         INTEGER,
    cucsEquipmentSiocTempStatsHistMidTempMin                         INTEGER,
    cucsEquipmentSiocTempStatsHistMostRecent                         TruthValue,
    cucsEquipmentSiocTempStatsHistRearTemp                           INTEGER,
    cucsEquipmentSiocTempStatsHistRearTempAvg                        INTEGER,
    cucsEquipmentSiocTempStatsHistRearTempMax                        INTEGER,
    cucsEquipmentSiocTempStatsHistRearTempMin                        INTEGER,
    cucsEquipmentSiocTempStatsHistSuspect                            TruthValue,
    cucsEquipmentSiocTempStatsHistThresholded                        CucsEquipmentSiocTempStatsHistThresholded,
    cucsEquipmentSiocTempStatsHistTimeCollected                      DateAndTime,
    cucsEquipmentSiocTempStatsHistVicTemp                            INTEGER,
    cucsEquipmentSiocTempStatsHistVicTempAvg                         INTEGER,
    cucsEquipmentSiocTempStatsHistVicTempMax                         INTEGER,
    cucsEquipmentSiocTempStatsHistVicTempMin                         INTEGER
}

cucsEquipmentSiocTempStatsHistInstanceId OBJECT-TYPE
    SYNTAX       CucsManagedObjectId
    MAX-ACCESS   not-accessible
    STATUS       current
    DESCRIPTION
        "Instance identifier of the managed object."
    ::= { cucsEquipmentSiocTempStatsHistEntry 1 }

cucsEquipmentSiocTempStatsHistDn OBJECT-TYPE
    SYNTAX       CucsManagedObjectDn
    MAX-ACCESS   read-only
    STATUS       current
    DESCRIPTION
        "Cisco UCS equipment:SiocTempStatsHist:dn managed object property"
    ::= { cucsEquipmentSiocTempStatsHistEntry 2 }

cucsEquipmentSiocTempStatsHistRn OBJECT-TYPE
    SYNTAX       SnmpAdminString
    MAX-ACCESS   read-only
    STATUS       current
    DESCRIPTION
        "Cisco UCS equipment:SiocTempStatsHist:rn managed object property"
    ::= { cucsEquipmentSiocTempStatsHistEntry 3 }

cucsEquipmentSiocTempStatsHistCmcTemp OBJECT-TYPE
    SYNTAX       INTEGER
    MAX-ACCESS   read-only
    STATUS       current
    DESCRIPTION
        "Cisco UCS equipment:SiocTempStatsHist:cmcTemp
        managed object property"
    ::= { cucsEquipmentSiocTempStatsHistEntry 4 }

cucsEquipmentSiocTempStatsHistCmcTempAvg OBJECT-TYPE
    SYNTAX       INTEGER
    MAX-ACCESS   read-only
    STATUS       current
    DESCRIPTION
        "Cisco UCS equipment:SiocTempStatsHist:cmcTempAvg
        managed object property"
    ::= { cucsEquipmentSiocTempStatsHistEntry 5 }

cucsEquipmentSiocTempStatsHistCmcTempMax OBJECT-TYPE
    SYNTAX       INTEGER
    MAX-ACCESS   read-only
    STATUS       current
    DESCRIPTION
        "Cisco UCS equipment:SiocTempStatsHist:cmcTempMax
        managed object property"
    ::= { cucsEquipmentSiocTempStatsHistEntry 6 }

cucsEquipmentSiocTempStatsHistCmcTempMin OBJECT-TYPE
    SYNTAX       INTEGER
    MAX-ACCESS   read-only
    STATUS       current
    DESCRIPTION
        "Cisco UCS equipment:SiocTempStatsHist:cmcTempMin
        managed object property"
    ::= { cucsEquipmentSiocTempStatsHistEntry 7 }

cucsEquipmentSiocTempStatsHistFrontTemp OBJECT-TYPE
    SYNTAX       INTEGER
    MAX-ACCESS   read-only
    STATUS       current
    DESCRIPTION
        "Cisco UCS equipment:SiocTempStatsHist:frontTemp
        managed object property"
    ::= { cucsEquipmentSiocTempStatsHistEntry 8 }

cucsEquipmentSiocTempStatsHistFrontTempAvg OBJECT-TYPE
    SYNTAX       INTEGER
    MAX-ACCESS   read-only
    STATUS       current
    DESCRIPTION
        "Cisco UCS equipment:SiocTempStatsHist:frontTempAvg
        managed object property"
    ::= { cucsEquipmentSiocTempStatsHistEntry 9 }

cucsEquipmentSiocTempStatsHistFrontTempMax OBJECT-TYPE
    SYNTAX       INTEGER
    MAX-ACCESS   read-only
    STATUS       current
    DESCRIPTION
        "Cisco UCS equipment:SiocTempStatsHist:frontTempMax
        managed object property"
    ::= { cucsEquipmentSiocTempStatsHistEntry 10 }

cucsEquipmentSiocTempStatsHistFrontTempMin OBJECT-TYPE
    SYNTAX       INTEGER
    MAX-ACCESS   read-only
    STATUS       current
    DESCRIPTION
        "Cisco UCS equipment:SiocTempStatsHist:frontTempMin
        managed object property"
    ::= { cucsEquipmentSiocTempStatsHistEntry 11 }

cucsEquipmentSiocTempStatsHistId OBJECT-TYPE
    SYNTAX       Unsigned64
    MAX-ACCESS   read-only
    STATUS       current
    DESCRIPTION
        "Cisco UCS equipment:SiocTempStatsHist:id managed object property"
    ::= { cucsEquipmentSiocTempStatsHistEntry 12 }

cucsEquipmentSiocTempStatsHistMidTemp OBJECT-TYPE
    SYNTAX       INTEGER
    MAX-ACCESS   read-only
    STATUS       current
    DESCRIPTION
        "Cisco UCS equipment:SiocTempStatsHist:midTemp
        managed object property"
    ::= { cucsEquipmentSiocTempStatsHistEntry 13 }

cucsEquipmentSiocTempStatsHistMidTempAvg OBJECT-TYPE
    SYNTAX       INTEGER
    MAX-ACCESS   read-only
    STATUS       current
    DESCRIPTION
        "Cisco UCS equipment:SiocTempStatsHist:midTempAvg
        managed object property"
    ::= { cucsEquipmentSiocTempStatsHistEntry 14 }

cucsEquipmentSiocTempStatsHistMidTempMax OBJECT-TYPE
    SYNTAX       INTEGER
    MAX-ACCESS   read-only
    STATUS       current
    DESCRIPTION
        "Cisco UCS equipment:SiocTempStatsHist:midTempMax
        managed object property"
    ::= { cucsEquipmentSiocTempStatsHistEntry 15 }

cucsEquipmentSiocTempStatsHistMidTempMin OBJECT-TYPE
    SYNTAX       INTEGER
    MAX-ACCESS   read-only
    STATUS       current
    DESCRIPTION
        "Cisco UCS equipment:SiocTempStatsHist:midTempMin
        managed object property"
    ::= { cucsEquipmentSiocTempStatsHistEntry 16 }

cucsEquipmentSiocTempStatsHistMostRecent OBJECT-TYPE
    SYNTAX       TruthValue
    MAX-ACCESS   read-only
    STATUS       current
    DESCRIPTION
        "Cisco UCS equipment:SiocTempStatsHist:mostRecent
        managed object property"
    ::= { cucsEquipmentSiocTempStatsHistEntry 17 }

cucsEquipmentSiocTempStatsHistRearTemp OBJECT-TYPE
    SYNTAX       INTEGER
    MAX-ACCESS   read-only
    STATUS       current
    DESCRIPTION
        "Cisco UCS equipment:SiocTempStatsHist:rearTemp
        managed object property"
    ::= { cucsEquipmentSiocTempStatsHistEntry 18 }

cucsEquipmentSiocTempStatsHistRearTempAvg OBJECT-TYPE
    SYNTAX       INTEGER
    MAX-ACCESS   read-only
    STATUS       current
    DESCRIPTION
        "Cisco UCS equipment:SiocTempStatsHist:rearTempAvg
        managed object property"
    ::= { cucsEquipmentSiocTempStatsHistEntry 19 }

cucsEquipmentSiocTempStatsHistRearTempMax OBJECT-TYPE
    SYNTAX       INTEGER
    MAX-ACCESS   read-only
    STATUS       current
    DESCRIPTION
        "Cisco UCS equipment:SiocTempStatsHist:rearTempMax
        managed object property"
    ::= { cucsEquipmentSiocTempStatsHistEntry 20 }

cucsEquipmentSiocTempStatsHistRearTempMin OBJECT-TYPE
    SYNTAX       INTEGER
    MAX-ACCESS   read-only
    STATUS       current
    DESCRIPTION
        "Cisco UCS equipment:SiocTempStatsHist:rearTempMin
        managed object property"
    ::= { cucsEquipmentSiocTempStatsHistEntry 21 }

cucsEquipmentSiocTempStatsHistSuspect OBJECT-TYPE
    SYNTAX       TruthValue
    MAX-ACCESS   read-only
    STATUS       current
    DESCRIPTION
        "Cisco UCS equipment:SiocTempStatsHist:suspect
        managed object property"
    ::= { cucsEquipmentSiocTempStatsHistEntry 22 }

cucsEquipmentSiocTempStatsHistThresholded OBJECT-TYPE
    SYNTAX       CucsEquipmentSiocTempStatsHistThresholded
    MAX-ACCESS   read-only
    STATUS       current
    DESCRIPTION
        "Cisco UCS equipment:SiocTempStatsHist:thresholded
        managed object property"
    ::= { cucsEquipmentSiocTempStatsHistEntry 23 }

cucsEquipmentSiocTempStatsHistTimeCollected OBJECT-TYPE
    SYNTAX       DateAndTime
    MAX-ACCESS   read-only
    STATUS       current
    DESCRIPTION
        "Cisco UCS equipment:SiocTempStatsHist:timeCollected
        managed object property"
    ::= { cucsEquipmentSiocTempStatsHistEntry 24 }

cucsEquipmentSiocTempStatsHistVicTemp OBJECT-TYPE
    SYNTAX       INTEGER
    MAX-ACCESS   read-only
    STATUS       current
    DESCRIPTION
        "Cisco UCS equipment:SiocTempStatsHist:vicTemp
        managed object property"
    ::= { cucsEquipmentSiocTempStatsHistEntry 25 }

cucsEquipmentSiocTempStatsHistVicTempAvg OBJECT-TYPE
    SYNTAX       INTEGER
    MAX-ACCESS   read-only
    STATUS       current
    DESCRIPTION
        "Cisco UCS equipment:SiocTempStatsHist:vicTempAvg
        managed object property"
    ::= { cucsEquipmentSiocTempStatsHistEntry 26 }

cucsEquipmentSiocTempStatsHistVicTempMax OBJECT-TYPE
    SYNTAX       INTEGER
    MAX-ACCESS   read-only
    STATUS       current
    DESCRIPTION
        "Cisco UCS equipment:SiocTempStatsHist:vicTempMax
        managed object property"
    ::= { cucsEquipmentSiocTempStatsHistEntry 27 }

cucsEquipmentSiocTempStatsHistVicTempMin OBJECT-TYPE
    SYNTAX       INTEGER
    MAX-ACCESS   read-only
    STATUS       current
    DESCRIPTION
        "Cisco UCS equipment:SiocTempStatsHist:vicTempMin
        managed object property"
    ::= { cucsEquipmentSiocTempStatsHistEntry 28 }

cucsEquipmentSlotArrayTable OBJECT-TYPE
    SYNTAX           SEQUENCE OF CucsEquipmentSlotArrayEntry
    MAX-ACCESS       not-accessible
    STATUS           current
    DESCRIPTION
        "Cisco UCS equipment:SlotArray managed object table"
    ::= { cucsEquipmentObjects 66 }

cucsEquipmentSlotArrayEntry OBJECT-TYPE
    SYNTAX           CucsEquipmentSlotArrayEntry
    MAX-ACCESS       not-accessible
    STATUS           current
    DESCRIPTION
        "Entry for the cucsEquipmentSlotArrayTable table."
    INDEX { cucsEquipmentSlotArrayInstanceId }
    ::= { cucsEquipmentSlotArrayTable 1 }

CucsEquipmentSlotArrayEntry ::= SEQUENCE {
    cucsEquipmentSlotArrayInstanceId                                 CucsManagedObjectId,
    cucsEquipmentSlotArrayDn                                         CucsManagedObjectDn,
    cucsEquipmentSlotArrayRn                                         SnmpAdminString,
    cucsEquipmentSlotArrayDescr                                      SnmpAdminString,
    cucsEquipmentSlotArrayFirstIndex                                 Gauge32,
    cucsEquipmentSlotArrayHeight                                     SnmpAdminString,
    cucsEquipmentSlotArrayHorizontalStartOffset                      SnmpAdminString,
    cucsEquipmentSlotArrayInlineGroupSeparation                      SnmpAdminString,
    cucsEquipmentSlotArrayInlineGroupSize                            Gauge32,
    cucsEquipmentSlotArrayInlineOffset                               SnmpAdminString,
    cucsEquipmentSlotArrayIntId                                      SnmpAdminString,
    cucsEquipmentSlotArrayLocation                                   CucsEquipmentSlotArrayLocation,
    cucsEquipmentSlotArrayName                                       SnmpAdminString,
    cucsEquipmentSlotArrayNumberOfSlots                              Gauge32,
    cucsEquipmentSlotArrayOrientation                                CucsEquipmentSlotArrayOrientation,
    cucsEquipmentSlotArraySelector                                   CucsEquipmentSlotArraySelector,
    cucsEquipmentSlotArraySlotsPerLine                               Gauge32,
    cucsEquipmentSlotArrayTransverseGroupSeparation                  SnmpAdminString,
    cucsEquipmentSlotArrayTransverseGroupSize                        Gauge32,
    cucsEquipmentSlotArrayTransverseOffset                           SnmpAdminString,
    cucsEquipmentSlotArrayVerticalStartOffset                        SnmpAdminString,
    cucsEquipmentSlotArrayWidth                                      SnmpAdminString,
    cucsEquipmentSlotArrayPolicyLevel                                Gauge32,
    cucsEquipmentSlotArrayPolicyOwner                                CucsPolicyPolicyOwner,
    cucsEquipmentSlotArrayDeviceSlotOffset                           Gauge32,
    cucsEquipmentSlotArrayStorageBiosMode                            SnmpAdminString,
    cucsEquipmentSlotArraySubOemId                                   Gauge32,
    cucsEquipmentSlotArrayNumberOfOnboardDisks                       Gauge32,
    cucsEquipmentSlotArrayOnboardDiskBasePortNo                      Gauge32,
    cucsEquipmentSlotArrayOnboardDiskFirstIndex                      Gauge32
}

cucsEquipmentSlotArrayInstanceId OBJECT-TYPE
    SYNTAX       CucsManagedObjectId
    MAX-ACCESS   not-accessible
    STATUS       current
    DESCRIPTION
        "Instance identifier of the managed object."
    ::= { cucsEquipmentSlotArrayEntry 1 }

cucsEquipmentSlotArrayDn OBJECT-TYPE
    SYNTAX       CucsManagedObjectDn
    MAX-ACCESS   read-only
    STATUS       current
    DESCRIPTION
        "Cisco UCS equipment:SlotArray:dn managed object property"
    ::= { cucsEquipmentSlotArrayEntry 2 }

cucsEquipmentSlotArrayRn OBJECT-TYPE
    SYNTAX       SnmpAdminString
    MAX-ACCESS   read-only
    STATUS       current
    DESCRIPTION
        "Cisco UCS equipment:SlotArray:rn managed object property"
    ::= { cucsEquipmentSlotArrayEntry 3 }

cucsEquipmentSlotArrayDescr OBJECT-TYPE
    SYNTAX       SnmpAdminString
    MAX-ACCESS   read-only
    STATUS       current
    DESCRIPTION
        "Cisco UCS equipment:SlotArray:descr managed object property"
    ::= { cucsEquipmentSlotArrayEntry 4 }

cucsEquipmentSlotArrayFirstIndex OBJECT-TYPE
    SYNTAX       Gauge32
    MAX-ACCESS   read-only
    STATUS       current
    DESCRIPTION
        "Cisco UCS equipment:SlotArray:firstIndex managed object property"
    ::= { cucsEquipmentSlotArrayEntry 5 }

cucsEquipmentSlotArrayHeight OBJECT-TYPE
    SYNTAX       SnmpAdminString
    MAX-ACCESS   read-only
    STATUS       current
    DESCRIPTION
        "Cisco UCS equipment:SlotArray:height managed object property"
    ::= { cucsEquipmentSlotArrayEntry 6 }

cucsEquipmentSlotArrayHorizontalStartOffset OBJECT-TYPE
    SYNTAX       SnmpAdminString
    MAX-ACCESS   read-only
    STATUS       current
    DESCRIPTION
        "Cisco UCS equipment:SlotArray:horizontalStartOffset
        managed object property"
    ::= { cucsEquipmentSlotArrayEntry 7 }

cucsEquipmentSlotArrayInlineGroupSeparation OBJECT-TYPE
    SYNTAX       SnmpAdminString
    MAX-ACCESS   read-only
    STATUS       current
    DESCRIPTION
        "Cisco UCS equipment:SlotArray:inlineGroupSeparation
        managed object property"
    ::= { cucsEquipmentSlotArrayEntry 8 }

cucsEquipmentSlotArrayInlineGroupSize OBJECT-TYPE
    SYNTAX       Gauge32
    MAX-ACCESS   read-only
    STATUS       current
    DESCRIPTION
        "Cisco UCS equipment:SlotArray:inlineGroupSize
        managed object property"
    ::= { cucsEquipmentSlotArrayEntry 9 }

cucsEquipmentSlotArrayInlineOffset OBJECT-TYPE
    SYNTAX       SnmpAdminString
    MAX-ACCESS   read-only
    STATUS       current
    DESCRIPTION
        "Cisco UCS equipment:SlotArray:inlineOffset managed
        object property"
    ::= { cucsEquipmentSlotArrayEntry 10 }

cucsEquipmentSlotArrayIntId OBJECT-TYPE
    SYNTAX       SnmpAdminString
    MAX-ACCESS   read-only
    STATUS       current
    DESCRIPTION
        "Cisco UCS equipment:SlotArray:intId managed object property"
    ::= { cucsEquipmentSlotArrayEntry 11 }

cucsEquipmentSlotArrayLocation OBJECT-TYPE
    SYNTAX       CucsEquipmentSlotArrayLocation
    MAX-ACCESS   read-only
    STATUS       current
    DESCRIPTION
        "Cisco UCS equipment:SlotArray:location managed object property"
    ::= { cucsEquipmentSlotArrayEntry 12 }

cucsEquipmentSlotArrayName OBJECT-TYPE
    SYNTAX       SnmpAdminString
    MAX-ACCESS   read-only
    STATUS       current
    DESCRIPTION
        "Cisco UCS equipment:SlotArray:name managed object property"
    ::= { cucsEquipmentSlotArrayEntry 13 }

cucsEquipmentSlotArrayNumberOfSlots OBJECT-TYPE
    SYNTAX       Gauge32
    MAX-ACCESS   read-only
    STATUS       current
    DESCRIPTION
        "Cisco UCS equipment:SlotArray:numberOfSlots managed
        object property"
    ::= { cucsEquipmentSlotArrayEntry 14 }

cucsEquipmentSlotArrayOrientation OBJECT-TYPE
    SYNTAX       CucsEquipmentSlotArrayOrientation
    MAX-ACCESS   read-only
    STATUS       current
    DESCRIPTION
        "Cisco UCS equipment:SlotArray:orientation managed
        object property"
    ::= { cucsEquipmentSlotArrayEntry 15 }

cucsEquipmentSlotArraySelector OBJECT-TYPE
    SYNTAX       CucsEquipmentSlotArraySelector
    MAX-ACCESS   read-only
    STATUS       current
    DESCRIPTION
        "Cisco UCS equipment:SlotArray:selector managed object property"
    ::= { cucsEquipmentSlotArrayEntry 16 }

cucsEquipmentSlotArraySlotsPerLine OBJECT-TYPE
    SYNTAX       Gauge32
    MAX-ACCESS   read-only
    STATUS       current
    DESCRIPTION
        "Cisco UCS equipment:SlotArray:slotsPerLine managed
        object property"
    ::= { cucsEquipmentSlotArrayEntry 17 }

cucsEquipmentSlotArrayTransverseGroupSeparation OBJECT-TYPE
    SYNTAX       SnmpAdminString
    MAX-ACCESS   read-only
    STATUS       current
    DESCRIPTION
        "Cisco UCS equipment:SlotArray:transverseGroupSeparation
        managed object property"
    ::= { cucsEquipmentSlotArrayEntry 18 }

cucsEquipmentSlotArrayTransverseGroupSize OBJECT-TYPE
    SYNTAX       Gauge32
    MAX-ACCESS   read-only
    STATUS       current
    DESCRIPTION
        "Cisco UCS equipment:SlotArray:transverseGroupSize
        managed object property"
    ::= { cucsEquipmentSlotArrayEntry 19 }

cucsEquipmentSlotArrayTransverseOffset OBJECT-TYPE
    SYNTAX       SnmpAdminString
    MAX-ACCESS   read-only
    STATUS       current
    DESCRIPTION
        "Cisco UCS equipment:SlotArray:transverseOffset
        managed object property"
    ::= { cucsEquipmentSlotArrayEntry 20 }

cucsEquipmentSlotArrayVerticalStartOffset OBJECT-TYPE
    SYNTAX       SnmpAdminString
    MAX-ACCESS   read-only
    STATUS       current
    DESCRIPTION
        "Cisco UCS equipment:SlotArray:verticalStartOffset
        managed object property"
    ::= { cucsEquipmentSlotArrayEntry 21 }

cucsEquipmentSlotArrayWidth OBJECT-TYPE
    SYNTAX       SnmpAdminString
    MAX-ACCESS   read-only
    STATUS       current
    DESCRIPTION
        "Cisco UCS equipment:SlotArray:width managed object property"
    ::= { cucsEquipmentSlotArrayEntry 22 }

cucsEquipmentSlotArrayPolicyLevel OBJECT-TYPE
    SYNTAX       Gauge32
    MAX-ACCESS   read-only
    STATUS       current
    DESCRIPTION
        "Cisco UCS equipment:SlotArray:policyLevel managed
        object property"
    ::= { cucsEquipmentSlotArrayEntry 23 }

cucsEquipmentSlotArrayPolicyOwner OBJECT-TYPE
    SYNTAX       CucsPolicyPolicyOwner
    MAX-ACCESS   read-only
    STATUS       current
    DESCRIPTION
        "Cisco UCS equipment:SlotArray:policyOwner managed
        object property"
    ::= { cucsEquipmentSlotArrayEntry 24 }

cucsEquipmentSlotArrayDeviceSlotOffset OBJECT-TYPE
    SYNTAX       Gauge32
    MAX-ACCESS   read-only
    STATUS       current
    DESCRIPTION
        "Cisco UCS equipment:SlotArray:deviceSlotOffset
        managed object property"
    ::= { cucsEquipmentSlotArrayEntry 25 }

cucsEquipmentSlotArrayStorageBiosMode OBJECT-TYPE
    SYNTAX       SnmpAdminString
    MAX-ACCESS   read-only
    STATUS       current
    DESCRIPTION
        "Cisco UCS equipment:SlotArray:storageBiosMode
        managed object property"
    ::= { cucsEquipmentSlotArrayEntry 26 }

cucsEquipmentSlotArraySubOemId OBJECT-TYPE
    SYNTAX       Gauge32
    MAX-ACCESS   read-only
    STATUS       current
    DESCRIPTION
        "Cisco UCS equipment:SlotArray:subOemId managed object property"
    ::= { cucsEquipmentSlotArrayEntry 27 }

cucsEquipmentSlotArrayNumberOfOnboardDisks OBJECT-TYPE
    SYNTAX       Gauge32
    MAX-ACCESS   read-only
    STATUS       current
    DESCRIPTION
        "Cisco UCS equipment:SlotArray:numberOfOnboardDisks
        managed object property"
    ::= { cucsEquipmentSlotArrayEntry 28 }

cucsEquipmentSlotArrayOnboardDiskBasePortNo OBJECT-TYPE
    SYNTAX       Gauge32
    MAX-ACCESS   read-only
    STATUS       current
    DESCRIPTION
        "Cisco UCS equipment:SlotArray:onboardDiskBasePortNo
        managed object property"
    ::= { cucsEquipmentSlotArrayEntry 29 }

cucsEquipmentSlotArrayOnboardDiskFirstIndex OBJECT-TYPE
    SYNTAX       Gauge32
    MAX-ACCESS   read-only
    STATUS       current
    DESCRIPTION
        "Cisco UCS equipment:SlotArray:onboardDiskFirstIndex
        managed object property"
    ::= { cucsEquipmentSlotArrayEntry 30 }

cucsEquipmentSlotArrayRefTable OBJECT-TYPE
    SYNTAX           SEQUENCE OF CucsEquipmentSlotArrayRefEntry
    MAX-ACCESS       not-accessible
    STATUS           current
    DESCRIPTION
        "Cisco UCS equipment:SlotArrayRef managed object table"
    ::= { cucsEquipmentObjects 67 }

cucsEquipmentSlotArrayRefEntry OBJECT-TYPE
    SYNTAX           CucsEquipmentSlotArrayRefEntry
    MAX-ACCESS       not-accessible
    STATUS           current
    DESCRIPTION
        "Entry for the cucsEquipmentSlotArrayRefTable table."
    INDEX { cucsEquipmentSlotArrayRefInstanceId }
    ::= { cucsEquipmentSlotArrayRefTable 1 }

CucsEquipmentSlotArrayRefEntry ::= SEQUENCE {
    cucsEquipmentSlotArrayRefInstanceId                              CucsManagedObjectId,
    cucsEquipmentSlotArrayRefDn                                      CucsManagedObjectDn,
    cucsEquipmentSlotArrayRefRn                                      SnmpAdminString,
    cucsEquipmentSlotArrayRefDescr                                   SnmpAdminString,
    cucsEquipmentSlotArrayRefIntId                                   SnmpAdminString,
    cucsEquipmentSlotArrayRefName                                    SnmpAdminString,
    cucsEquipmentSlotArrayRefNumberOfSlotsSpanned                    Gauge32,
    cucsEquipmentSlotArrayRefSlotSpanOrientation                     CucsEquipmentSlotSpanOrientation,
    cucsEquipmentSlotArrayRefTargetDn                                SnmpAdminString,
    cucsEquipmentSlotArrayRefPolicyLevel                             Gauge32,
    cucsEquipmentSlotArrayRefPolicyOwner                             CucsPolicyPolicyOwner
}

cucsEquipmentSlotArrayRefInstanceId OBJECT-TYPE
    SYNTAX       CucsManagedObjectId
    MAX-ACCESS   not-accessible
    STATUS       current
    DESCRIPTION
        "Instance identifier of the managed object."
    ::= { cucsEquipmentSlotArrayRefEntry 1 }

cucsEquipmentSlotArrayRefDn OBJECT-TYPE
    SYNTAX       CucsManagedObjectDn
    MAX-ACCESS   read-only
    STATUS       current
    DESCRIPTION
        "Cisco UCS equipment:SlotArrayRef:dn managed object property"
    ::= { cucsEquipmentSlotArrayRefEntry 2 }

cucsEquipmentSlotArrayRefRn OBJECT-TYPE
    SYNTAX       SnmpAdminString
    MAX-ACCESS   read-only
    STATUS       current
    DESCRIPTION
        "Cisco UCS equipment:SlotArrayRef:rn managed object property"
    ::= { cucsEquipmentSlotArrayRefEntry 3 }

cucsEquipmentSlotArrayRefDescr OBJECT-TYPE
    SYNTAX       SnmpAdminString
    MAX-ACCESS   read-only
    STATUS       current
    DESCRIPTION
        "Cisco UCS equipment:SlotArrayRef:descr managed object property"
    ::= { cucsEquipmentSlotArrayRefEntry 4 }

cucsEquipmentSlotArrayRefIntId OBJECT-TYPE
    SYNTAX       SnmpAdminString
    MAX-ACCESS   read-only
    STATUS       current
    DESCRIPTION
        "Cisco UCS equipment:SlotArrayRef:intId managed object property"
    ::= { cucsEquipmentSlotArrayRefEntry 5 }

cucsEquipmentSlotArrayRefName OBJECT-TYPE
    SYNTAX       SnmpAdminString
    MAX-ACCESS   read-only
    STATUS       current
    DESCRIPTION
        "Cisco UCS equipment:SlotArrayRef:name managed object property"
    ::= { cucsEquipmentSlotArrayRefEntry 6 }

cucsEquipmentSlotArrayRefNumberOfSlotsSpanned OBJECT-TYPE
    SYNTAX       Gauge32
    MAX-ACCESS   read-only
    STATUS       current
    DESCRIPTION
        "Cisco UCS equipment:SlotArrayRef:numberOfSlotsSpanned
        managed object property"
    ::= { cucsEquipmentSlotArrayRefEntry 7 }

cucsEquipmentSlotArrayRefSlotSpanOrientation OBJECT-TYPE
    SYNTAX       CucsEquipmentSlotSpanOrientation
    MAX-ACCESS   read-only
    STATUS       current
    DESCRIPTION
        "Cisco UCS equipment:SlotArrayRef:slotSpanOrientation
        managed object property"
    ::= { cucsEquipmentSlotArrayRefEntry 8 }

cucsEquipmentSlotArrayRefTargetDn OBJECT-TYPE
    SYNTAX       SnmpAdminString
    MAX-ACCESS   read-only
    STATUS       current
    DESCRIPTION
        "Cisco UCS equipment:SlotArrayRef:targetDn managed
        object property"
    ::= { cucsEquipmentSlotArrayRefEntry 9 }

cucsEquipmentSlotArrayRefPolicyLevel OBJECT-TYPE
    SYNTAX       Gauge32
    MAX-ACCESS   read-only
    STATUS       current
    DESCRIPTION
        "Cisco UCS equipment:SlotArrayRef:policyLevel managed
        object property"
    ::= { cucsEquipmentSlotArrayRefEntry 10 }

cucsEquipmentSlotArrayRefPolicyOwner OBJECT-TYPE
    SYNTAX       CucsPolicyPolicyOwner
    MAX-ACCESS   read-only
    STATUS       current
    DESCRIPTION
        "Cisco UCS equipment:SlotArrayRef:policyOwner managed
        object property"
    ::= { cucsEquipmentSlotArrayRefEntry 11 }

cucsEquipmentStorageControllerConfigTable OBJECT-TYPE
    SYNTAX           SEQUENCE OF CucsEquipmentStorageControllerConfigEntry
    MAX-ACCESS       not-accessible
    STATUS           current
    DESCRIPTION
        "Cisco UCS equipment:StorageControllerConfig managed object table"
    ::= { cucsEquipmentObjects 156 }

cucsEquipmentStorageControllerConfigEntry OBJECT-TYPE
    SYNTAX           CucsEquipmentStorageControllerConfigEntry
    MAX-ACCESS       not-accessible
    STATUS           current
    DESCRIPTION
        "Entry for the cucsEquipmentStorageControllerConfigTable table."
    INDEX { cucsEquipmentStorageControllerConfigInstanceId }
    ::= { cucsEquipmentStorageControllerConfigTable 1 }

CucsEquipmentStorageControllerConfigEntry ::= SEQUENCE {
    cucsEquipmentStorageControllerConfigInstanceId                   CucsManagedObjectId,
    cucsEquipmentStorageControllerConfigDn                           CucsManagedObjectDn,
    cucsEquipmentStorageControllerConfigRn                           SnmpAdminString,
    cucsEquipmentStorageControllerConfigDescr                        SnmpAdminString,
    cucsEquipmentStorageControllerConfigDevice                       Gauge32,
    cucsEquipmentStorageControllerConfigIntId                        SnmpAdminString,
    cucsEquipmentStorageControllerConfigName                         SnmpAdminString,
    cucsEquipmentStorageControllerConfigPolicyLevel                  Gauge32,
    cucsEquipmentStorageControllerConfigPolicyOwner                  CucsPolicyPolicyOwner,
    cucsEquipmentStorageControllerConfigStorageBiosMode              SnmpAdminString,
    cucsEquipmentStorageControllerConfigStoragepid                   SnmpAdminString,
    cucsEquipmentStorageControllerConfigSubOemId                     Gauge32,
    cucsEquipmentStorageControllerConfigSubdevice                    Gauge32,
    cucsEquipmentStorageControllerConfigSubvendor                    Gauge32,
    cucsEquipmentStorageControllerConfigVendor                       Gauge32,
    cucsEquipmentStorageControllerConfigPnuosSupported               TruthValue
}

cucsEquipmentStorageControllerConfigInstanceId OBJECT-TYPE
    SYNTAX       CucsManagedObjectId
    MAX-ACCESS   not-accessible
    STATUS       current
    DESCRIPTION
        "Instance identifier of the managed object."
    ::= { cucsEquipmentStorageControllerConfigEntry 1 }

cucsEquipmentStorageControllerConfigDn OBJECT-TYPE
    SYNTAX       CucsManagedObjectDn
    MAX-ACCESS   read-only
    STATUS       current
    DESCRIPTION
        "Cisco UCS equipment:StorageControllerConfig:dn
        managed object property"
    ::= { cucsEquipmentStorageControllerConfigEntry 2 }

cucsEquipmentStorageControllerConfigRn OBJECT-TYPE
    SYNTAX       SnmpAdminString
    MAX-ACCESS   read-only
    STATUS       current
    DESCRIPTION
        "Cisco UCS equipment:StorageControllerConfig:rn
        managed object property"
    ::= { cucsEquipmentStorageControllerConfigEntry 3 }

cucsEquipmentStorageControllerConfigDescr OBJECT-TYPE
    SYNTAX       SnmpAdminString
    MAX-ACCESS   read-only
    STATUS       current
    DESCRIPTION
        "Cisco UCS equipment:StorageControllerConfig:descr
        managed object property"
    ::= { cucsEquipmentStorageControllerConfigEntry 4 }

cucsEquipmentStorageControllerConfigDevice OBJECT-TYPE
    SYNTAX       Gauge32
    MAX-ACCESS   read-only
    STATUS       current
    DESCRIPTION
        "Cisco UCS equipment:StorageControllerConfig:device
        managed object property"
    ::= { cucsEquipmentStorageControllerConfigEntry 5 }

cucsEquipmentStorageControllerConfigIntId OBJECT-TYPE
    SYNTAX       SnmpAdminString
    MAX-ACCESS   read-only
    STATUS       current
    DESCRIPTION
        "Cisco UCS equipment:StorageControllerConfig:intId
        managed object property"
    ::= { cucsEquipmentStorageControllerConfigEntry 6 }

cucsEquipmentStorageControllerConfigName OBJECT-TYPE
    SYNTAX       SnmpAdminString
    MAX-ACCESS   read-only
    STATUS       current
    DESCRIPTION
        "Cisco UCS equipment:StorageControllerConfig:name
        managed object property"
    ::= { cucsEquipmentStorageControllerConfigEntry 7 }

cucsEquipmentStorageControllerConfigPolicyLevel OBJECT-TYPE
    SYNTAX       Gauge32
    MAX-ACCESS   read-only
    STATUS       current
    DESCRIPTION
        "Cisco UCS equipment:StorageControllerConfig:policyLevel
        managed object property"
    ::= { cucsEquipmentStorageControllerConfigEntry 8 }

cucsEquipmentStorageControllerConfigPolicyOwner OBJECT-TYPE
    SYNTAX       CucsPolicyPolicyOwner
    MAX-ACCESS   read-only
    STATUS       current
    DESCRIPTION
        "Cisco UCS equipment:StorageControllerConfig:policyOwner
        managed object property"
    ::= { cucsEquipmentStorageControllerConfigEntry 9 }

cucsEquipmentStorageControllerConfigStorageBiosMode OBJECT-TYPE
    SYNTAX       SnmpAdminString
    MAX-ACCESS   read-only
    STATUS       current
    DESCRIPTION
        "Cisco UCS equipment:StorageControllerConfig:storageBiosMode
        managed object property"
    ::= { cucsEquipmentStorageControllerConfigEntry 10 }

cucsEquipmentStorageControllerConfigStoragepid OBJECT-TYPE
    SYNTAX       SnmpAdminString
    MAX-ACCESS   read-only
    STATUS       current
    DESCRIPTION
        "Cisco UCS equipment:StorageControllerConfig:storagepid
        managed object property"
    ::= { cucsEquipmentStorageControllerConfigEntry 11 }

cucsEquipmentStorageControllerConfigSubOemId OBJECT-TYPE
    SYNTAX       Gauge32
    MAX-ACCESS   read-only
    STATUS       current
    DESCRIPTION
        "Cisco UCS equipment:StorageControllerConfig:subOemId
        managed object property"
    ::= { cucsEquipmentStorageControllerConfigEntry 12 }

cucsEquipmentStorageControllerConfigSubdevice OBJECT-TYPE
    SYNTAX       Gauge32
    MAX-ACCESS   read-only
    STATUS       current
    DESCRIPTION
        "Cisco UCS equipment:StorageControllerConfig:subdevice
        managed object property"
    ::= { cucsEquipmentStorageControllerConfigEntry 13 }

cucsEquipmentStorageControllerConfigSubvendor OBJECT-TYPE
    SYNTAX       Gauge32
    MAX-ACCESS   read-only
    STATUS       current
    DESCRIPTION
        "Cisco UCS equipment:StorageControllerConfig:subvendor
        managed object property"
    ::= { cucsEquipmentStorageControllerConfigEntry 14 }

cucsEquipmentStorageControllerConfigVendor OBJECT-TYPE
    SYNTAX       Gauge32
    MAX-ACCESS   read-only
    STATUS       current
    DESCRIPTION
        "Cisco UCS equipment:StorageControllerConfig:vendor
        managed object property"
    ::= { cucsEquipmentStorageControllerConfigEntry 15 }

cucsEquipmentStorageControllerConfigPnuosSupported OBJECT-TYPE
    SYNTAX       TruthValue
    MAX-ACCESS   read-only
    STATUS       current
    DESCRIPTION
        "Cisco UCS equipment:StorageControllerConfig:pnuosSupported
        managed object property"
    ::= { cucsEquipmentStorageControllerConfigEntry 16 }

cucsEquipmentStorageControllerSlotDefTable OBJECT-TYPE
    SYNTAX           SEQUENCE OF CucsEquipmentStorageControllerSlotDefEntry
    MAX-ACCESS       not-accessible
    STATUS           current
    DESCRIPTION
        "Cisco UCS equipment:StorageControllerSlotDef managed
        object table"
    ::= { cucsEquipmentObjects 146 }

cucsEquipmentStorageControllerSlotDefEntry OBJECT-TYPE
    SYNTAX           CucsEquipmentStorageControllerSlotDefEntry
    MAX-ACCESS       not-accessible
    STATUS           current
    DESCRIPTION
        "Entry for the cucsEquipmentStorageControllerSlotDefTable table."
    INDEX { cucsEquipmentStorageControllerSlotDefInstanceId }
    ::= { cucsEquipmentStorageControllerSlotDefTable 1 }

CucsEquipmentStorageControllerSlotDefEntry ::= SEQUENCE {
    cucsEquipmentStorageControllerSlotDefInstanceId                  CucsManagedObjectId,
    cucsEquipmentStorageControllerSlotDefDn                          CucsManagedObjectDn,
    cucsEquipmentStorageControllerSlotDefRn                          SnmpAdminString,
    cucsEquipmentStorageControllerSlotDefNumSlots                    Gauge32,
    cucsEquipmentStorageControllerSlotDefOrder                       Gauge32,
    cucsEquipmentStorageControllerSlotDefSlotNum                     Gauge32
}

cucsEquipmentStorageControllerSlotDefInstanceId OBJECT-TYPE
    SYNTAX       CucsManagedObjectId
    MAX-ACCESS   not-accessible
    STATUS       current
    DESCRIPTION
        "Instance identifier of the managed object."
    ::= { cucsEquipmentStorageControllerSlotDefEntry 1 }

cucsEquipmentStorageControllerSlotDefDn OBJECT-TYPE
    SYNTAX       CucsManagedObjectDn
    MAX-ACCESS   read-only
    STATUS       current
    DESCRIPTION
        "Cisco UCS equipment:StorageControllerSlotDef:dn
        managed object property"
    ::= { cucsEquipmentStorageControllerSlotDefEntry 2 }

cucsEquipmentStorageControllerSlotDefRn OBJECT-TYPE
    SYNTAX       SnmpAdminString
    MAX-ACCESS   read-only
    STATUS       current
    DESCRIPTION
        "Cisco UCS equipment:StorageControllerSlotDef:rn
        managed object property"
    ::= { cucsEquipmentStorageControllerSlotDefEntry 3 }

cucsEquipmentStorageControllerSlotDefNumSlots OBJECT-TYPE
    SYNTAX       Gauge32
    MAX-ACCESS   read-only
    STATUS       current
    DESCRIPTION
        "Cisco UCS equipment:StorageControllerSlotDef:numSlots
        managed object property"
    ::= { cucsEquipmentStorageControllerSlotDefEntry 4 }

cucsEquipmentStorageControllerSlotDefOrder OBJECT-TYPE
    SYNTAX       Gauge32
    MAX-ACCESS   read-only
    STATUS       current
    DESCRIPTION
        "Cisco UCS equipment:StorageControllerSlotDef:order
        managed object property"
    ::= { cucsEquipmentStorageControllerSlotDefEntry 5 }

cucsEquipmentStorageControllerSlotDefSlotNum OBJECT-TYPE
    SYNTAX       Gauge32
    MAX-ACCESS   read-only
    STATUS       current
    DESCRIPTION
        "Cisco UCS equipment:StorageControllerSlotDef:slotNum
        managed object property"
    ::= { cucsEquipmentStorageControllerSlotDefEntry 6 }

cucsEquipmentStorageEncCapProviderTable OBJECT-TYPE
    SYNTAX           SEQUENCE OF CucsEquipmentStorageEncCapProviderEntry
    MAX-ACCESS       not-accessible
    STATUS           current
    DESCRIPTION
        "Cisco UCS equipment:StorageEncCapProvider managed object table"
    ::= { cucsEquipmentObjects 217 }

cucsEquipmentStorageEncCapProviderEntry OBJECT-TYPE
    SYNTAX           CucsEquipmentStorageEncCapProviderEntry
    MAX-ACCESS       not-accessible
    STATUS           current
    DESCRIPTION
        "Entry for the cucsEquipmentStorageEncCapProviderTable table."
    INDEX { cucsEquipmentStorageEncCapProviderInstanceId }
    ::= { cucsEquipmentStorageEncCapProviderTable 1 }

CucsEquipmentStorageEncCapProviderEntry ::= SEQUENCE {
    cucsEquipmentStorageEncCapProviderInstanceId                     CucsManagedObjectId,
    cucsEquipmentStorageEncCapProviderDn                             CucsManagedObjectDn,
    cucsEquipmentStorageEncCapProviderRn                             SnmpAdminString,
    cucsEquipmentStorageEncCapProviderDeleted                        TruthValue,
    cucsEquipmentStorageEncCapProviderDeprecated                     TruthValue,
    cucsEquipmentStorageEncCapProviderElementLoadFailures            Gauge32,
    cucsEquipmentStorageEncCapProviderElementsLoaded                 Gauge32,
    cucsEquipmentStorageEncCapProviderGencount                       Gauge32,
    cucsEquipmentStorageEncCapProviderLoadErrors                     Gauge32,
    cucsEquipmentStorageEncCapProviderLoadWarnings                   Gauge32,
    cucsEquipmentStorageEncCapProviderMgmtPlaneVer                   SnmpAdminString,
    cucsEquipmentStorageEncCapProviderModel                          SnmpAdminString,
    cucsEquipmentStorageEncCapProviderPromCardType                   Gauge32,
    cucsEquipmentStorageEncCapProviderRevision                       SnmpAdminString,
    cucsEquipmentStorageEncCapProviderVendor                         SnmpAdminString
}

cucsEquipmentStorageEncCapProviderInstanceId OBJECT-TYPE
    SYNTAX       CucsManagedObjectId
    MAX-ACCESS   not-accessible
    STATUS       current
    DESCRIPTION
        "Instance identifier of the managed object."
    ::= { cucsEquipmentStorageEncCapProviderEntry 1 }

cucsEquipmentStorageEncCapProviderDn OBJECT-TYPE
    SYNTAX       CucsManagedObjectDn
    MAX-ACCESS   read-only
    STATUS       current
    DESCRIPTION
        "Cisco UCS equipment:StorageEncCapProvider:dn managed
        object property"
    ::= { cucsEquipmentStorageEncCapProviderEntry 2 }

cucsEquipmentStorageEncCapProviderRn OBJECT-TYPE
    SYNTAX       SnmpAdminString
    MAX-ACCESS   read-only
    STATUS       current
    DESCRIPTION
        "Cisco UCS equipment:StorageEncCapProvider:rn managed
        object property"
    ::= { cucsEquipmentStorageEncCapProviderEntry 3 }

cucsEquipmentStorageEncCapProviderDeleted OBJECT-TYPE
    SYNTAX       TruthValue
    MAX-ACCESS   read-only
    STATUS       current
    DESCRIPTION
        "Cisco UCS equipment:StorageEncCapProvider:deleted
        managed object property"
    ::= { cucsEquipmentStorageEncCapProviderEntry 4 }

cucsEquipmentStorageEncCapProviderDeprecated OBJECT-TYPE
    SYNTAX       TruthValue
    MAX-ACCESS   read-only
    STATUS       current
    DESCRIPTION
        "Cisco UCS equipment:StorageEncCapProvider:deprecated
        managed object property"
    ::= { cucsEquipmentStorageEncCapProviderEntry 5 }

cucsEquipmentStorageEncCapProviderElementLoadFailures OBJECT-TYPE
    SYNTAX       Gauge32
    MAX-ACCESS   read-only
    STATUS       current
    DESCRIPTION
        "Cisco UCS equipment:StorageEncCapProvider:elementLoadFailures
        managed object property"
    ::= { cucsEquipmentStorageEncCapProviderEntry 6 }

cucsEquipmentStorageEncCapProviderElementsLoaded OBJECT-TYPE
    SYNTAX       Gauge32
    MAX-ACCESS   read-only
    STATUS       current
    DESCRIPTION
        "Cisco UCS equipment:StorageEncCapProvider:elementsLoaded
        managed object property"
    ::= { cucsEquipmentStorageEncCapProviderEntry 7 }

cucsEquipmentStorageEncCapProviderGencount OBJECT-TYPE
    SYNTAX       Gauge32
    MAX-ACCESS   read-only
    STATUS       current
    DESCRIPTION
        "Cisco UCS equipment:StorageEncCapProvider:gencount
        managed object property"
    ::= { cucsEquipmentStorageEncCapProviderEntry 8 }

cucsEquipmentStorageEncCapProviderLoadErrors OBJECT-TYPE
    SYNTAX       Gauge32
    MAX-ACCESS   read-only
    STATUS       current
    DESCRIPTION
        "Cisco UCS equipment:StorageEncCapProvider:loadErrors
        managed object property"
    ::= { cucsEquipmentStorageEncCapProviderEntry 9 }

cucsEquipmentStorageEncCapProviderLoadWarnings OBJECT-TYPE
    SYNTAX       Gauge32
    MAX-ACCESS   read-only
    STATUS       current
    DESCRIPTION
        "Cisco UCS equipment:StorageEncCapProvider:loadWarnings
        managed object property"
    ::= { cucsEquipmentStorageEncCapProviderEntry 10 }

cucsEquipmentStorageEncCapProviderMgmtPlaneVer OBJECT-TYPE
    SYNTAX       SnmpAdminString
    MAX-ACCESS   read-only
    STATUS       current
    DESCRIPTION
        "Cisco UCS equipment:StorageEncCapProvider:mgmtPlaneVer
        managed object property"
    ::= { cucsEquipmentStorageEncCapProviderEntry 11 }

cucsEquipmentStorageEncCapProviderModel OBJECT-TYPE
    SYNTAX       SnmpAdminString
    MAX-ACCESS   read-only
    STATUS       current
    DESCRIPTION
        "Cisco UCS equipment:StorageEncCapProvider:model
        managed object property"
    ::= { cucsEquipmentStorageEncCapProviderEntry 12 }

cucsEquipmentStorageEncCapProviderPromCardType OBJECT-TYPE
    SYNTAX       Gauge32
    MAX-ACCESS   read-only
    STATUS       current
    DESCRIPTION
        "Cisco UCS equipment:StorageEncCapProvider:promCardType
        managed object property"
    ::= { cucsEquipmentStorageEncCapProviderEntry 13 }

cucsEquipmentStorageEncCapProviderRevision OBJECT-TYPE
    SYNTAX       SnmpAdminString
    MAX-ACCESS   read-only
    STATUS       current
    DESCRIPTION
        "Cisco UCS equipment:StorageEncCapProvider:revision
        managed object property"
    ::= { cucsEquipmentStorageEncCapProviderEntry 14 }

cucsEquipmentStorageEncCapProviderVendor OBJECT-TYPE
    SYNTAX       SnmpAdminString
    MAX-ACCESS   read-only
    STATUS       current
    DESCRIPTION
        "Cisco UCS equipment:StorageEncCapProvider:vendor
        managed object property"
    ::= { cucsEquipmentStorageEncCapProviderEntry 15 }

cucsEquipmentStorageLimitCapTable OBJECT-TYPE
    SYNTAX           SEQUENCE OF CucsEquipmentStorageLimitCapEntry
    MAX-ACCESS       not-accessible
    STATUS           current
    DESCRIPTION
        "Cisco UCS equipment:StorageLimitCap managed object table"
    ::= { cucsEquipmentObjects 153 }

cucsEquipmentStorageLimitCapEntry OBJECT-TYPE
    SYNTAX           CucsEquipmentStorageLimitCapEntry
    MAX-ACCESS       not-accessible
    STATUS           current
    DESCRIPTION
        "Entry for the cucsEquipmentStorageLimitCapTable table."
    INDEX { cucsEquipmentStorageLimitCapInstanceId }
    ::= { cucsEquipmentStorageLimitCapTable 1 }

CucsEquipmentStorageLimitCapEntry ::= SEQUENCE {
    cucsEquipmentStorageLimitCapInstanceId                           CucsManagedObjectId,
    cucsEquipmentStorageLimitCapDn                                   CucsManagedObjectDn,
    cucsEquipmentStorageLimitCapRn                                   SnmpAdminString,
    cucsEquipmentStorageLimitCapMaxLuns                              Gauge32,
    cucsEquipmentStorageLimitCapMe4308Supported                      TruthValue,
    cucsEquipmentStorageLimitCapMaxLunsPerDG                         Gauge32
}

cucsEquipmentStorageLimitCapInstanceId OBJECT-TYPE
    SYNTAX       CucsManagedObjectId
    MAX-ACCESS   not-accessible
    STATUS       current
    DESCRIPTION
        "Instance identifier of the managed object."
    ::= { cucsEquipmentStorageLimitCapEntry 1 }

cucsEquipmentStorageLimitCapDn OBJECT-TYPE
    SYNTAX       CucsManagedObjectDn
    MAX-ACCESS   read-only
    STATUS       current
    DESCRIPTION
        "Cisco UCS equipment:StorageLimitCap:dn managed object property"
    ::= { cucsEquipmentStorageLimitCapEntry 2 }

cucsEquipmentStorageLimitCapRn OBJECT-TYPE
    SYNTAX       SnmpAdminString
    MAX-ACCESS   read-only
    STATUS       current
    DESCRIPTION
        "Cisco UCS equipment:StorageLimitCap:rn managed object property"
    ::= { cucsEquipmentStorageLimitCapEntry 3 }

cucsEquipmentStorageLimitCapMaxLuns OBJECT-TYPE
    SYNTAX       Gauge32
    MAX-ACCESS   read-only
    STATUS       current
    DESCRIPTION
        "Cisco UCS equipment:StorageLimitCap:maxLuns managed
        object property"
    ::= { cucsEquipmentStorageLimitCapEntry 4 }

cucsEquipmentStorageLimitCapMe4308Supported OBJECT-TYPE
    SYNTAX       TruthValue
    MAX-ACCESS   read-only
    STATUS       current
    DESCRIPTION
        "Cisco UCS equipment:StorageLimitCap:me4308Supported
        managed object property"
    ::= { cucsEquipmentStorageLimitCapEntry 5 }

cucsEquipmentStorageLimitCapMaxLunsPerDG OBJECT-TYPE
    SYNTAX       Gauge32
    MAX-ACCESS   read-only
    STATUS       current
    DESCRIPTION
        "Cisco UCS equipment:StorageLimitCap:maxLunsPerDG
        managed object property"
    ::= { cucsEquipmentStorageLimitCapEntry 6 }

cucsEquipmentStorageSasExpanderCapProviderTable OBJECT-TYPE
    SYNTAX           SEQUENCE OF CucsEquipmentStorageSasExpanderCapProviderEntry
    MAX-ACCESS       not-accessible
    STATUS           current
    DESCRIPTION
        "Cisco UCS equipment:StorageSasExpanderCapProvider
        managed object table"
    ::= { cucsEquipmentObjects 170 }

cucsEquipmentStorageSasExpanderCapProviderEntry OBJECT-TYPE
    SYNTAX           CucsEquipmentStorageSasExpanderCapProviderEntry
    MAX-ACCESS       not-accessible
    STATUS           current
    DESCRIPTION
        "Entry for the cucsEquipmentStorageSasExpanderCapProviderTable table."
    INDEX { cucsEquipmentStorageSasExpanderCapProviderInstanceId }
    ::= { cucsEquipmentStorageSasExpanderCapProviderTable 1 }

CucsEquipmentStorageSasExpanderCapProviderEntry ::= SEQUENCE {
    cucsEquipmentStorageSasExpanderCapProviderInstanceId             CucsManagedObjectId,
    cucsEquipmentStorageSasExpanderCapProviderDn                     CucsManagedObjectDn,
    cucsEquipmentStorageSasExpanderCapProviderRn                     SnmpAdminString,
    cucsEquipmentStorageSasExpanderCapProviderDeleted                TruthValue,
    cucsEquipmentStorageSasExpanderCapProviderDeprecated             TruthValue,
    cucsEquipmentStorageSasExpanderCapProviderElementLoadFailures    Gauge32,
    cucsEquipmentStorageSasExpanderCapProviderElementsLoaded         Gauge32,
    cucsEquipmentStorageSasExpanderCapProviderGencount               Gauge32,
    cucsEquipmentStorageSasExpanderCapProviderLoadErrors             Gauge32,
    cucsEquipmentStorageSasExpanderCapProviderLoadWarnings           Gauge32,
    cucsEquipmentStorageSasExpanderCapProviderMgmtPlaneVer           SnmpAdminString,
    cucsEquipmentStorageSasExpanderCapProviderModel                  SnmpAdminString,
    cucsEquipmentStorageSasExpanderCapProviderPromCardType           Gauge32,
    cucsEquipmentStorageSasExpanderCapProviderRevision               SnmpAdminString,
    cucsEquipmentStorageSasExpanderCapProviderVendor                 SnmpAdminString
}

cucsEquipmentStorageSasExpanderCapProviderInstanceId OBJECT-TYPE
    SYNTAX       CucsManagedObjectId
    MAX-ACCESS   not-accessible
    STATUS       current
    DESCRIPTION
        "Instance identifier of the managed object."
    ::= { cucsEquipmentStorageSasExpanderCapProviderEntry 1 }

cucsEquipmentStorageSasExpanderCapProviderDn OBJECT-TYPE
    SYNTAX       CucsManagedObjectDn
    MAX-ACCESS   read-only
    STATUS       current
    DESCRIPTION
        "Cisco UCS equipment:StorageSasExpanderCapProvider:dn
        managed object property"
    ::= { cucsEquipmentStorageSasExpanderCapProviderEntry 2 }

cucsEquipmentStorageSasExpanderCapProviderRn OBJECT-TYPE
    SYNTAX       SnmpAdminString
    MAX-ACCESS   read-only
    STATUS       current
    DESCRIPTION
        "Cisco UCS equipment:StorageSasExpanderCapProvider:rn
        managed object property"
    ::= { cucsEquipmentStorageSasExpanderCapProviderEntry 3 }

cucsEquipmentStorageSasExpanderCapProviderDeleted OBJECT-TYPE
    SYNTAX       TruthValue
    MAX-ACCESS   read-only
    STATUS       current
    DESCRIPTION
        "Cisco UCS equipment:StorageSasExpanderCapProvider:deleted
        managed object property"
    ::= { cucsEquipmentStorageSasExpanderCapProviderEntry 4 }

cucsEquipmentStorageSasExpanderCapProviderDeprecated OBJECT-TYPE
    SYNTAX       TruthValue
    MAX-ACCESS   read-only
    STATUS       current
    DESCRIPTION
        "Cisco UCS equipment:StorageSasExpanderCapProvider:deprecated
        managed object property"
    ::= { cucsEquipmentStorageSasExpanderCapProviderEntry 5 }

cucsEquipmentStorageSasExpanderCapProviderElementLoadFailures OBJECT-TYPE
    SYNTAX       Gauge32
    MAX-ACCESS   read-only
    STATUS       current
    DESCRIPTION
        "Cisco UCS equipment:StorageSasExpanderCapProvider:elementLoadFail
        ures managed object property"
    ::= { cucsEquipmentStorageSasExpanderCapProviderEntry 6 }

cucsEquipmentStorageSasExpanderCapProviderElementsLoaded OBJECT-TYPE
    SYNTAX       Gauge32
    MAX-ACCESS   read-only
    STATUS       current
    DESCRIPTION
        "Cisco UCS equipment:StorageSasExpanderCapProvider:elementsLoaded
        managed object property"
    ::= { cucsEquipmentStorageSasExpanderCapProviderEntry 7 }

cucsEquipmentStorageSasExpanderCapProviderGencount OBJECT-TYPE
    SYNTAX       Gauge32
    MAX-ACCESS   read-only
    STATUS       current
    DESCRIPTION
        "Cisco UCS equipment:StorageSasExpanderCapProvider:gencount
        managed object property"
    ::= { cucsEquipmentStorageSasExpanderCapProviderEntry 8 }

cucsEquipmentStorageSasExpanderCapProviderLoadErrors OBJECT-TYPE
    SYNTAX       Gauge32
    MAX-ACCESS   read-only
    STATUS       current
    DESCRIPTION
        "Cisco UCS equipment:StorageSasExpanderCapProvider:loadErrors
        managed object property"
    ::= { cucsEquipmentStorageSasExpanderCapProviderEntry 9 }

cucsEquipmentStorageSasExpanderCapProviderLoadWarnings OBJECT-TYPE
    SYNTAX       Gauge32
    MAX-ACCESS   read-only
    STATUS       current
    DESCRIPTION
        "Cisco UCS equipment:StorageSasExpanderCapProvider:loadWarnings
        managed object property"
    ::= { cucsEquipmentStorageSasExpanderCapProviderEntry 10 }

cucsEquipmentStorageSasExpanderCapProviderMgmtPlaneVer OBJECT-TYPE
    SYNTAX       SnmpAdminString
    MAX-ACCESS   read-only
    STATUS       current
    DESCRIPTION
        "Cisco UCS equipment:StorageSasExpanderCapProvider:mgmtPlaneVer
        managed object property"
    ::= { cucsEquipmentStorageSasExpanderCapProviderEntry 11 }

cucsEquipmentStorageSasExpanderCapProviderModel OBJECT-TYPE
    SYNTAX       SnmpAdminString
    MAX-ACCESS   read-only
    STATUS       current
    DESCRIPTION
        "Cisco UCS equipment:StorageSasExpanderCapProvider:model
        managed object property"
    ::= { cucsEquipmentStorageSasExpanderCapProviderEntry 12 }

cucsEquipmentStorageSasExpanderCapProviderPromCardType OBJECT-TYPE
    SYNTAX       Gauge32
    MAX-ACCESS   read-only
    STATUS       current
    DESCRIPTION
        "Cisco UCS equipment:StorageSasExpanderCapProvider:promCardType
        managed object property"
    ::= { cucsEquipmentStorageSasExpanderCapProviderEntry 13 }

cucsEquipmentStorageSasExpanderCapProviderRevision OBJECT-TYPE
    SYNTAX       SnmpAdminString
    MAX-ACCESS   read-only
    STATUS       current
    DESCRIPTION
        "Cisco UCS equipment:StorageSasExpanderCapProvider:revision
        managed object property"
    ::= { cucsEquipmentStorageSasExpanderCapProviderEntry 14 }

cucsEquipmentStorageSasExpanderCapProviderVendor OBJECT-TYPE
    SYNTAX       SnmpAdminString
    MAX-ACCESS   read-only
    STATUS       current
    DESCRIPTION
        "Cisco UCS equipment:StorageSasExpanderCapProvider:vendor
        managed object property"
    ::= { cucsEquipmentStorageSasExpanderCapProviderEntry 15 }

cucsEquipmentStorageSasExpanderCapRefTable OBJECT-TYPE
    SYNTAX           SEQUENCE OF CucsEquipmentStorageSasExpanderCapRefEntry
    MAX-ACCESS       not-accessible
    STATUS           current
    DESCRIPTION
        "Cisco UCS equipment:StorageSasExpanderCapRef managed
        object table"
    ::= { cucsEquipmentObjects 171 }

cucsEquipmentStorageSasExpanderCapRefEntry OBJECT-TYPE
    SYNTAX           CucsEquipmentStorageSasExpanderCapRefEntry
    MAX-ACCESS       not-accessible
    STATUS           current
    DESCRIPTION
        "Entry for the cucsEquipmentStorageSasExpanderCapRefTable table."
    INDEX { cucsEquipmentStorageSasExpanderCapRefInstanceId }
    ::= { cucsEquipmentStorageSasExpanderCapRefTable 1 }

CucsEquipmentStorageSasExpanderCapRefEntry ::= SEQUENCE {
    cucsEquipmentStorageSasExpanderCapRefInstanceId                  CucsManagedObjectId,
    cucsEquipmentStorageSasExpanderCapRefDn                          CucsManagedObjectDn,
    cucsEquipmentStorageSasExpanderCapRefRn                          SnmpAdminString,
    cucsEquipmentStorageSasExpanderCapRefModel                       SnmpAdminString,
    cucsEquipmentStorageSasExpanderCapRefRevision                    SnmpAdminString,
    cucsEquipmentStorageSasExpanderCapRefVendor                      SnmpAdminString,
    cucsEquipmentStorageSasExpanderCapRefMinCimcVersion              SnmpAdminString
}

cucsEquipmentStorageSasExpanderCapRefInstanceId OBJECT-TYPE
    SYNTAX       CucsManagedObjectId
    MAX-ACCESS   not-accessible
    STATUS       current
    DESCRIPTION
        "Instance identifier of the managed object."
    ::= { cucsEquipmentStorageSasExpanderCapRefEntry 1 }

cucsEquipmentStorageSasExpanderCapRefDn OBJECT-TYPE
    SYNTAX       CucsManagedObjectDn
    MAX-ACCESS   read-only
    STATUS       current
    DESCRIPTION
        "Cisco UCS equipment:StorageSasExpanderCapRef:dn
        managed object property"
    ::= { cucsEquipmentStorageSasExpanderCapRefEntry 2 }

cucsEquipmentStorageSasExpanderCapRefRn OBJECT-TYPE
    SYNTAX       SnmpAdminString
    MAX-ACCESS   read-only
    STATUS       current
    DESCRIPTION
        "Cisco UCS equipment:StorageSasExpanderCapRef:rn
        managed object property"
    ::= { cucsEquipmentStorageSasExpanderCapRefEntry 3 }

cucsEquipmentStorageSasExpanderCapRefModel OBJECT-TYPE
    SYNTAX       SnmpAdminString
    MAX-ACCESS   read-only
    STATUS       current
    DESCRIPTION
        "Cisco UCS equipment:StorageSasExpanderCapRef:model
        managed object property"
    ::= { cucsEquipmentStorageSasExpanderCapRefEntry 4 }

cucsEquipmentStorageSasExpanderCapRefRevision OBJECT-TYPE
    SYNTAX       SnmpAdminString
    MAX-ACCESS   read-only
    STATUS       current
    DESCRIPTION
        "Cisco UCS equipment:StorageSasExpanderCapRef:revision
        managed object property"
    ::= { cucsEquipmentStorageSasExpanderCapRefEntry 5 }

cucsEquipmentStorageSasExpanderCapRefVendor OBJECT-TYPE
    SYNTAX       SnmpAdminString
    MAX-ACCESS   read-only
    STATUS       current
    DESCRIPTION
        "Cisco UCS equipment:StorageSasExpanderCapRef:vendor
        managed object property"
    ::= { cucsEquipmentStorageSasExpanderCapRefEntry 6 }

cucsEquipmentStorageSasExpanderCapRefMinCimcVersion OBJECT-TYPE
    SYNTAX       SnmpAdminString
    MAX-ACCESS   read-only
    STATUS       current
    DESCRIPTION
        "Cisco UCS equipment:StorageSasExpanderCapRef:minCimcVersion
        managed object property"
    ::= { cucsEquipmentStorageSasExpanderCapRefEntry 7 }

cucsEquipmentStorageSasExpanderDefTable OBJECT-TYPE
    SYNTAX           SEQUENCE OF CucsEquipmentStorageSasExpanderDefEntry
    MAX-ACCESS       not-accessible
    STATUS           current
    DESCRIPTION
        "Cisco UCS equipment:StorageSasExpanderDef managed object table"
    ::= { cucsEquipmentObjects 218 }

cucsEquipmentStorageSasExpanderDefEntry OBJECT-TYPE
    SYNTAX           CucsEquipmentStorageSasExpanderDefEntry
    MAX-ACCESS       not-accessible
    STATUS           current
    DESCRIPTION
        "Entry for the cucsEquipmentStorageSasExpanderDefTable table."
    INDEX { cucsEquipmentStorageSasExpanderDefInstanceId }
    ::= { cucsEquipmentStorageSasExpanderDefTable 1 }

CucsEquipmentStorageSasExpanderDefEntry ::= SEQUENCE {
    cucsEquipmentStorageSasExpanderDefInstanceId                     CucsManagedObjectId,
    cucsEquipmentStorageSasExpanderDefDn                             CucsManagedObjectDn,
    cucsEquipmentStorageSasExpanderDefRn                             SnmpAdminString,
    cucsEquipmentStorageSasExpanderDefDescr                          SnmpAdminString,
    cucsEquipmentStorageSasExpanderDefForceUpdateVersion             TruthValue,
    cucsEquipmentStorageSasExpanderDefIntId                          SnmpAdminString,
    cucsEquipmentStorageSasExpanderDefName                           SnmpAdminString,
    cucsEquipmentStorageSasExpanderDefOobInterfaceSupported          TruthValue,
    cucsEquipmentStorageSasExpanderDefPolicyLevel                    Gauge32,
    cucsEquipmentStorageSasExpanderDefPolicyOwner                    CucsPolicyPolicyOwner
}

cucsEquipmentStorageSasExpanderDefInstanceId OBJECT-TYPE
    SYNTAX       CucsManagedObjectId
    MAX-ACCESS   not-accessible
    STATUS       current
    DESCRIPTION
        "Instance identifier of the managed object."
    ::= { cucsEquipmentStorageSasExpanderDefEntry 1 }

cucsEquipmentStorageSasExpanderDefDn OBJECT-TYPE
    SYNTAX       CucsManagedObjectDn
    MAX-ACCESS   read-only
    STATUS       current
    DESCRIPTION
        "Cisco UCS equipment:StorageSasExpanderDef:dn managed
        object property"
    ::= { cucsEquipmentStorageSasExpanderDefEntry 2 }

cucsEquipmentStorageSasExpanderDefRn OBJECT-TYPE
    SYNTAX       SnmpAdminString
    MAX-ACCESS   read-only
    STATUS       current
    DESCRIPTION
        "Cisco UCS equipment:StorageSasExpanderDef:rn managed
        object property"
    ::= { cucsEquipmentStorageSasExpanderDefEntry 3 }

cucsEquipmentStorageSasExpanderDefDescr OBJECT-TYPE
    SYNTAX       SnmpAdminString
    MAX-ACCESS   read-only
    STATUS       current
    DESCRIPTION
        "Cisco UCS equipment:StorageSasExpanderDef:descr
        managed object property"
    ::= { cucsEquipmentStorageSasExpanderDefEntry 4 }

cucsEquipmentStorageSasExpanderDefForceUpdateVersion OBJECT-TYPE
    SYNTAX       TruthValue
    MAX-ACCESS   read-only
    STATUS       current
    DESCRIPTION
        "Cisco UCS equipment:StorageSasExpanderDef:forceUpdateVersion
        managed object property"
    ::= { cucsEquipmentStorageSasExpanderDefEntry 5 }

cucsEquipmentStorageSasExpanderDefIntId OBJECT-TYPE
    SYNTAX       SnmpAdminString
    MAX-ACCESS   read-only
    STATUS       current
    DESCRIPTION
        "Cisco UCS equipment:StorageSasExpanderDef:intId
        managed object property"
    ::= { cucsEquipmentStorageSasExpanderDefEntry 6 }

cucsEquipmentStorageSasExpanderDefName OBJECT-TYPE
    SYNTAX       SnmpAdminString
    MAX-ACCESS   read-only
    STATUS       current
    DESCRIPTION
        "Cisco UCS equipment:StorageSasExpanderDef:name
        managed object property"
    ::= { cucsEquipmentStorageSasExpanderDefEntry 7 }

cucsEquipmentStorageSasExpanderDefOobInterfaceSupported OBJECT-TYPE
    SYNTAX       TruthValue
    MAX-ACCESS   read-only
    STATUS       current
    DESCRIPTION
        "Cisco UCS equipment:StorageSasExpanderDef:oobInterfaceSupported
        managed object property"
    ::= { cucsEquipmentStorageSasExpanderDefEntry 8 }

cucsEquipmentStorageSasExpanderDefPolicyLevel OBJECT-TYPE
    SYNTAX       Gauge32
    MAX-ACCESS   read-only
    STATUS       current
    DESCRIPTION
        "Cisco UCS equipment:StorageSasExpanderDef:policyLevel
        managed object property"
    ::= { cucsEquipmentStorageSasExpanderDefEntry 9 }

cucsEquipmentStorageSasExpanderDefPolicyOwner OBJECT-TYPE
    SYNTAX       CucsPolicyPolicyOwner
    MAX-ACCESS   read-only
    STATUS       current
    DESCRIPTION
        "Cisco UCS equipment:StorageSasExpanderDef:policyOwner
        managed object property"
    ::= { cucsEquipmentStorageSasExpanderDefEntry 10 }

cucsEquipmentSwitchCapTable OBJECT-TYPE
    SYNTAX           SEQUENCE OF CucsEquipmentSwitchCapEntry
    MAX-ACCESS       not-accessible
    STATUS           current
    DESCRIPTION
        "Cisco UCS equipment:SwitchCap managed object table"
    ::= { cucsEquipmentObjects 68 }

cucsEquipmentSwitchCapEntry OBJECT-TYPE
    SYNTAX           CucsEquipmentSwitchCapEntry
    MAX-ACCESS       not-accessible
    STATUS           current
    DESCRIPTION
        "Entry for the cucsEquipmentSwitchCapTable table."
    INDEX { cucsEquipmentSwitchCapInstanceId }
    ::= { cucsEquipmentSwitchCapTable 1 }

CucsEquipmentSwitchCapEntry ::= SEQUENCE {
    cucsEquipmentSwitchCapInstanceId                                 CucsManagedObjectId,
    cucsEquipmentSwitchCapDn                                         CucsManagedObjectDn,
    cucsEquipmentSwitchCapRn                                         SnmpAdminString,
    cucsEquipmentSwitchCapDescr                                      SnmpAdminString,
    cucsEquipmentSwitchCapIntId                                      SnmpAdminString,
    cucsEquipmentSwitchCapMaxEth1gPort                               Gauge32,
    cucsEquipmentSwitchCapMaxEth1gSlot                               Gauge32,
    cucsEquipmentSwitchCapName                                       SnmpAdminString,
    cucsEquipmentSwitchCapFanModulesSupported                        TruthValue,
    cucsEquipmentSwitchCapLocatorBeaconSupported                     TruthValue,
    cucsEquipmentSwitchCapMaxActiveSpanSessionCount                  Gauge32,
    cucsEquipmentSwitchCapMgmtDaughterCardSlotId                     Gauge32,
    cucsEquipmentSwitchCapMaxEthPcMembers                            Gauge32,
    cucsEquipmentSwitchCapMaxFcoePcMembers                           Gauge32,
    cucsEquipmentSwitchCapPolicyLevel                                Gauge32,
    cucsEquipmentSwitchCapPolicyOwner                                CucsPolicyPolicyOwner,
    cucsEquipmentSwitchCapMaxEthPcs                                  Gauge32,
    cucsEquipmentSwitchCapMaxUplinkPorts                             Gauge32,
    cucsEquipmentSwitchCapSerenoNetflowSupported                     TruthValue,
    cucsEquipmentSwitchCapDynamicVifsSupported                       TruthValue,
    cucsEquipmentSwitchCapMaxFcPcs                                   Gauge32,
    cucsEquipmentSwitchCapMaxPortId                                  Gauge32,
    cucsEquipmentSwitchCapMaxSlot                                    Gauge32,
    cucsEquipmentSwitchCapMinActiveFan                               Gauge32,
    cucsEquipmentSwitchCapVpCompressionSupported                     TruthValue
}

cucsEquipmentSwitchCapInstanceId OBJECT-TYPE
    SYNTAX       CucsManagedObjectId
    MAX-ACCESS   not-accessible
    STATUS       current
    DESCRIPTION
        "Instance identifier of the managed object."
    ::= { cucsEquipmentSwitchCapEntry 1 }

cucsEquipmentSwitchCapDn OBJECT-TYPE
    SYNTAX       CucsManagedObjectDn
    MAX-ACCESS   read-only
    STATUS       current
    DESCRIPTION
        "Cisco UCS equipment:SwitchCap:dn managed object property"
    ::= { cucsEquipmentSwitchCapEntry 2 }

cucsEquipmentSwitchCapRn OBJECT-TYPE
    SYNTAX       SnmpAdminString
    MAX-ACCESS   read-only
    STATUS       current
    DESCRIPTION
        "Cisco UCS equipment:SwitchCap:rn managed object property"
    ::= { cucsEquipmentSwitchCapEntry 3 }

cucsEquipmentSwitchCapDescr OBJECT-TYPE
    SYNTAX       SnmpAdminString
    MAX-ACCESS   read-only
    STATUS       current
    DESCRIPTION
        "Cisco UCS equipment:SwitchCap:descr managed object property"
    ::= { cucsEquipmentSwitchCapEntry 4 }

cucsEquipmentSwitchCapIntId OBJECT-TYPE
    SYNTAX       SnmpAdminString
    MAX-ACCESS   read-only
    STATUS       current
    DESCRIPTION
        "Cisco UCS equipment:SwitchCap:intId managed object property"
    ::= { cucsEquipmentSwitchCapEntry 5 }

cucsEquipmentSwitchCapMaxEth1gPort OBJECT-TYPE
    SYNTAX       Gauge32
    MAX-ACCESS   read-only
    STATUS       current
    DESCRIPTION
        "Cisco UCS equipment:SwitchCap:maxEth1gPort managed
        object property"
    ::= { cucsEquipmentSwitchCapEntry 6 }

cucsEquipmentSwitchCapMaxEth1gSlot OBJECT-TYPE
    SYNTAX       Gauge32
    MAX-ACCESS   read-only
    STATUS       current
    DESCRIPTION
        "Cisco UCS equipment:SwitchCap:maxEth1gSlot managed
        object property"
    ::= { cucsEquipmentSwitchCapEntry 7 }

cucsEquipmentSwitchCapName OBJECT-TYPE
    SYNTAX       SnmpAdminString
    MAX-ACCESS   read-only
    STATUS       current
    DESCRIPTION
        "Cisco UCS equipment:SwitchCap:name managed object property"
    ::= { cucsEquipmentSwitchCapEntry 8 }

cucsEquipmentSwitchCapFanModulesSupported OBJECT-TYPE
    SYNTAX       TruthValue
    MAX-ACCESS   read-only
    STATUS       current
    DESCRIPTION
        "Cisco UCS equipment:SwitchCap:fanModulesSupported
        managed object property"
    ::= { cucsEquipmentSwitchCapEntry 9 }

cucsEquipmentSwitchCapLocatorBeaconSupported OBJECT-TYPE
    SYNTAX       TruthValue
    MAX-ACCESS   read-only
    STATUS       current
    DESCRIPTION
        "Cisco UCS equipment:SwitchCap:locatorBeaconSupported
        managed object property"
    ::= { cucsEquipmentSwitchCapEntry 10 }

cucsEquipmentSwitchCapMaxActiveSpanSessionCount OBJECT-TYPE
    SYNTAX       Gauge32
    MAX-ACCESS   read-only
    STATUS       current
    DESCRIPTION
        "Cisco UCS equipment:SwitchCap:maxActiveSpanSessionCount
        managed object property"
    ::= { cucsEquipmentSwitchCapEntry 11 }

cucsEquipmentSwitchCapMgmtDaughterCardSlotId OBJECT-TYPE
    SYNTAX       Gauge32
    MAX-ACCESS   read-only
    STATUS       current
    DESCRIPTION
        "Cisco UCS equipment:SwitchCap:mgmtDaughterCardSlotId
        managed object property"
    ::= { cucsEquipmentSwitchCapEntry 12 }

cucsEquipmentSwitchCapMaxEthPcMembers OBJECT-TYPE
    SYNTAX       Gauge32
    MAX-ACCESS   read-only
    STATUS       current
    DESCRIPTION
        "Cisco UCS equipment:SwitchCap:maxEthPcMembers
        managed object property"
    ::= { cucsEquipmentSwitchCapEntry 13 }

cucsEquipmentSwitchCapMaxFcoePcMembers OBJECT-TYPE
    SYNTAX       Gauge32
    MAX-ACCESS   read-only
    STATUS       current
    DESCRIPTION
        "Cisco UCS equipment:SwitchCap:maxFcoePcMembers
        managed object property"
    ::= { cucsEquipmentSwitchCapEntry 14 }

cucsEquipmentSwitchCapPolicyLevel OBJECT-TYPE
    SYNTAX       Gauge32
    MAX-ACCESS   read-only
    STATUS       current
    DESCRIPTION
        "Cisco UCS equipment:SwitchCap:policyLevel managed
        object property"
    ::= { cucsEquipmentSwitchCapEntry 15 }

cucsEquipmentSwitchCapPolicyOwner OBJECT-TYPE
    SYNTAX       CucsPolicyPolicyOwner
    MAX-ACCESS   read-only
    STATUS       current
    DESCRIPTION
        "Cisco UCS equipment:SwitchCap:policyOwner managed
        object property"
    ::= { cucsEquipmentSwitchCapEntry 16 }

cucsEquipmentSwitchCapMaxEthPcs OBJECT-TYPE
    SYNTAX       Gauge32
    MAX-ACCESS   read-only
    STATUS       current
    DESCRIPTION
        "Cisco UCS equipment:SwitchCap:maxEthPcs managed object property"
    ::= { cucsEquipmentSwitchCapEntry 17 }

cucsEquipmentSwitchCapMaxUplinkPorts OBJECT-TYPE
    SYNTAX       Gauge32
    MAX-ACCESS   read-only
    STATUS       current
    DESCRIPTION
        "Cisco UCS equipment:SwitchCap:maxUplinkPorts managed
        object property"
    ::= { cucsEquipmentSwitchCapEntry 18 }

cucsEquipmentSwitchCapSerenoNetflowSupported OBJECT-TYPE
    SYNTAX       TruthValue
    MAX-ACCESS   read-only
    STATUS       current
    DESCRIPTION
        "Cisco UCS equipment:SwitchCap:serenoNetflowSupported
        managed object property"
    ::= { cucsEquipmentSwitchCapEntry 19 }

cucsEquipmentSwitchCapDynamicVifsSupported OBJECT-TYPE
    SYNTAX       TruthValue
    MAX-ACCESS   read-only
    STATUS       current
    DESCRIPTION
        "Cisco UCS equipment:SwitchCap:dynamicVifsSupported
        managed object property"
    ::= { cucsEquipmentSwitchCapEntry 20 }

cucsEquipmentSwitchCapMaxFcPcs OBJECT-TYPE
    SYNTAX       Gauge32
    MAX-ACCESS   read-only
    STATUS       current
    DESCRIPTION
        "Cisco UCS equipment:SwitchCap:maxFcPcs managed object property"
    ::= { cucsEquipmentSwitchCapEntry 21 }

cucsEquipmentSwitchCapMaxPortId OBJECT-TYPE
    SYNTAX       Gauge32
    MAX-ACCESS   read-only
    STATUS       current
    DESCRIPTION
        "Cisco UCS equipment:SwitchCap:maxPortId managed object property"
    ::= { cucsEquipmentSwitchCapEntry 22 }

cucsEquipmentSwitchCapMaxSlot OBJECT-TYPE
    SYNTAX       Gauge32
    MAX-ACCESS   read-only
    STATUS       current
    DESCRIPTION
        "Cisco UCS equipment:SwitchCap:maxSlot managed object property"
    ::= { cucsEquipmentSwitchCapEntry 23 }

cucsEquipmentSwitchCapMinActiveFan OBJECT-TYPE
    SYNTAX       Gauge32
    MAX-ACCESS   read-only
    STATUS       current
    DESCRIPTION
        "Cisco UCS equipment:SwitchCap:minActiveFan managed
        object property"
    ::= { cucsEquipmentSwitchCapEntry 24 }

cucsEquipmentSwitchCapVpCompressionSupported OBJECT-TYPE
    SYNTAX       TruthValue
    MAX-ACCESS   read-only
    STATUS       current
    DESCRIPTION
        "Cisco UCS equipment:SwitchCap:vpCompressionSupported
        managed object property"
    ::= { cucsEquipmentSwitchCapEntry 25 }

cucsEquipmentSwitchCapProviderTable OBJECT-TYPE
    SYNTAX           SEQUENCE OF CucsEquipmentSwitchCapProviderEntry
    MAX-ACCESS       not-accessible
    STATUS           current
    DESCRIPTION
        "Cisco UCS equipment:SwitchCapProvider managed object table"
    ::= { cucsEquipmentObjects 69 }

cucsEquipmentSwitchCapProviderEntry OBJECT-TYPE
    SYNTAX           CucsEquipmentSwitchCapProviderEntry
    MAX-ACCESS       not-accessible
    STATUS           current
    DESCRIPTION
        "Entry for the cucsEquipmentSwitchCapProviderTable table."
    INDEX { cucsEquipmentSwitchCapProviderInstanceId }
    ::= { cucsEquipmentSwitchCapProviderTable 1 }

CucsEquipmentSwitchCapProviderEntry ::= SEQUENCE {
    cucsEquipmentSwitchCapProviderInstanceId                         CucsManagedObjectId,
    cucsEquipmentSwitchCapProviderDn                                 CucsManagedObjectDn,
    cucsEquipmentSwitchCapProviderRn                                 SnmpAdminString,
    cucsEquipmentSwitchCapProviderDeprecated                         TruthValue,
    cucsEquipmentSwitchCapProviderGencount                           Gauge32,
    cucsEquipmentSwitchCapProviderMgmtPlaneVer                       SnmpAdminString,
    cucsEquipmentSwitchCapProviderModel                              SnmpAdminString,
    cucsEquipmentSwitchCapProviderRevision                           SnmpAdminString,
    cucsEquipmentSwitchCapProviderVendor                             SnmpAdminString,
    cucsEquipmentSwitchCapProviderPromCardType                       Gauge32,
    cucsEquipmentSwitchCapProviderDeleted                            TruthValue,
    cucsEquipmentSwitchCapProviderElementLoadFailures                Gauge32,
    cucsEquipmentSwitchCapProviderElementsLoaded                     Gauge32,
    cucsEquipmentSwitchCapProviderLoadErrors                         Gauge32,
    cucsEquipmentSwitchCapProviderLoadWarnings                       Gauge32,
    cucsEquipmentSwitchCapProviderExpectedMemory                     Gauge32
}

cucsEquipmentSwitchCapProviderInstanceId OBJECT-TYPE
    SYNTAX       CucsManagedObjectId
    MAX-ACCESS   not-accessible
    STATUS       current
    DESCRIPTION
        "Instance identifier of the managed object."
    ::= { cucsEquipmentSwitchCapProviderEntry 1 }

cucsEquipmentSwitchCapProviderDn OBJECT-TYPE
    SYNTAX       CucsManagedObjectDn
    MAX-ACCESS   read-only
    STATUS       current
    DESCRIPTION
        "Cisco UCS equipment:SwitchCapProvider:dn managed object property"
    ::= { cucsEquipmentSwitchCapProviderEntry 2 }

cucsEquipmentSwitchCapProviderRn OBJECT-TYPE
    SYNTAX       SnmpAdminString
    MAX-ACCESS   read-only
    STATUS       current
    DESCRIPTION
        "Cisco UCS equipment:SwitchCapProvider:rn managed object property"
    ::= { cucsEquipmentSwitchCapProviderEntry 3 }

cucsEquipmentSwitchCapProviderDeprecated OBJECT-TYPE
    SYNTAX       TruthValue
    MAX-ACCESS   read-only
    STATUS       current
    DESCRIPTION
        "Cisco UCS equipment:SwitchCapProvider:deprecated
        managed object property"
    ::= { cucsEquipmentSwitchCapProviderEntry 4 }

cucsEquipmentSwitchCapProviderGencount OBJECT-TYPE
    SYNTAX       Gauge32
    MAX-ACCESS   read-only
    STATUS       current
    DESCRIPTION
        "Cisco UCS equipment:SwitchCapProvider:gencount
        managed object property"
    ::= { cucsEquipmentSwitchCapProviderEntry 5 }

cucsEquipmentSwitchCapProviderMgmtPlaneVer OBJECT-TYPE
    SYNTAX       SnmpAdminString
    MAX-ACCESS   read-only
    STATUS       current
    DESCRIPTION
        "Cisco UCS equipment:SwitchCapProvider:mgmtPlaneVer
        managed object property"
    ::= { cucsEquipmentSwitchCapProviderEntry 6 }

cucsEquipmentSwitchCapProviderModel OBJECT-TYPE
    SYNTAX       SnmpAdminString
    MAX-ACCESS   read-only
    STATUS       current
    DESCRIPTION
        "Cisco UCS equipment:SwitchCapProvider:model managed
        object property"
    ::= { cucsEquipmentSwitchCapProviderEntry 7 }

cucsEquipmentSwitchCapProviderRevision OBJECT-TYPE
    SYNTAX       SnmpAdminString
    MAX-ACCESS   read-only
    STATUS       current
    DESCRIPTION
        "Cisco UCS equipment:SwitchCapProvider:revision
        managed object property"
    ::= { cucsEquipmentSwitchCapProviderEntry 8 }

cucsEquipmentSwitchCapProviderVendor OBJECT-TYPE
    SYNTAX       SnmpAdminString
    MAX-ACCESS   read-only
    STATUS       current
    DESCRIPTION
        "Cisco UCS equipment:SwitchCapProvider:vendor managed
        object property"
    ::= { cucsEquipmentSwitchCapProviderEntry 9 }

cucsEquipmentSwitchCapProviderPromCardType OBJECT-TYPE
    SYNTAX       Gauge32
    MAX-ACCESS   read-only
    STATUS       current
    DESCRIPTION
        "Cisco UCS equipment:SwitchCapProvider:promCardType
        managed object property"
    ::= { cucsEquipmentSwitchCapProviderEntry 10 }

cucsEquipmentSwitchCapProviderDeleted OBJECT-TYPE
    SYNTAX       TruthValue
    MAX-ACCESS   read-only
    STATUS       current
    DESCRIPTION
        "Cisco UCS equipment:SwitchCapProvider:deleted
        managed object property"
    ::= { cucsEquipmentSwitchCapProviderEntry 11 }

cucsEquipmentSwitchCapProviderElementLoadFailures OBJECT-TYPE
    SYNTAX       Gauge32
    MAX-ACCESS   read-only
    STATUS       current
    DESCRIPTION
        "Cisco UCS equipment:SwitchCapProvider:elementLoadFailures
        managed object property"
    ::= { cucsEquipmentSwitchCapProviderEntry 12 }

cucsEquipmentSwitchCapProviderElementsLoaded OBJECT-TYPE
    SYNTAX       Gauge32
    MAX-ACCESS   read-only
    STATUS       current
    DESCRIPTION
        "Cisco UCS equipment:SwitchCapProvider:elementsLoaded
        managed object property"
    ::= { cucsEquipmentSwitchCapProviderEntry 13 }

cucsEquipmentSwitchCapProviderLoadErrors OBJECT-TYPE
    SYNTAX       Gauge32
    MAX-ACCESS   read-only
    STATUS       current
    DESCRIPTION
        "Cisco UCS equipment:SwitchCapProvider:loadErrors
        managed object property"
    ::= { cucsEquipmentSwitchCapProviderEntry 14 }

cucsEquipmentSwitchCapProviderLoadWarnings OBJECT-TYPE
    SYNTAX       Gauge32
    MAX-ACCESS   read-only
    STATUS       current
    DESCRIPTION
        "Cisco UCS equipment:SwitchCapProvider:loadWarnings
        managed object property"
    ::= { cucsEquipmentSwitchCapProviderEntry 15 }

cucsEquipmentSwitchCapProviderExpectedMemory OBJECT-TYPE
    SYNTAX       Gauge32
    MAX-ACCESS   read-only
    STATUS       current
    DESCRIPTION
        "Cisco UCS equipment:SwitchCapProvider:expectedMemory
        managed object property"
    ::= { cucsEquipmentSwitchCapProviderEntry 16 }

cucsEquipmentSwitchCardTable OBJECT-TYPE
    SYNTAX           SEQUENCE OF CucsEquipmentSwitchCardEntry
    MAX-ACCESS       not-accessible
    STATUS           current
    DESCRIPTION
        "Cisco UCS equipment:SwitchCard managed object table"
    ::= { cucsEquipmentObjects 70 }

cucsEquipmentSwitchCardEntry OBJECT-TYPE
    SYNTAX           CucsEquipmentSwitchCardEntry
    MAX-ACCESS       not-accessible
    STATUS           current
    DESCRIPTION
        "Entry for the cucsEquipmentSwitchCardTable table."
    INDEX { cucsEquipmentSwitchCardInstanceId }
    ::= { cucsEquipmentSwitchCardTable 1 }

CucsEquipmentSwitchCardEntry ::= SEQUENCE {
    cucsEquipmentSwitchCardInstanceId                                CucsManagedObjectId,
    cucsEquipmentSwitchCardDn                                        CucsManagedObjectDn,
    cucsEquipmentSwitchCardRn                                        SnmpAdminString,
    cucsEquipmentSwitchCardDescr                                     SnmpAdminString,
    cucsEquipmentSwitchCardFltAggr                                   Unsigned64,
    cucsEquipmentSwitchCardId                                        Gauge32,
    cucsEquipmentSwitchCardModel                                     SnmpAdminString,
    cucsEquipmentSwitchCardNumPorts                                  Gauge32,
    cucsEquipmentSwitchCardOperState                                 CucsEquipmentOperability,
    cucsEquipmentSwitchCardOperability                               CucsEquipmentOperability,
    cucsEquipmentSwitchCardPerf                                      CucsEquipmentSensorThresholdStatus,
    cucsEquipmentSwitchCardPower                                     CucsEquipmentPowerState,
    cucsEquipmentSwitchCardPresence                                  CucsEquipmentPresence,
    cucsEquipmentSwitchCardRevision                                  SnmpAdminString,
    cucsEquipmentSwitchCardSerial                                    SnmpAdminString,
    cucsEquipmentSwitchCardState                                     CucsEquipmentPowerState,
    cucsEquipmentSwitchCardThermal                                   CucsEquipmentSensorThresholdStatus,
    cucsEquipmentSwitchCardTs                                        DateAndTime,
    cucsEquipmentSwitchCardVendor                                    SnmpAdminString,
    cucsEquipmentSwitchCardVoltage                                   CucsEquipmentSensorThresholdStatus,
    cucsEquipmentSwitchCardOperQualifierReason                       SnmpAdminString
}

cucsEquipmentSwitchCardInstanceId OBJECT-TYPE
    SYNTAX       CucsManagedObjectId
    MAX-ACCESS   not-accessible
    STATUS       current
    DESCRIPTION
        "Instance identifier of the managed object."
    ::= { cucsEquipmentSwitchCardEntry 1 }

cucsEquipmentSwitchCardDn OBJECT-TYPE
    SYNTAX       CucsManagedObjectDn
    MAX-ACCESS   read-only
    STATUS       current
    DESCRIPTION
        "Cisco UCS equipment:SwitchCard:dn managed object property"
    ::= { cucsEquipmentSwitchCardEntry 2 }

cucsEquipmentSwitchCardRn OBJECT-TYPE
    SYNTAX       SnmpAdminString
    MAX-ACCESS   read-only
    STATUS       current
    DESCRIPTION
        "Cisco UCS equipment:SwitchCard:rn managed object property"
    ::= { cucsEquipmentSwitchCardEntry 3 }

cucsEquipmentSwitchCardDescr OBJECT-TYPE
    SYNTAX       SnmpAdminString
    MAX-ACCESS   read-only
    STATUS       current
    DESCRIPTION
        "Cisco UCS equipment:SwitchCard:descr managed object property"
    ::= { cucsEquipmentSwitchCardEntry 4 }

cucsEquipmentSwitchCardFltAggr OBJECT-TYPE
    SYNTAX       Unsigned64
    MAX-ACCESS   read-only
    STATUS       current
    DESCRIPTION
        "Cisco UCS equipment:SwitchCard:fltAggr managed object property"
    ::= { cucsEquipmentSwitchCardEntry 5 }

cucsEquipmentSwitchCardId OBJECT-TYPE
    SYNTAX       Gauge32
    MAX-ACCESS   read-only
    STATUS       current
    DESCRIPTION
        "Cisco UCS equipment:SwitchCard:id managed object property"
    ::= { cucsEquipmentSwitchCardEntry 6 }

cucsEquipmentSwitchCardModel OBJECT-TYPE
    SYNTAX       SnmpAdminString
    MAX-ACCESS   read-only
    STATUS       current
    DESCRIPTION
        "Cisco UCS equipment:SwitchCard:model managed object property"
    ::= { cucsEquipmentSwitchCardEntry 7 }

cucsEquipmentSwitchCardNumPorts OBJECT-TYPE
    SYNTAX       Gauge32
    MAX-ACCESS   read-only
    STATUS       current
    DESCRIPTION
        "Cisco UCS equipment:SwitchCard:numPorts managed object property"
    ::= { cucsEquipmentSwitchCardEntry 8 }

cucsEquipmentSwitchCardOperState OBJECT-TYPE
    SYNTAX       CucsEquipmentOperability
    MAX-ACCESS   read-only
    STATUS       current
    DESCRIPTION
        "Cisco UCS equipment:SwitchCard:operState managed object property"
    ::= { cucsEquipmentSwitchCardEntry 9 }

cucsEquipmentSwitchCardOperability OBJECT-TYPE
    SYNTAX       CucsEquipmentOperability
    MAX-ACCESS   read-only
    STATUS       current
    DESCRIPTION
        "Cisco UCS equipment:SwitchCard:operability managed
        object property"
    ::= { cucsEquipmentSwitchCardEntry 10 }

cucsEquipmentSwitchCardPerf OBJECT-TYPE
    SYNTAX       CucsEquipmentSensorThresholdStatus
    MAX-ACCESS   read-only
    STATUS       current
    DESCRIPTION
        "Cisco UCS equipment:SwitchCard:perf managed object property"
    ::= { cucsEquipmentSwitchCardEntry 11 }

cucsEquipmentSwitchCardPower OBJECT-TYPE
    SYNTAX       CucsEquipmentPowerState
    MAX-ACCESS   read-only
    STATUS       current
    DESCRIPTION
        "Cisco UCS equipment:SwitchCard:power managed object property"
    ::= { cucsEquipmentSwitchCardEntry 12 }

cucsEquipmentSwitchCardPresence OBJECT-TYPE
    SYNTAX       CucsEquipmentPresence
    MAX-ACCESS   read-only
    STATUS       current
    DESCRIPTION
        "Cisco UCS equipment:SwitchCard:presence managed object property"
    ::= { cucsEquipmentSwitchCardEntry 13 }

cucsEquipmentSwitchCardRevision OBJECT-TYPE
    SYNTAX       SnmpAdminString
    MAX-ACCESS   read-only
    STATUS       current
    DESCRIPTION
        "Cisco UCS equipment:SwitchCard:revision managed object property"
    ::= { cucsEquipmentSwitchCardEntry 14 }

cucsEquipmentSwitchCardSerial OBJECT-TYPE
    SYNTAX       SnmpAdminString
    MAX-ACCESS   read-only
    STATUS       current
    DESCRIPTION
        "Cisco UCS equipment:SwitchCard:serial managed object property"
    ::= { cucsEquipmentSwitchCardEntry 15 }

cucsEquipmentSwitchCardState OBJECT-TYPE
    SYNTAX       CucsEquipmentPowerState
    MAX-ACCESS   read-only
    STATUS       current
    DESCRIPTION
        "Cisco UCS equipment:SwitchCard:state managed object property"
    ::= { cucsEquipmentSwitchCardEntry 16 }

cucsEquipmentSwitchCardThermal OBJECT-TYPE
    SYNTAX       CucsEquipmentSensorThresholdStatus
    MAX-ACCESS   read-only
    STATUS       current
    DESCRIPTION
        "Cisco UCS equipment:SwitchCard:thermal managed object property"
    ::= { cucsEquipmentSwitchCardEntry 17 }

cucsEquipmentSwitchCardTs OBJECT-TYPE
    SYNTAX       DateAndTime
    MAX-ACCESS   read-only
    STATUS       current
    DESCRIPTION
        "Cisco UCS equipment:SwitchCard:ts managed object property"
    ::= { cucsEquipmentSwitchCardEntry 18 }

cucsEquipmentSwitchCardVendor OBJECT-TYPE
    SYNTAX       SnmpAdminString
    MAX-ACCESS   read-only
    STATUS       current
    DESCRIPTION
        "Cisco UCS equipment:SwitchCard:vendor managed object property"
    ::= { cucsEquipmentSwitchCardEntry 19 }

cucsEquipmentSwitchCardVoltage OBJECT-TYPE
    SYNTAX       CucsEquipmentSensorThresholdStatus
    MAX-ACCESS   read-only
    STATUS       current
    DESCRIPTION
        "Cisco UCS equipment:SwitchCard:voltage managed object property"
    ::= { cucsEquipmentSwitchCardEntry 20 }

cucsEquipmentSwitchCardOperQualifierReason OBJECT-TYPE
    SYNTAX       SnmpAdminString
    MAX-ACCESS   read-only
    STATUS       current
    DESCRIPTION
        "Cisco UCS equipment:SwitchCard:operQualifierReason
        managed object property"
    ::= { cucsEquipmentSwitchCardEntry 21 }

cucsEquipmentSwitchIOCardTable OBJECT-TYPE
    SYNTAX           SEQUENCE OF CucsEquipmentSwitchIOCardEntry
    MAX-ACCESS       not-accessible
    STATUS           current
    DESCRIPTION
        "Cisco UCS equipment:SwitchIOCard managed object table"
    ::= { cucsEquipmentObjects 136 }

cucsEquipmentSwitchIOCardEntry OBJECT-TYPE
    SYNTAX           CucsEquipmentSwitchIOCardEntry
    MAX-ACCESS       not-accessible
    STATUS           current
    DESCRIPTION
        "Entry for the cucsEquipmentSwitchIOCardTable table."
    INDEX { cucsEquipmentSwitchIOCardInstanceId }
    ::= { cucsEquipmentSwitchIOCardTable 1 }

CucsEquipmentSwitchIOCardEntry ::= SEQUENCE {
    cucsEquipmentSwitchIOCardInstanceId                              CucsManagedObjectId,
    cucsEquipmentSwitchIOCardDn                                      CucsManagedObjectDn,
    cucsEquipmentSwitchIOCardRn                                      SnmpAdminString,
    cucsEquipmentSwitchIOCardAdminPowerState                         CucsEquipmentAdminPowerState,
    cucsEquipmentSwitchIOCardBaseAddr                                InetAddressIPv4,
    cucsEquipmentSwitchIOCardChassisId                               Gauge32,
    cucsEquipmentSwitchIOCardConfigState                             CucsEquipmentChassisConfigState,
    cucsEquipmentSwitchIOCardDiscovery                               CucsEquipmentDiscoveryState,
    cucsEquipmentSwitchIOCardFeOfflineTs                             Unsigned64,
    cucsEquipmentSwitchIOCardFeReadyTs                               Unsigned64,
    cucsEquipmentSwitchIOCardFltAggr                                 Unsigned64,
    cucsEquipmentSwitchIOCardFsmDescr                                SnmpAdminString,
    cucsEquipmentSwitchIOCardFsmFlags                                SnmpAdminString,
    cucsEquipmentSwitchIOCardFsmPrev                                 SnmpAdminString,
    cucsEquipmentSwitchIOCardFsmProgr                                Gauge32,
    cucsEquipmentSwitchIOCardFsmRmtInvErrCode                        Gauge32,
    cucsEquipmentSwitchIOCardFsmRmtInvErrDescr                       SnmpAdminString,
    cucsEquipmentSwitchIOCardFsmRmtInvRslt                           CucsConditionRemoteInvRslt,
    cucsEquipmentSwitchIOCardFsmStageDescr                           SnmpAdminString,
    cucsEquipmentSwitchIOCardFsmStamp                                DateAndTime,
    cucsEquipmentSwitchIOCardFsmStatus                               SnmpAdminString,
    cucsEquipmentSwitchIOCardFsmTry                                  Gauge32,
    cucsEquipmentSwitchIOCardId                                      CucsEquipmentSwitchIOCardId,
    cucsEquipmentSwitchIOCardLcName                                  SnmpAdminString,
    cucsEquipmentSwitchIOCardLcTs                                    DateAndTime,
    cucsEquipmentSwitchIOCardMfgTime                                 DateAndTime,
    cucsEquipmentSwitchIOCardModel                                   SnmpAdminString,
    cucsEquipmentSwitchIOCardOperQualifier                           CucsEquipmentIOCardIssues,
    cucsEquipmentSwitchIOCardOperQualifierReason                     SnmpAdminString,
    cucsEquipmentSwitchIOCardOperState                               CucsEquipmentOperability,
    cucsEquipmentSwitchIOCardOperability                             CucsEquipmentOperability,
    cucsEquipmentSwitchIOCardPeerCommStatus                          CucsEquipmentCommStatus,
    cucsEquipmentSwitchIOCardPeerDn                                  SnmpAdminString,
    cucsEquipmentSwitchIOCardPerf                                    CucsEquipmentSensorThresholdStatus,
    cucsEquipmentSwitchIOCardPower                                   CucsEquipmentPowerState,
    cucsEquipmentSwitchIOCardPresence                                CucsEquipmentPresence,
    cucsEquipmentSwitchIOCardProcessorThermalState                   CucsEquipmentSensorThresholdStatus,
    cucsEquipmentSwitchIOCardRevision                                SnmpAdminString,
    cucsEquipmentSwitchIOCardSerial                                  SnmpAdminString,
    cucsEquipmentSwitchIOCardSide                                    CucsNetworkSide,
    cucsEquipmentSwitchIOCardSwitchId                                CucsNetworkSwitchId,
    cucsEquipmentSwitchIOCardThermal                                 CucsEquipmentSensorThresholdStatus,
    cucsEquipmentSwitchIOCardUpgradeStatus                           CucsMgmtUpgradeStatus,
    cucsEquipmentSwitchIOCardUsrLbl                                  SnmpAdminString,
    cucsEquipmentSwitchIOCardVendor                                  SnmpAdminString,
    cucsEquipmentSwitchIOCardVoltage                                 CucsEquipmentSensorThresholdStatus,
    cucsEquipmentSwitchIOCardAdminPeerPowerState                     CucsEquipmentAdminPowerState,
    cucsEquipmentSwitchIOCardAdminState                              CucsEquipmentChassisAdminState,
    cucsEquipmentSwitchIOCardOperEvacState                           CucsNetworkEvacState,
    cucsEquipmentSwitchIOCardPartNumber                              SnmpAdminString,
    cucsEquipmentSwitchIOCardVid                                     SnmpAdminString,
    cucsEquipmentSwitchIOCardAssetTag                                SnmpAdminString
}

cucsEquipmentSwitchIOCardInstanceId OBJECT-TYPE
    SYNTAX       CucsManagedObjectId
    MAX-ACCESS   not-accessible
    STATUS       current
    DESCRIPTION
        "Instance identifier of the managed object."
    ::= { cucsEquipmentSwitchIOCardEntry 1 }

cucsEquipmentSwitchIOCardDn OBJECT-TYPE
    SYNTAX       CucsManagedObjectDn
    MAX-ACCESS   read-only
    STATUS       current
    DESCRIPTION
        "Cisco UCS equipment:SwitchIOCard:dn managed object property"
    ::= { cucsEquipmentSwitchIOCardEntry 2 }

cucsEquipmentSwitchIOCardRn OBJECT-TYPE
    SYNTAX       SnmpAdminString
    MAX-ACCESS   read-only
    STATUS       current
    DESCRIPTION
        "Cisco UCS equipment:SwitchIOCard:rn managed object property"
    ::= { cucsEquipmentSwitchIOCardEntry 3 }

cucsEquipmentSwitchIOCardAdminPowerState OBJECT-TYPE
    SYNTAX       CucsEquipmentAdminPowerState
    MAX-ACCESS   read-only
    STATUS       current
    DESCRIPTION
        "Cisco UCS equipment:SwitchIOCard:adminPowerState
        managed object property"
    ::= { cucsEquipmentSwitchIOCardEntry 4 }

cucsEquipmentSwitchIOCardBaseAddr OBJECT-TYPE
    SYNTAX       InetAddressIPv4
    MAX-ACCESS   read-only
    STATUS       current
    DESCRIPTION
        "Cisco UCS equipment:SwitchIOCard:baseAddr managed
        object property"
    ::= { cucsEquipmentSwitchIOCardEntry 5 }

cucsEquipmentSwitchIOCardChassisId OBJECT-TYPE
    SYNTAX       Gauge32
    MAX-ACCESS   read-only
    STATUS       current
    DESCRIPTION
        "Cisco UCS equipment:SwitchIOCard:chassisId managed
        object property"
    ::= { cucsEquipmentSwitchIOCardEntry 6 }

cucsEquipmentSwitchIOCardConfigState OBJECT-TYPE
    SYNTAX       CucsEquipmentChassisConfigState
    MAX-ACCESS   read-only
    STATUS       current
    DESCRIPTION
        "Cisco UCS equipment:SwitchIOCard:configState managed
        object property"
    ::= { cucsEquipmentSwitchIOCardEntry 7 }

cucsEquipmentSwitchIOCardDiscovery OBJECT-TYPE
    SYNTAX       CucsEquipmentDiscoveryState
    MAX-ACCESS   read-only
    STATUS       current
    DESCRIPTION
        "Cisco UCS equipment:SwitchIOCard:discovery managed
        object property"
    ::= { cucsEquipmentSwitchIOCardEntry 8 }

cucsEquipmentSwitchIOCardFeOfflineTs OBJECT-TYPE
    SYNTAX       Unsigned64
    MAX-ACCESS   read-only
    STATUS       current
    DESCRIPTION
        "Cisco UCS equipment:SwitchIOCard:feOfflineTs managed
        object property"
    ::= { cucsEquipmentSwitchIOCardEntry 9 }

cucsEquipmentSwitchIOCardFeReadyTs OBJECT-TYPE
    SYNTAX       Unsigned64
    MAX-ACCESS   read-only
    STATUS       current
    DESCRIPTION
        "Cisco UCS equipment:SwitchIOCard:feReadyTs managed
        object property"
    ::= { cucsEquipmentSwitchIOCardEntry 10 }

cucsEquipmentSwitchIOCardFltAggr OBJECT-TYPE
    SYNTAX       Unsigned64
    MAX-ACCESS   read-only
    STATUS       current
    DESCRIPTION
        "Cisco UCS equipment:SwitchIOCard:fltAggr managed object property"
    ::= { cucsEquipmentSwitchIOCardEntry 11 }

cucsEquipmentSwitchIOCardFsmDescr OBJECT-TYPE
    SYNTAX       SnmpAdminString
    MAX-ACCESS   read-only
    STATUS       current
    DESCRIPTION
        "Cisco UCS equipment:SwitchIOCard:fsmDescr managed
        object property"
    ::= { cucsEquipmentSwitchIOCardEntry 12 }

cucsEquipmentSwitchIOCardFsmFlags OBJECT-TYPE
    SYNTAX       SnmpAdminString
    MAX-ACCESS   read-only
    STATUS       current
    DESCRIPTION
        "Cisco UCS equipment:SwitchIOCard:fsmFlags managed
        object property"
    ::= { cucsEquipmentSwitchIOCardEntry 13 }

cucsEquipmentSwitchIOCardFsmPrev OBJECT-TYPE
    SYNTAX       SnmpAdminString
    MAX-ACCESS   read-only
    STATUS       current
    DESCRIPTION
        "Cisco UCS equipment:SwitchIOCard:fsmPrev managed object property"
    ::= { cucsEquipmentSwitchIOCardEntry 14 }

cucsEquipmentSwitchIOCardFsmProgr OBJECT-TYPE
    SYNTAX       Gauge32
    MAX-ACCESS   read-only
    STATUS       current
    DESCRIPTION
        "Cisco UCS equipment:SwitchIOCard:fsmProgr managed
        object property"
    ::= { cucsEquipmentSwitchIOCardEntry 15 }

cucsEquipmentSwitchIOCardFsmRmtInvErrCode OBJECT-TYPE
    SYNTAX       Gauge32
    MAX-ACCESS   read-only
    STATUS       current
    DESCRIPTION
        "Cisco UCS equipment:SwitchIOCard:fsmRmtInvErrCode
        managed object property"
    ::= { cucsEquipmentSwitchIOCardEntry 16 }

cucsEquipmentSwitchIOCardFsmRmtInvErrDescr OBJECT-TYPE
    SYNTAX       SnmpAdminString
    MAX-ACCESS   read-only
    STATUS       current
    DESCRIPTION
        "Cisco UCS equipment:SwitchIOCard:fsmRmtInvErrDescr
        managed object property"
    ::= { cucsEquipmentSwitchIOCardEntry 17 }

cucsEquipmentSwitchIOCardFsmRmtInvRslt OBJECT-TYPE
    SYNTAX       CucsConditionRemoteInvRslt
    MAX-ACCESS   read-only
    STATUS       current
    DESCRIPTION
        "Cisco UCS equipment:SwitchIOCard:fsmRmtInvRslt
        managed object property"
    ::= { cucsEquipmentSwitchIOCardEntry 18 }

cucsEquipmentSwitchIOCardFsmStageDescr OBJECT-TYPE
    SYNTAX       SnmpAdminString
    MAX-ACCESS   read-only
    STATUS       current
    DESCRIPTION
        "Cisco UCS equipment:SwitchIOCard:fsmStageDescr
        managed object property"
    ::= { cucsEquipmentSwitchIOCardEntry 19 }

cucsEquipmentSwitchIOCardFsmStamp OBJECT-TYPE
    SYNTAX       DateAndTime
    MAX-ACCESS   read-only
    STATUS       current
    DESCRIPTION
        "Cisco UCS equipment:SwitchIOCard:fsmStamp managed
        object property"
    ::= { cucsEquipmentSwitchIOCardEntry 20 }

cucsEquipmentSwitchIOCardFsmStatus OBJECT-TYPE
    SYNTAX       SnmpAdminString
    MAX-ACCESS   read-only
    STATUS       current
    DESCRIPTION
        "Cisco UCS equipment:SwitchIOCard:fsmStatus managed
        object property"
    ::= { cucsEquipmentSwitchIOCardEntry 21 }

cucsEquipmentSwitchIOCardFsmTry OBJECT-TYPE
    SYNTAX       Gauge32
    MAX-ACCESS   read-only
    STATUS       current
    DESCRIPTION
        "Cisco UCS equipment:SwitchIOCard:fsmTry managed object property"
    ::= { cucsEquipmentSwitchIOCardEntry 22 }

cucsEquipmentSwitchIOCardId OBJECT-TYPE
    SYNTAX       CucsEquipmentSwitchIOCardId
    MAX-ACCESS   read-only
    STATUS       current
    DESCRIPTION
        "Cisco UCS equipment:SwitchIOCard:id managed object property"
    ::= { cucsEquipmentSwitchIOCardEntry 23 }

cucsEquipmentSwitchIOCardLcName OBJECT-TYPE
    SYNTAX       SnmpAdminString
    MAX-ACCESS   read-only
    STATUS       current
    DESCRIPTION
        "Cisco UCS equipment:SwitchIOCard:lcName managed object property"
    ::= { cucsEquipmentSwitchIOCardEntry 24 }

cucsEquipmentSwitchIOCardLcTs OBJECT-TYPE
    SYNTAX       DateAndTime
    MAX-ACCESS   read-only
    STATUS       current
    DESCRIPTION
        "Cisco UCS equipment:SwitchIOCard:lcTs managed object property"
    ::= { cucsEquipmentSwitchIOCardEntry 25 }

cucsEquipmentSwitchIOCardMfgTime OBJECT-TYPE
    SYNTAX       DateAndTime
    MAX-ACCESS   read-only
    STATUS       current
    DESCRIPTION
        "Cisco UCS equipment:SwitchIOCard:mfgTime managed object property"
    ::= { cucsEquipmentSwitchIOCardEntry 26 }

cucsEquipmentSwitchIOCardModel OBJECT-TYPE
    SYNTAX       SnmpAdminString
    MAX-ACCESS   read-only
    STATUS       current
    DESCRIPTION
        "Cisco UCS equipment:SwitchIOCard:model managed object property"
    ::= { cucsEquipmentSwitchIOCardEntry 27 }

cucsEquipmentSwitchIOCardOperQualifier OBJECT-TYPE
    SYNTAX       CucsEquipmentIOCardIssues
    MAX-ACCESS   read-only
    STATUS       current
    DESCRIPTION
        "Cisco UCS equipment:SwitchIOCard:operQualifier
        managed object property"
    ::= { cucsEquipmentSwitchIOCardEntry 28 }

cucsEquipmentSwitchIOCardOperQualifierReason OBJECT-TYPE
    SYNTAX       SnmpAdminString
    MAX-ACCESS   read-only
    STATUS       current
    DESCRIPTION
        "Cisco UCS equipment:SwitchIOCard:operQualifierReason
        managed object property"
    ::= { cucsEquipmentSwitchIOCardEntry 29 }

cucsEquipmentSwitchIOCardOperState OBJECT-TYPE
    SYNTAX       CucsEquipmentOperability
    MAX-ACCESS   read-only
    STATUS       current
    DESCRIPTION
        "Cisco UCS equipment:SwitchIOCard:operState managed
        object property"
    ::= { cucsEquipmentSwitchIOCardEntry 30 }

cucsEquipmentSwitchIOCardOperability OBJECT-TYPE
    SYNTAX       CucsEquipmentOperability
    MAX-ACCESS   read-only
    STATUS       current
    DESCRIPTION
        "Cisco UCS equipment:SwitchIOCard:operability managed
        object property"
    ::= { cucsEquipmentSwitchIOCardEntry 31 }

cucsEquipmentSwitchIOCardPeerCommStatus OBJECT-TYPE
    SYNTAX       CucsEquipmentCommStatus
    MAX-ACCESS   read-only
    STATUS       current
    DESCRIPTION
        "Cisco UCS equipment:SwitchIOCard:peerCommStatus
        managed object property"
    ::= { cucsEquipmentSwitchIOCardEntry 32 }

cucsEquipmentSwitchIOCardPeerDn OBJECT-TYPE
    SYNTAX       SnmpAdminString
    MAX-ACCESS   read-only
    STATUS       current
    DESCRIPTION
        "Cisco UCS equipment:SwitchIOCard:peerDn managed object property"
    ::= { cucsEquipmentSwitchIOCardEntry 33 }

cucsEquipmentSwitchIOCardPerf OBJECT-TYPE
    SYNTAX       CucsEquipmentSensorThresholdStatus
    MAX-ACCESS   read-only
    STATUS       current
    DESCRIPTION
        "Cisco UCS equipment:SwitchIOCard:perf managed object property"
    ::= { cucsEquipmentSwitchIOCardEntry 34 }

cucsEquipmentSwitchIOCardPower OBJECT-TYPE
    SYNTAX       CucsEquipmentPowerState
    MAX-ACCESS   read-only
    STATUS       current
    DESCRIPTION
        "Cisco UCS equipment:SwitchIOCard:power managed object property"
    ::= { cucsEquipmentSwitchIOCardEntry 35 }

cucsEquipmentSwitchIOCardPresence OBJECT-TYPE
    SYNTAX       CucsEquipmentPresence
    MAX-ACCESS   read-only
    STATUS       current
    DESCRIPTION
        "Cisco UCS equipment:SwitchIOCard:presence managed
        object property"
    ::= { cucsEquipmentSwitchIOCardEntry 36 }

cucsEquipmentSwitchIOCardProcessorThermalState OBJECT-TYPE
    SYNTAX       CucsEquipmentSensorThresholdStatus
    MAX-ACCESS   read-only
    STATUS       current
    DESCRIPTION
        "Cisco UCS equipment:SwitchIOCard:processorThermalState
        managed object property"
    ::= { cucsEquipmentSwitchIOCardEntry 37 }

cucsEquipmentSwitchIOCardRevision OBJECT-TYPE
    SYNTAX       SnmpAdminString
    MAX-ACCESS   read-only
    STATUS       current
    DESCRIPTION
        "Cisco UCS equipment:SwitchIOCard:revision managed
        object property"
    ::= { cucsEquipmentSwitchIOCardEntry 38 }

cucsEquipmentSwitchIOCardSerial OBJECT-TYPE
    SYNTAX       SnmpAdminString
    MAX-ACCESS   read-only
    STATUS       current
    DESCRIPTION
        "Cisco UCS equipment:SwitchIOCard:serial managed object property"
    ::= { cucsEquipmentSwitchIOCardEntry 39 }

cucsEquipmentSwitchIOCardSide OBJECT-TYPE
    SYNTAX       CucsNetworkSide
    MAX-ACCESS   read-only
    STATUS       current
    DESCRIPTION
        "Cisco UCS equipment:SwitchIOCard:side managed object property"
    ::= { cucsEquipmentSwitchIOCardEntry 40 }

cucsEquipmentSwitchIOCardSwitchId OBJECT-TYPE
    SYNTAX       CucsNetworkSwitchId
    MAX-ACCESS   read-only
    STATUS       current
    DESCRIPTION
        "Cisco UCS equipment:SwitchIOCard:switchId managed
        object property"
    ::= { cucsEquipmentSwitchIOCardEntry 41 }

cucsEquipmentSwitchIOCardThermal OBJECT-TYPE
    SYNTAX       CucsEquipmentSensorThresholdStatus
    MAX-ACCESS   read-only
    STATUS       current
    DESCRIPTION
        "Cisco UCS equipment:SwitchIOCard:thermal managed object property"
    ::= { cucsEquipmentSwitchIOCardEntry 42 }

cucsEquipmentSwitchIOCardUpgradeStatus OBJECT-TYPE
    SYNTAX       CucsMgmtUpgradeStatus
    MAX-ACCESS   read-only
    STATUS       current
    DESCRIPTION
        "Cisco UCS equipment:SwitchIOCard:upgradeStatus
        managed object property"
    ::= { cucsEquipmentSwitchIOCardEntry 43 }

cucsEquipmentSwitchIOCardUsrLbl OBJECT-TYPE
    SYNTAX       SnmpAdminString
    MAX-ACCESS   read-only
    STATUS       current
    DESCRIPTION
        "Cisco UCS equipment:SwitchIOCard:usrLbl managed object property"
    ::= { cucsEquipmentSwitchIOCardEntry 44 }

cucsEquipmentSwitchIOCardVendor OBJECT-TYPE
    SYNTAX       SnmpAdminString
    MAX-ACCESS   read-only
    STATUS       current
    DESCRIPTION
        "Cisco UCS equipment:SwitchIOCard:vendor managed object property"
    ::= { cucsEquipmentSwitchIOCardEntry 45 }

cucsEquipmentSwitchIOCardVoltage OBJECT-TYPE
    SYNTAX       CucsEquipmentSensorThresholdStatus
    MAX-ACCESS   read-only
    STATUS       current
    DESCRIPTION
        "Cisco UCS equipment:SwitchIOCard:voltage managed object property"
    ::= { cucsEquipmentSwitchIOCardEntry 46 }

cucsEquipmentSwitchIOCardAdminPeerPowerState OBJECT-TYPE
    SYNTAX       CucsEquipmentAdminPowerState
    MAX-ACCESS   read-only
    STATUS       current
    DESCRIPTION
        "Cisco UCS equipment:SwitchIOCard:adminPeerPowerState
        managed object property"
    ::= { cucsEquipmentSwitchIOCardEntry 47 }

cucsEquipmentSwitchIOCardAdminState OBJECT-TYPE
    SYNTAX       CucsEquipmentChassisAdminState
    MAX-ACCESS   read-only
    STATUS       current
    DESCRIPTION
        "Cisco UCS equipment:SwitchIOCard:adminState managed
        object property"
    ::= { cucsEquipmentSwitchIOCardEntry 48 }

cucsEquipmentSwitchIOCardOperEvacState OBJECT-TYPE
    SYNTAX       CucsNetworkEvacState
    MAX-ACCESS   read-only
    STATUS       current
    DESCRIPTION
        "Cisco UCS equipment:SwitchIOCard:operEvacState
        managed object property"
    ::= { cucsEquipmentSwitchIOCardEntry 49 }

cucsEquipmentSwitchIOCardPartNumber OBJECT-TYPE
    SYNTAX       SnmpAdminString
    MAX-ACCESS   read-only
    STATUS       current
    DESCRIPTION
        "Cisco UCS equipment:SwitchIOCard:partNumber managed
        object property"
    ::= { cucsEquipmentSwitchIOCardEntry 50 }

cucsEquipmentSwitchIOCardVid OBJECT-TYPE
    SYNTAX       SnmpAdminString
    MAX-ACCESS   read-only
    STATUS       current
    DESCRIPTION
        "Cisco UCS equipment:SwitchIOCard:vid managed object property"
    ::= { cucsEquipmentSwitchIOCardEntry 51 }

cucsEquipmentSwitchIOCardAssetTag OBJECT-TYPE
    SYNTAX       SnmpAdminString
    MAX-ACCESS   read-only
    STATUS       current
    DESCRIPTION
        "Cisco UCS equipment:SwitchIOCard:assetTag managed
        object property"
    ::= { cucsEquipmentSwitchIOCardEntry 52 }

cucsEquipmentSwitchIOCardCapProviderTable OBJECT-TYPE
    SYNTAX           SEQUENCE OF CucsEquipmentSwitchIOCardCapProviderEntry
    MAX-ACCESS       not-accessible
    STATUS           current
    DESCRIPTION
        "Cisco UCS equipment:SwitchIOCardCapProvider managed object table"
    ::= { cucsEquipmentObjects 137 }

cucsEquipmentSwitchIOCardCapProviderEntry OBJECT-TYPE
    SYNTAX           CucsEquipmentSwitchIOCardCapProviderEntry
    MAX-ACCESS       not-accessible
    STATUS           current
    DESCRIPTION
        "Entry for the cucsEquipmentSwitchIOCardCapProviderTable table."
    INDEX { cucsEquipmentSwitchIOCardCapProviderInstanceId }
    ::= { cucsEquipmentSwitchIOCardCapProviderTable 1 }

CucsEquipmentSwitchIOCardCapProviderEntry ::= SEQUENCE {
    cucsEquipmentSwitchIOCardCapProviderInstanceId                   CucsManagedObjectId,
    cucsEquipmentSwitchIOCardCapProviderDn                           CucsManagedObjectDn,
    cucsEquipmentSwitchIOCardCapProviderRn                           SnmpAdminString,
    cucsEquipmentSwitchIOCardCapProviderDeleted                      TruthValue,
    cucsEquipmentSwitchIOCardCapProviderDeprecated                   TruthValue,
    cucsEquipmentSwitchIOCardCapProviderElementLoadFailures          Gauge32,
    cucsEquipmentSwitchIOCardCapProviderElementsLoaded               Gauge32,
    cucsEquipmentSwitchIOCardCapProviderGencount                     Gauge32,
    cucsEquipmentSwitchIOCardCapProviderLoadErrors                   Gauge32,
    cucsEquipmentSwitchIOCardCapProviderLoadWarnings                 Gauge32,
    cucsEquipmentSwitchIOCardCapProviderMgmtPlaneVer                 SnmpAdminString,
    cucsEquipmentSwitchIOCardCapProviderModel                        SnmpAdminString,
    cucsEquipmentSwitchIOCardCapProviderPromCardType                 Gauge32,
    cucsEquipmentSwitchIOCardCapProviderRevision                     SnmpAdminString,
    cucsEquipmentSwitchIOCardCapProviderVendor                       SnmpAdminString,
    cucsEquipmentSwitchIOCardCapProviderExpectedMemory               Gauge32
}

cucsEquipmentSwitchIOCardCapProviderInstanceId OBJECT-TYPE
    SYNTAX       CucsManagedObjectId
    MAX-ACCESS   not-accessible
    STATUS       current
    DESCRIPTION
        "Instance identifier of the managed object."
    ::= { cucsEquipmentSwitchIOCardCapProviderEntry 1 }

cucsEquipmentSwitchIOCardCapProviderDn OBJECT-TYPE
    SYNTAX       CucsManagedObjectDn
    MAX-ACCESS   read-only
    STATUS       current
    DESCRIPTION
        "Cisco UCS equipment:SwitchIOCardCapProvider:dn
        managed object property"
    ::= { cucsEquipmentSwitchIOCardCapProviderEntry 2 }

cucsEquipmentSwitchIOCardCapProviderRn OBJECT-TYPE
    SYNTAX       SnmpAdminString
    MAX-ACCESS   read-only
    STATUS       current
    DESCRIPTION
        "Cisco UCS equipment:SwitchIOCardCapProvider:rn
        managed object property"
    ::= { cucsEquipmentSwitchIOCardCapProviderEntry 3 }

cucsEquipmentSwitchIOCardCapProviderDeleted OBJECT-TYPE
    SYNTAX       TruthValue
    MAX-ACCESS   read-only
    STATUS       current
    DESCRIPTION
        "Cisco UCS equipment:SwitchIOCardCapProvider:deleted
        managed object property"
    ::= { cucsEquipmentSwitchIOCardCapProviderEntry 4 }

cucsEquipmentSwitchIOCardCapProviderDeprecated OBJECT-TYPE
    SYNTAX       TruthValue
    MAX-ACCESS   read-only
    STATUS       current
    DESCRIPTION
        "Cisco UCS equipment:SwitchIOCardCapProvider:deprecated
        managed object property"
    ::= { cucsEquipmentSwitchIOCardCapProviderEntry 5 }

cucsEquipmentSwitchIOCardCapProviderElementLoadFailures OBJECT-TYPE
    SYNTAX       Gauge32
    MAX-ACCESS   read-only
    STATUS       current
    DESCRIPTION
        "Cisco UCS equipment:SwitchIOCardCapProvider:elementLoadFailures
        managed object property"
    ::= { cucsEquipmentSwitchIOCardCapProviderEntry 6 }

cucsEquipmentSwitchIOCardCapProviderElementsLoaded OBJECT-TYPE
    SYNTAX       Gauge32
    MAX-ACCESS   read-only
    STATUS       current
    DESCRIPTION
        "Cisco UCS equipment:SwitchIOCardCapProvider:elementsLoaded
        managed object property"
    ::= { cucsEquipmentSwitchIOCardCapProviderEntry 7 }

cucsEquipmentSwitchIOCardCapProviderGencount OBJECT-TYPE
    SYNTAX       Gauge32
    MAX-ACCESS   read-only
    STATUS       current
    DESCRIPTION
        "Cisco UCS equipment:SwitchIOCardCapProvider:gencount
        managed object property"
    ::= { cucsEquipmentSwitchIOCardCapProviderEntry 8 }

cucsEquipmentSwitchIOCardCapProviderLoadErrors OBJECT-TYPE
    SYNTAX       Gauge32
    MAX-ACCESS   read-only
    STATUS       current
    DESCRIPTION
        "Cisco UCS equipment:SwitchIOCardCapProvider:loadErrors
        managed object property"
    ::= { cucsEquipmentSwitchIOCardCapProviderEntry 9 }

cucsEquipmentSwitchIOCardCapProviderLoadWarnings OBJECT-TYPE
    SYNTAX       Gauge32
    MAX-ACCESS   read-only
    STATUS       current
    DESCRIPTION
        "Cisco UCS equipment:SwitchIOCardCapProvider:loadWarnings
        managed object property"
    ::= { cucsEquipmentSwitchIOCardCapProviderEntry 10 }

cucsEquipmentSwitchIOCardCapProviderMgmtPlaneVer OBJECT-TYPE
    SYNTAX       SnmpAdminString
    MAX-ACCESS   read-only
    STATUS       current
    DESCRIPTION
        "Cisco UCS equipment:SwitchIOCardCapProvider:mgmtPlaneVer
        managed object property"
    ::= { cucsEquipmentSwitchIOCardCapProviderEntry 11 }

cucsEquipmentSwitchIOCardCapProviderModel OBJECT-TYPE
    SYNTAX       SnmpAdminString
    MAX-ACCESS   read-only
    STATUS       current
    DESCRIPTION
        "Cisco UCS equipment:SwitchIOCardCapProvider:model
        managed object property"
    ::= { cucsEquipmentSwitchIOCardCapProviderEntry 12 }

cucsEquipmentSwitchIOCardCapProviderPromCardType OBJECT-TYPE
    SYNTAX       Gauge32
    MAX-ACCESS   read-only
    STATUS       current
    DESCRIPTION
        "Cisco UCS equipment:SwitchIOCardCapProvider:promCardType
        managed object property"
    ::= { cucsEquipmentSwitchIOCardCapProviderEntry 13 }

cucsEquipmentSwitchIOCardCapProviderRevision OBJECT-TYPE
    SYNTAX       SnmpAdminString
    MAX-ACCESS   read-only
    STATUS       current
    DESCRIPTION
        "Cisco UCS equipment:SwitchIOCardCapProvider:revision
        managed object property"
    ::= { cucsEquipmentSwitchIOCardCapProviderEntry 14 }

cucsEquipmentSwitchIOCardCapProviderVendor OBJECT-TYPE
    SYNTAX       SnmpAdminString
    MAX-ACCESS   read-only
    STATUS       current
    DESCRIPTION
        "Cisco UCS equipment:SwitchIOCardCapProvider:vendor
        managed object property"
    ::= { cucsEquipmentSwitchIOCardCapProviderEntry 15 }

cucsEquipmentSwitchIOCardCapProviderExpectedMemory OBJECT-TYPE
    SYNTAX       Gauge32
    MAX-ACCESS   read-only
    STATUS       current
    DESCRIPTION
        "Cisco UCS equipment:SwitchIOCardCapProvider:expectedMemory
        managed object property"
    ::= { cucsEquipmentSwitchIOCardCapProviderEntry 16 }

cucsEquipmentSwitchIOCardFsmTable OBJECT-TYPE
    SYNTAX           SEQUENCE OF CucsEquipmentSwitchIOCardFsmEntry
    MAX-ACCESS       not-accessible
    STATUS           current
    DESCRIPTION
        "Cisco UCS equipment:SwitchIOCardFsm managed object table"
    ::= { cucsEquipmentObjects 138 }

cucsEquipmentSwitchIOCardFsmEntry OBJECT-TYPE
    SYNTAX           CucsEquipmentSwitchIOCardFsmEntry
    MAX-ACCESS       not-accessible
    STATUS           current
    DESCRIPTION
        "Entry for the cucsEquipmentSwitchIOCardFsmTable table."
    INDEX { cucsEquipmentSwitchIOCardFsmInstanceId }
    ::= { cucsEquipmentSwitchIOCardFsmTable 1 }

CucsEquipmentSwitchIOCardFsmEntry ::= SEQUENCE {
    cucsEquipmentSwitchIOCardFsmInstanceId                           CucsManagedObjectId,
    cucsEquipmentSwitchIOCardFsmDn                                   CucsManagedObjectDn,
    cucsEquipmentSwitchIOCardFsmRn                                   SnmpAdminString,
    cucsEquipmentSwitchIOCardFsmCompletionTime                       DateAndTime,
    cucsEquipmentSwitchIOCardFsmCurrentFsm                           CucsEquipmentSwitchIOCardFsmCurrentFsm,
    cucsEquipmentSwitchIOCardFsmDescrData                            SnmpAdminString,
    cucsEquipmentSwitchIOCardFsmFsmStatus                            CucsFsmFsmStageStatus,
    cucsEquipmentSwitchIOCardFsmProgress                             Gauge32,
    cucsEquipmentSwitchIOCardFsmRmtErrCode                           Gauge32,
    cucsEquipmentSwitchIOCardFsmRmtErrDescr                          SnmpAdminString,
    cucsEquipmentSwitchIOCardFsmRmtRslt                              CucsConditionRemoteInvRslt
}

cucsEquipmentSwitchIOCardFsmInstanceId OBJECT-TYPE
    SYNTAX       CucsManagedObjectId
    MAX-ACCESS   not-accessible
    STATUS       current
    DESCRIPTION
        "Instance identifier of the managed object."
    ::= { cucsEquipmentSwitchIOCardFsmEntry 1 }

cucsEquipmentSwitchIOCardFsmDn OBJECT-TYPE
    SYNTAX       CucsManagedObjectDn
    MAX-ACCESS   read-only
    STATUS       current
    DESCRIPTION
        "Cisco UCS equipment:SwitchIOCardFsm:dn managed object property"
    ::= { cucsEquipmentSwitchIOCardFsmEntry 2 }

cucsEquipmentSwitchIOCardFsmRn OBJECT-TYPE
    SYNTAX       SnmpAdminString
    MAX-ACCESS   read-only
    STATUS       current
    DESCRIPTION
        "Cisco UCS equipment:SwitchIOCardFsm:rn managed object property"
    ::= { cucsEquipmentSwitchIOCardFsmEntry 3 }

cucsEquipmentSwitchIOCardFsmCompletionTime OBJECT-TYPE
    SYNTAX       DateAndTime
    MAX-ACCESS   read-only
    STATUS       current
    DESCRIPTION
        "Cisco UCS equipment:SwitchIOCardFsm:completionTime
        managed object property"
    ::= { cucsEquipmentSwitchIOCardFsmEntry 4 }

cucsEquipmentSwitchIOCardFsmCurrentFsm OBJECT-TYPE
    SYNTAX       CucsEquipmentSwitchIOCardFsmCurrentFsm
    MAX-ACCESS   read-only
    STATUS       current
    DESCRIPTION
        "Cisco UCS equipment:SwitchIOCardFsm:currentFsm
        managed object property"
    ::= { cucsEquipmentSwitchIOCardFsmEntry 5 }

cucsEquipmentSwitchIOCardFsmDescrData OBJECT-TYPE
    SYNTAX       SnmpAdminString
    MAX-ACCESS   read-only
    STATUS       current
    DESCRIPTION
        "Cisco UCS equipment:SwitchIOCardFsm:descr managed
        object property"
    ::= { cucsEquipmentSwitchIOCardFsmEntry 6 }

cucsEquipmentSwitchIOCardFsmFsmStatus OBJECT-TYPE
    SYNTAX       CucsFsmFsmStageStatus
    MAX-ACCESS   read-only
    STATUS       current
    DESCRIPTION
        "Cisco UCS equipment:SwitchIOCardFsm:fsmStatus
        managed object property"
    ::= { cucsEquipmentSwitchIOCardFsmEntry 7 }

cucsEquipmentSwitchIOCardFsmProgress OBJECT-TYPE
    SYNTAX       Gauge32
    MAX-ACCESS   read-only
    STATUS       current
    DESCRIPTION
        "Cisco UCS equipment:SwitchIOCardFsm:progress managed
        object property"
    ::= { cucsEquipmentSwitchIOCardFsmEntry 8 }

cucsEquipmentSwitchIOCardFsmRmtErrCode OBJECT-TYPE
    SYNTAX       Gauge32
    MAX-ACCESS   read-only
    STATUS       current
    DESCRIPTION
        "Cisco UCS equipment:SwitchIOCardFsm:rmtErrCode
        managed object property"
    ::= { cucsEquipmentSwitchIOCardFsmEntry 9 }

cucsEquipmentSwitchIOCardFsmRmtErrDescr OBJECT-TYPE
    SYNTAX       SnmpAdminString
    MAX-ACCESS   read-only
    STATUS       current
    DESCRIPTION
        "Cisco UCS equipment:SwitchIOCardFsm:rmtErrDescr
        managed object property"
    ::= { cucsEquipmentSwitchIOCardFsmEntry 10 }

cucsEquipmentSwitchIOCardFsmRmtRslt OBJECT-TYPE
    SYNTAX       CucsConditionRemoteInvRslt
    MAX-ACCESS   read-only
    STATUS       current
    DESCRIPTION
        "Cisco UCS equipment:SwitchIOCardFsm:rmtRslt managed
        object property"
    ::= { cucsEquipmentSwitchIOCardFsmEntry 11 }

cucsEquipmentSwitchIOCardFsmStageTable OBJECT-TYPE
    SYNTAX           SEQUENCE OF CucsEquipmentSwitchIOCardFsmStageEntry
    MAX-ACCESS       not-accessible
    STATUS           current
    DESCRIPTION
        "Cisco UCS equipment:SwitchIOCardFsmStage managed object table"
    ::= { cucsEquipmentObjects 139 }

cucsEquipmentSwitchIOCardFsmStageEntry OBJECT-TYPE
    SYNTAX           CucsEquipmentSwitchIOCardFsmStageEntry
    MAX-ACCESS       not-accessible
    STATUS           current
    DESCRIPTION
        "Entry for the cucsEquipmentSwitchIOCardFsmStageTable table."
    INDEX { cucsEquipmentSwitchIOCardFsmStageInstanceId }
    ::= { cucsEquipmentSwitchIOCardFsmStageTable 1 }

CucsEquipmentSwitchIOCardFsmStageEntry ::= SEQUENCE {
    cucsEquipmentSwitchIOCardFsmStageInstanceId                      CucsManagedObjectId,
    cucsEquipmentSwitchIOCardFsmStageDn                              CucsManagedObjectDn,
    cucsEquipmentSwitchIOCardFsmStageRn                              SnmpAdminString,
    cucsEquipmentSwitchIOCardFsmStageDescrData                       SnmpAdminString,
    cucsEquipmentSwitchIOCardFsmStageLastUpdateTime                  DateAndTime,
    cucsEquipmentSwitchIOCardFsmStageName                            CucsEquipmentSwitchIOCardFsmStageName,
    cucsEquipmentSwitchIOCardFsmStageOrder                           Gauge32,
    cucsEquipmentSwitchIOCardFsmStageRetry                           Gauge32,
    cucsEquipmentSwitchIOCardFsmStageStageStatus                     CucsFsmFsmStageStatus
}

cucsEquipmentSwitchIOCardFsmStageInstanceId OBJECT-TYPE
    SYNTAX       CucsManagedObjectId
    MAX-ACCESS   not-accessible
    STATUS       current
    DESCRIPTION
        "Instance identifier of the managed object."
    ::= { cucsEquipmentSwitchIOCardFsmStageEntry 1 }

cucsEquipmentSwitchIOCardFsmStageDn OBJECT-TYPE
    SYNTAX       CucsManagedObjectDn
    MAX-ACCESS   read-only
    STATUS       current
    DESCRIPTION
        "Cisco UCS equipment:SwitchIOCardFsmStage:dn managed
        object property"
    ::= { cucsEquipmentSwitchIOCardFsmStageEntry 2 }

cucsEquipmentSwitchIOCardFsmStageRn OBJECT-TYPE
    SYNTAX       SnmpAdminString
    MAX-ACCESS   read-only
    STATUS       current
    DESCRIPTION
        "Cisco UCS equipment:SwitchIOCardFsmStage:rn managed
        object property"
    ::= { cucsEquipmentSwitchIOCardFsmStageEntry 3 }

cucsEquipmentSwitchIOCardFsmStageDescrData OBJECT-TYPE
    SYNTAX       SnmpAdminString
    MAX-ACCESS   read-only
    STATUS       current
    DESCRIPTION
        "Cisco UCS equipment:SwitchIOCardFsmStage:descr
        managed object property"
    ::= { cucsEquipmentSwitchIOCardFsmStageEntry 4 }

cucsEquipmentSwitchIOCardFsmStageLastUpdateTime OBJECT-TYPE
    SYNTAX       DateAndTime
    MAX-ACCESS   read-only
    STATUS       current
    DESCRIPTION
        "Cisco UCS equipment:SwitchIOCardFsmStage:lastUpdateTime
        managed object property"
    ::= { cucsEquipmentSwitchIOCardFsmStageEntry 5 }

cucsEquipmentSwitchIOCardFsmStageName OBJECT-TYPE
    SYNTAX       CucsEquipmentSwitchIOCardFsmStageName
    MAX-ACCESS   read-only
    STATUS       current
    DESCRIPTION
        "Cisco UCS equipment:SwitchIOCardFsmStage:name
        managed object property"
    ::= { cucsEquipmentSwitchIOCardFsmStageEntry 6 }

cucsEquipmentSwitchIOCardFsmStageOrder OBJECT-TYPE
    SYNTAX       Gauge32
    MAX-ACCESS   read-only
    STATUS       current
    DESCRIPTION
        "Cisco UCS equipment:SwitchIOCardFsmStage:order
        managed object property"
    ::= { cucsEquipmentSwitchIOCardFsmStageEntry 7 }

cucsEquipmentSwitchIOCardFsmStageRetry OBJECT-TYPE
    SYNTAX       Gauge32
    MAX-ACCESS   read-only
    STATUS       current
    DESCRIPTION
        "Cisco UCS equipment:SwitchIOCardFsmStage:retry
        managed object property"
    ::= { cucsEquipmentSwitchIOCardFsmStageEntry 8 }

cucsEquipmentSwitchIOCardFsmStageStageStatus OBJECT-TYPE
    SYNTAX       CucsFsmFsmStageStatus
    MAX-ACCESS   read-only
    STATUS       current
    DESCRIPTION
        "Cisco UCS equipment:SwitchIOCardFsmStage:stageStatus
        managed object property"
    ::= { cucsEquipmentSwitchIOCardFsmStageEntry 9 }

cucsEquipmentSwitchIOCardFsmTaskTable OBJECT-TYPE
    SYNTAX           SEQUENCE OF CucsEquipmentSwitchIOCardFsmTaskEntry
    MAX-ACCESS       not-accessible
    STATUS           current
    DESCRIPTION
        "Cisco UCS equipment:SwitchIOCardFsmTask managed object table"
    ::= { cucsEquipmentObjects 172 }

cucsEquipmentSwitchIOCardFsmTaskEntry OBJECT-TYPE
    SYNTAX           CucsEquipmentSwitchIOCardFsmTaskEntry
    MAX-ACCESS       not-accessible
    STATUS           current
    DESCRIPTION
        "Entry for the cucsEquipmentSwitchIOCardFsmTaskTable table."
    INDEX { cucsEquipmentSwitchIOCardFsmTaskInstanceId }
    ::= { cucsEquipmentSwitchIOCardFsmTaskTable 1 }

CucsEquipmentSwitchIOCardFsmTaskEntry ::= SEQUENCE {
    cucsEquipmentSwitchIOCardFsmTaskInstanceId                       CucsManagedObjectId,
    cucsEquipmentSwitchIOCardFsmTaskDn                               CucsManagedObjectDn,
    cucsEquipmentSwitchIOCardFsmTaskRn                               SnmpAdminString,
    cucsEquipmentSwitchIOCardFsmTaskCompletion                       CucsFsmCompletion,
    cucsEquipmentSwitchIOCardFsmTaskFlags                            CucsFsmFlags,
    cucsEquipmentSwitchIOCardFsmTaskItem                             CucsEquipmentSwitchIOCardFsmTaskItem,
    cucsEquipmentSwitchIOCardFsmTaskSeqId                            Gauge32
}

cucsEquipmentSwitchIOCardFsmTaskInstanceId OBJECT-TYPE
    SYNTAX       CucsManagedObjectId
    MAX-ACCESS   not-accessible
    STATUS       current
    DESCRIPTION
        "Instance identifier of the managed object."
    ::= { cucsEquipmentSwitchIOCardFsmTaskEntry 1 }

cucsEquipmentSwitchIOCardFsmTaskDn OBJECT-TYPE
    SYNTAX       CucsManagedObjectDn
    MAX-ACCESS   read-only
    STATUS       current
    DESCRIPTION
        "Cisco UCS equipment:SwitchIOCardFsmTask:dn managed
        object property"
    ::= { cucsEquipmentSwitchIOCardFsmTaskEntry 2 }

cucsEquipmentSwitchIOCardFsmTaskRn OBJECT-TYPE
    SYNTAX       SnmpAdminString
    MAX-ACCESS   read-only
    STATUS       current
    DESCRIPTION
        "Cisco UCS equipment:SwitchIOCardFsmTask:rn managed
        object property"
    ::= { cucsEquipmentSwitchIOCardFsmTaskEntry 3 }

cucsEquipmentSwitchIOCardFsmTaskCompletion OBJECT-TYPE
    SYNTAX       CucsFsmCompletion
    MAX-ACCESS   read-only
    STATUS       current
    DESCRIPTION
        "Cisco UCS equipment:SwitchIOCardFsmTask:completion
        managed object property"
    ::= { cucsEquipmentSwitchIOCardFsmTaskEntry 4 }

cucsEquipmentSwitchIOCardFsmTaskFlags OBJECT-TYPE
    SYNTAX       CucsFsmFlags
    MAX-ACCESS   read-only
    STATUS       current
    DESCRIPTION
        "Cisco UCS equipment:SwitchIOCardFsmTask:flags
        managed object property"
    ::= { cucsEquipmentSwitchIOCardFsmTaskEntry 5 }

cucsEquipmentSwitchIOCardFsmTaskItem OBJECT-TYPE
    SYNTAX       CucsEquipmentSwitchIOCardFsmTaskItem
    MAX-ACCESS   read-only
    STATUS       current
    DESCRIPTION
        "Cisco UCS equipment:SwitchIOCardFsmTask:item managed
        object property"
    ::= { cucsEquipmentSwitchIOCardFsmTaskEntry 6 }

cucsEquipmentSwitchIOCardFsmTaskSeqId OBJECT-TYPE
    SYNTAX       Gauge32
    MAX-ACCESS   read-only
    STATUS       current
    DESCRIPTION
        "Cisco UCS equipment:SwitchIOCardFsmTask:seqId
        managed object property"
    ::= { cucsEquipmentSwitchIOCardFsmTaskEntry 7 }

cucsEquipmentSwitchTypeDefTable OBJECT-TYPE
    SYNTAX           SEQUENCE OF CucsEquipmentSwitchTypeDefEntry
    MAX-ACCESS       not-accessible
    STATUS           current
    DESCRIPTION
        "Cisco UCS equipment:SwitchTypeDef managed object table"
    ::= { cucsEquipmentObjects 140 }

cucsEquipmentSwitchTypeDefEntry OBJECT-TYPE
    SYNTAX           CucsEquipmentSwitchTypeDefEntry
    MAX-ACCESS       not-accessible
    STATUS           current
    DESCRIPTION
        "Entry for the cucsEquipmentSwitchTypeDefTable table."
    INDEX { cucsEquipmentSwitchTypeDefInstanceId }
    ::= { cucsEquipmentSwitchTypeDefTable 1 }

CucsEquipmentSwitchTypeDefEntry ::= SEQUENCE {
    cucsEquipmentSwitchTypeDefInstanceId                             CucsManagedObjectId,
    cucsEquipmentSwitchTypeDefDn                                     CucsManagedObjectDn,
    cucsEquipmentSwitchTypeDefRn                                     SnmpAdminString,
    cucsEquipmentSwitchTypeDefDescr                                  SnmpAdminString,
    cucsEquipmentSwitchTypeDefIntId                                  SnmpAdminString,
    cucsEquipmentSwitchTypeDefName                                   SnmpAdminString,
    cucsEquipmentSwitchTypeDefPolicyLevel                            Gauge32,
    cucsEquipmentSwitchTypeDefPolicyOwner                            CucsPolicyPolicyOwner,
    cucsEquipmentSwitchTypeDefType                                   SnmpAdminString
}

cucsEquipmentSwitchTypeDefInstanceId OBJECT-TYPE
    SYNTAX       CucsManagedObjectId
    MAX-ACCESS   not-accessible
    STATUS       current
    DESCRIPTION
        "Instance identifier of the managed object."
    ::= { cucsEquipmentSwitchTypeDefEntry 1 }

cucsEquipmentSwitchTypeDefDn OBJECT-TYPE
    SYNTAX       CucsManagedObjectDn
    MAX-ACCESS   read-only
    STATUS       current
    DESCRIPTION
        "Cisco UCS equipment:SwitchTypeDef:dn managed object property"
    ::= { cucsEquipmentSwitchTypeDefEntry 2 }

cucsEquipmentSwitchTypeDefRn OBJECT-TYPE
    SYNTAX       SnmpAdminString
    MAX-ACCESS   read-only
    STATUS       current
    DESCRIPTION
        "Cisco UCS equipment:SwitchTypeDef:rn managed object property"
    ::= { cucsEquipmentSwitchTypeDefEntry 3 }

cucsEquipmentSwitchTypeDefDescr OBJECT-TYPE
    SYNTAX       SnmpAdminString
    MAX-ACCESS   read-only
    STATUS       current
    DESCRIPTION
        "Cisco UCS equipment:SwitchTypeDef:descr managed object property"
    ::= { cucsEquipmentSwitchTypeDefEntry 4 }

cucsEquipmentSwitchTypeDefIntId OBJECT-TYPE
    SYNTAX       SnmpAdminString
    MAX-ACCESS   read-only
    STATUS       current
    DESCRIPTION
        "Cisco UCS equipment:SwitchTypeDef:intId managed object property"
    ::= { cucsEquipmentSwitchTypeDefEntry 5 }

cucsEquipmentSwitchTypeDefName OBJECT-TYPE
    SYNTAX       SnmpAdminString
    MAX-ACCESS   read-only
    STATUS       current
    DESCRIPTION
        "Cisco UCS equipment:SwitchTypeDef:name managed object property"
    ::= { cucsEquipmentSwitchTypeDefEntry 6 }

cucsEquipmentSwitchTypeDefPolicyLevel OBJECT-TYPE
    SYNTAX       Gauge32
    MAX-ACCESS   read-only
    STATUS       current
    DESCRIPTION
        "Cisco UCS equipment:SwitchTypeDef:policyLevel
        managed object property"
    ::= { cucsEquipmentSwitchTypeDefEntry 7 }

cucsEquipmentSwitchTypeDefPolicyOwner OBJECT-TYPE
    SYNTAX       CucsPolicyPolicyOwner
    MAX-ACCESS   read-only
    STATUS       current
    DESCRIPTION
        "Cisco UCS equipment:SwitchTypeDef:policyOwner
        managed object property"
    ::= { cucsEquipmentSwitchTypeDefEntry 8 }

cucsEquipmentSwitchTypeDefType OBJECT-TYPE
    SYNTAX       SnmpAdminString
    MAX-ACCESS   read-only
    STATUS       current
    DESCRIPTION
        "Cisco UCS equipment:SwitchTypeDef:type managed object property"
    ::= { cucsEquipmentSwitchTypeDefEntry 9 }

cucsEquipmentSystemIOControllerTable OBJECT-TYPE
    SYNTAX           SEQUENCE OF CucsEquipmentSystemIOControllerEntry
    MAX-ACCESS       not-accessible
    STATUS           current
    DESCRIPTION
        "Cisco UCS equipment:SystemIOController managed object table"
    ::= { cucsEquipmentObjects 158 }

cucsEquipmentSystemIOControllerEntry OBJECT-TYPE
    SYNTAX           CucsEquipmentSystemIOControllerEntry
    MAX-ACCESS       not-accessible
    STATUS           current
    DESCRIPTION
        "Entry for the cucsEquipmentSystemIOControllerTable table."
    INDEX { cucsEquipmentSystemIOControllerInstanceId }
    ::= { cucsEquipmentSystemIOControllerTable 1 }

CucsEquipmentSystemIOControllerEntry ::= SEQUENCE {
    cucsEquipmentSystemIOControllerInstanceId                        CucsManagedObjectId,
    cucsEquipmentSystemIOControllerDn                                CucsManagedObjectDn,
    cucsEquipmentSystemIOControllerRn                                SnmpAdminString,
    cucsEquipmentSystemIOControllerChassisId                         Gauge32,
    cucsEquipmentSystemIOControllerCheckPoint                        CucsComputeCheckPoint,
    cucsEquipmentSystemIOControllerConfigState                       CucsEquipmentChassisConfigState,
    cucsEquipmentSystemIOControllerConnPath                          CucsEquipmentConnectionStatus,
    cucsEquipmentSystemIOControllerConnStatus                        CucsEquipmentConnectionStatus,
    cucsEquipmentSystemIOControllerDiscovery                         CucsEquipmentDiscoveryState,
    cucsEquipmentSystemIOControllerFltAggr                           Unsigned64,
    cucsEquipmentSystemIOControllerId                                CucsEquipmentSystemIOControllerId,
    cucsEquipmentSystemIOControllerLcName                            SnmpAdminString,
    cucsEquipmentSystemIOControllerLcTs                              DateAndTime,
    cucsEquipmentSystemIOControllerManagingInstance                  CucsNetworkSwitchId,
    cucsEquipmentSystemIOControllerMfgTime                           DateAndTime,
    cucsEquipmentSystemIOControllerModel                             SnmpAdminString,
    cucsEquipmentSystemIOControllerOperQualifier                     CucsEquipmentIOCardIssues,
    cucsEquipmentSystemIOControllerOperQualifierReason               SnmpAdminString,
    cucsEquipmentSystemIOControllerOperState                         CucsEquipmentOperability,
    cucsEquipmentSystemIOControllerOperability                       CucsEquipmentOperability,
    cucsEquipmentSystemIOControllerPartNumber                        SnmpAdminString,
    cucsEquipmentSystemIOControllerPerf                              CucsEquipmentSensorThresholdStatus,
    cucsEquipmentSystemIOControllerPower                             CucsEquipmentPowerState,
    cucsEquipmentSystemIOControllerPresence                          CucsEquipmentPresence,
    cucsEquipmentSystemIOControllerReachability                      CucsAdaptorReachability,
    cucsEquipmentSystemIOControllerRevision                          SnmpAdminString,
    cucsEquipmentSystemIOControllerRole                              CucsEquipmentSiocRole,
    cucsEquipmentSystemIOControllerSerial                            SnmpAdminString,
    cucsEquipmentSystemIOControllerThermal                           CucsEquipmentSensorThresholdStatus,
    cucsEquipmentSystemIOControllerUsrLbl                            SnmpAdminString,
    cucsEquipmentSystemIOControllerVendor                            SnmpAdminString,
    cucsEquipmentSystemIOControllerVid                               SnmpAdminString,
    cucsEquipmentSystemIOControllerVoltage                           CucsEquipmentSensorThresholdStatus,
    cucsEquipmentSystemIOControllerAdminPowerState                   CucsEquipmentAdminPowerState,
    cucsEquipmentSystemIOControllerAdminState                        CucsEquipmentChassisAdminState,
    cucsEquipmentSystemIOControllerFsmDescr                          SnmpAdminString,
    cucsEquipmentSystemIOControllerFsmPrev                           SnmpAdminString,
    cucsEquipmentSystemIOControllerFsmProgr                          Gauge32,
    cucsEquipmentSystemIOControllerFsmRmtInvErrCode                  Gauge32,
    cucsEquipmentSystemIOControllerFsmRmtInvErrDescr                 SnmpAdminString,
    cucsEquipmentSystemIOControllerFsmRmtInvRslt                     CucsConditionRemoteInvRslt,
    cucsEquipmentSystemIOControllerFsmStageDescr                     SnmpAdminString,
    cucsEquipmentSystemIOControllerFsmStamp                          DateAndTime,
    cucsEquipmentSystemIOControllerFsmStatus                         SnmpAdminString,
    cucsEquipmentSystemIOControllerFsmTry                            Gauge32,
    cucsEquipmentSystemIOControllerReInsert                          TruthValue,
    cucsEquipmentSystemIOControllerAssetTag                          SnmpAdminString
}

cucsEquipmentSystemIOControllerInstanceId OBJECT-TYPE
    SYNTAX       CucsManagedObjectId
    MAX-ACCESS   not-accessible
    STATUS       current
    DESCRIPTION
        "Instance identifier of the managed object."
    ::= { cucsEquipmentSystemIOControllerEntry 1 }

cucsEquipmentSystemIOControllerDn OBJECT-TYPE
    SYNTAX       CucsManagedObjectDn
    MAX-ACCESS   read-only
    STATUS       current
    DESCRIPTION
        "Cisco UCS equipment:SystemIOController:dn managed
        object property"
    ::= { cucsEquipmentSystemIOControllerEntry 2 }

cucsEquipmentSystemIOControllerRn OBJECT-TYPE
    SYNTAX       SnmpAdminString
    MAX-ACCESS   read-only
    STATUS       current
    DESCRIPTION
        "Cisco UCS equipment:SystemIOController:rn managed
        object property"
    ::= { cucsEquipmentSystemIOControllerEntry 3 }

cucsEquipmentSystemIOControllerChassisId OBJECT-TYPE
    SYNTAX       Gauge32
    MAX-ACCESS   read-only
    STATUS       current
    DESCRIPTION
        "Cisco UCS equipment:SystemIOController:chassisId
        managed object property"
    ::= { cucsEquipmentSystemIOControllerEntry 4 }

cucsEquipmentSystemIOControllerCheckPoint OBJECT-TYPE
    SYNTAX       CucsComputeCheckPoint
    MAX-ACCESS   read-only
    STATUS       current
    DESCRIPTION
        "Cisco UCS equipment:SystemIOController:checkPoint
        managed object property"
    ::= { cucsEquipmentSystemIOControllerEntry 5 }

cucsEquipmentSystemIOControllerConfigState OBJECT-TYPE
    SYNTAX       CucsEquipmentChassisConfigState
    MAX-ACCESS   read-only
    STATUS       current
    DESCRIPTION
        "Cisco UCS equipment:SystemIOController:configState
        managed object property"
    ::= { cucsEquipmentSystemIOControllerEntry 6 }

cucsEquipmentSystemIOControllerConnPath OBJECT-TYPE
    SYNTAX       CucsEquipmentConnectionStatus
    MAX-ACCESS   read-only
    STATUS       current
    DESCRIPTION
        "Cisco UCS equipment:SystemIOController:connPath
        managed object property"
    ::= { cucsEquipmentSystemIOControllerEntry 7 }

cucsEquipmentSystemIOControllerConnStatus OBJECT-TYPE
    SYNTAX       CucsEquipmentConnectionStatus
    MAX-ACCESS   read-only
    STATUS       current
    DESCRIPTION
        "Cisco UCS equipment:SystemIOController:connStatus
        managed object property"
    ::= { cucsEquipmentSystemIOControllerEntry 8 }

cucsEquipmentSystemIOControllerDiscovery OBJECT-TYPE
    SYNTAX       CucsEquipmentDiscoveryState
    MAX-ACCESS   read-only
    STATUS       current
    DESCRIPTION
        "Cisco UCS equipment:SystemIOController:discovery
        managed object property"
    ::= { cucsEquipmentSystemIOControllerEntry 9 }

cucsEquipmentSystemIOControllerFltAggr OBJECT-TYPE
    SYNTAX       Unsigned64
    MAX-ACCESS   read-only
    STATUS       current
    DESCRIPTION
        "Cisco UCS equipment:SystemIOController:fltAggr
        managed object property"
    ::= { cucsEquipmentSystemIOControllerEntry 10 }

cucsEquipmentSystemIOControllerId OBJECT-TYPE
    SYNTAX       CucsEquipmentSystemIOControllerId
    MAX-ACCESS   read-only
    STATUS       current
    DESCRIPTION
        "Cisco UCS equipment:SystemIOController:id managed
        object property"
    ::= { cucsEquipmentSystemIOControllerEntry 11 }

cucsEquipmentSystemIOControllerLcName OBJECT-TYPE
    SYNTAX       SnmpAdminString
    MAX-ACCESS   read-only
    STATUS       current
    DESCRIPTION
        "Cisco UCS equipment:SystemIOController:lcName
        managed object property"
    ::= { cucsEquipmentSystemIOControllerEntry 12 }

cucsEquipmentSystemIOControllerLcTs OBJECT-TYPE
    SYNTAX       DateAndTime
    MAX-ACCESS   read-only
    STATUS       current
    DESCRIPTION
        "Cisco UCS equipment:SystemIOController:lcTs managed
        object property"
    ::= { cucsEquipmentSystemIOControllerEntry 13 }

cucsEquipmentSystemIOControllerManagingInstance OBJECT-TYPE
    SYNTAX       CucsNetworkSwitchId
    MAX-ACCESS   read-only
    STATUS       current
    DESCRIPTION
        "Cisco UCS equipment:SystemIOController:managingInstance
        managed object property"
    ::= { cucsEquipmentSystemIOControllerEntry 14 }

cucsEquipmentSystemIOControllerMfgTime OBJECT-TYPE
    SYNTAX       DateAndTime
    MAX-ACCESS   read-only
    STATUS       current
    DESCRIPTION
        "Cisco UCS equipment:SystemIOController:mfgTime
        managed object property"
    ::= { cucsEquipmentSystemIOControllerEntry 15 }

cucsEquipmentSystemIOControllerModel OBJECT-TYPE
    SYNTAX       SnmpAdminString
    MAX-ACCESS   read-only
    STATUS       current
    DESCRIPTION
        "Cisco UCS equipment:SystemIOController:model managed
        object property"
    ::= { cucsEquipmentSystemIOControllerEntry 16 }

cucsEquipmentSystemIOControllerOperQualifier OBJECT-TYPE
    SYNTAX       CucsEquipmentIOCardIssues
    MAX-ACCESS   read-only
    STATUS       current
    DESCRIPTION
        "Cisco UCS equipment:SystemIOController:operQualifier
        managed object property"
    ::= { cucsEquipmentSystemIOControllerEntry 17 }

cucsEquipmentSystemIOControllerOperQualifierReason OBJECT-TYPE
    SYNTAX       SnmpAdminString
    MAX-ACCESS   read-only
    STATUS       current
    DESCRIPTION
        "Cisco UCS equipment:SystemIOController:operQualifierReason
        managed object property"
    ::= { cucsEquipmentSystemIOControllerEntry 18 }

cucsEquipmentSystemIOControllerOperState OBJECT-TYPE
    SYNTAX       CucsEquipmentOperability
    MAX-ACCESS   read-only
    STATUS       current
    DESCRIPTION
        "Cisco UCS equipment:SystemIOController:operState
        managed object property"
    ::= { cucsEquipmentSystemIOControllerEntry 19 }

cucsEquipmentSystemIOControllerOperability OBJECT-TYPE
    SYNTAX       CucsEquipmentOperability
    MAX-ACCESS   read-only
    STATUS       current
    DESCRIPTION
        "Cisco UCS equipment:SystemIOController:operability
        managed object property"
    ::= { cucsEquipmentSystemIOControllerEntry 20 }

cucsEquipmentSystemIOControllerPartNumber OBJECT-TYPE
    SYNTAX       SnmpAdminString
    MAX-ACCESS   read-only
    STATUS       current
    DESCRIPTION
        "Cisco UCS equipment:SystemIOController:partNumber
        managed object property"
    ::= { cucsEquipmentSystemIOControllerEntry 21 }

cucsEquipmentSystemIOControllerPerf OBJECT-TYPE
    SYNTAX       CucsEquipmentSensorThresholdStatus
    MAX-ACCESS   read-only
    STATUS       current
    DESCRIPTION
        "Cisco UCS equipment:SystemIOController:perf managed
        object property"
    ::= { cucsEquipmentSystemIOControllerEntry 22 }

cucsEquipmentSystemIOControllerPower OBJECT-TYPE
    SYNTAX       CucsEquipmentPowerState
    MAX-ACCESS   read-only
    STATUS       current
    DESCRIPTION
        "Cisco UCS equipment:SystemIOController:power managed
        object property"
    ::= { cucsEquipmentSystemIOControllerEntry 23 }

cucsEquipmentSystemIOControllerPresence OBJECT-TYPE
    SYNTAX       CucsEquipmentPresence
    MAX-ACCESS   read-only
    STATUS       current
    DESCRIPTION
        "Cisco UCS equipment:SystemIOController:presence
        managed object property"
    ::= { cucsEquipmentSystemIOControllerEntry 24 }

cucsEquipmentSystemIOControllerReachability OBJECT-TYPE
    SYNTAX       CucsAdaptorReachability
    MAX-ACCESS   read-only
    STATUS       current
    DESCRIPTION
        "Cisco UCS equipment:SystemIOController:reachability
        managed object property"
    ::= { cucsEquipmentSystemIOControllerEntry 25 }

cucsEquipmentSystemIOControllerRevision OBJECT-TYPE
    SYNTAX       SnmpAdminString
    MAX-ACCESS   read-only
    STATUS       current
    DESCRIPTION
        "Cisco UCS equipment:SystemIOController:revision
        managed object property"
    ::= { cucsEquipmentSystemIOControllerEntry 26 }

cucsEquipmentSystemIOControllerRole OBJECT-TYPE
    SYNTAX       CucsEquipmentSiocRole
    MAX-ACCESS   read-only
    STATUS       current
    DESCRIPTION
        "Cisco UCS equipment:SystemIOController:role managed
        object property"
    ::= { cucsEquipmentSystemIOControllerEntry 27 }

cucsEquipmentSystemIOControllerSerial OBJECT-TYPE
    SYNTAX       SnmpAdminString
    MAX-ACCESS   read-only
    STATUS       current
    DESCRIPTION
        "Cisco UCS equipment:SystemIOController:serial
        managed object property"
    ::= { cucsEquipmentSystemIOControllerEntry 28 }

cucsEquipmentSystemIOControllerThermal OBJECT-TYPE
    SYNTAX       CucsEquipmentSensorThresholdStatus
    MAX-ACCESS   read-only
    STATUS       current
    DESCRIPTION
        "Cisco UCS equipment:SystemIOController:thermal
        managed object property"
    ::= { cucsEquipmentSystemIOControllerEntry 29 }

cucsEquipmentSystemIOControllerUsrLbl OBJECT-TYPE
    SYNTAX       SnmpAdminString
    MAX-ACCESS   read-only
    STATUS       current
    DESCRIPTION
        "Cisco UCS equipment:SystemIOController:usrLbl
        managed object property"
    ::= { cucsEquipmentSystemIOControllerEntry 30 }

cucsEquipmentSystemIOControllerVendor OBJECT-TYPE
    SYNTAX       SnmpAdminString
    MAX-ACCESS   read-only
    STATUS       current
    DESCRIPTION
        "Cisco UCS equipment:SystemIOController:vendor
        managed object property"
    ::= { cucsEquipmentSystemIOControllerEntry 31 }

cucsEquipmentSystemIOControllerVid OBJECT-TYPE
    SYNTAX       SnmpAdminString
    MAX-ACCESS   read-only
    STATUS       current
    DESCRIPTION
        "Cisco UCS equipment:SystemIOController:vid managed
        object property"
    ::= { cucsEquipmentSystemIOControllerEntry 32 }

cucsEquipmentSystemIOControllerVoltage OBJECT-TYPE
    SYNTAX       CucsEquipmentSensorThresholdStatus
    MAX-ACCESS   read-only
    STATUS       current
    DESCRIPTION
        "Cisco UCS equipment:SystemIOController:voltage
        managed object property"
    ::= { cucsEquipmentSystemIOControllerEntry 33 }

cucsEquipmentSystemIOControllerAdminPowerState OBJECT-TYPE
    SYNTAX       CucsEquipmentAdminPowerState
    MAX-ACCESS   read-only
    STATUS       current
    DESCRIPTION
        "Cisco UCS equipment:SystemIOController:adminPowerState
        managed object property"
    ::= { cucsEquipmentSystemIOControllerEntry 34 }

cucsEquipmentSystemIOControllerAdminState OBJECT-TYPE
    SYNTAX       CucsEquipmentChassisAdminState
    MAX-ACCESS   read-only
    STATUS       current
    DESCRIPTION
        "Cisco UCS equipment:SystemIOController:adminState
        managed object property"
    ::= { cucsEquipmentSystemIOControllerEntry 35 }

cucsEquipmentSystemIOControllerFsmDescr OBJECT-TYPE
    SYNTAX       SnmpAdminString
    MAX-ACCESS   read-only
    STATUS       current
    DESCRIPTION
        "Cisco UCS equipment:SystemIOController:fsmDescr
        managed object property"
    ::= { cucsEquipmentSystemIOControllerEntry 36 }

cucsEquipmentSystemIOControllerFsmPrev OBJECT-TYPE
    SYNTAX       SnmpAdminString
    MAX-ACCESS   read-only
    STATUS       current
    DESCRIPTION
        "Cisco UCS equipment:SystemIOController:fsmPrev
        managed object property"
    ::= { cucsEquipmentSystemIOControllerEntry 37 }

cucsEquipmentSystemIOControllerFsmProgr OBJECT-TYPE
    SYNTAX       Gauge32
    MAX-ACCESS   read-only
    STATUS       current
    DESCRIPTION
        "Cisco UCS equipment:SystemIOController:fsmProgr
        managed object property"
    ::= { cucsEquipmentSystemIOControllerEntry 38 }

cucsEquipmentSystemIOControllerFsmRmtInvErrCode OBJECT-TYPE
    SYNTAX       Gauge32
    MAX-ACCESS   read-only
    STATUS       current
    DESCRIPTION
        "Cisco UCS equipment:SystemIOController:fsmRmtInvErrCode
        managed object property"
    ::= { cucsEquipmentSystemIOControllerEntry 39 }

cucsEquipmentSystemIOControllerFsmRmtInvErrDescr OBJECT-TYPE
    SYNTAX       SnmpAdminString
    MAX-ACCESS   read-only
    STATUS       current
    DESCRIPTION
        "Cisco UCS equipment:SystemIOController:fsmRmtInvErrDescr
        managed object property"
    ::= { cucsEquipmentSystemIOControllerEntry 40 }

cucsEquipmentSystemIOControllerFsmRmtInvRslt OBJECT-TYPE
    SYNTAX       CucsConditionRemoteInvRslt
    MAX-ACCESS   read-only
    STATUS       current
    DESCRIPTION
        "Cisco UCS equipment:SystemIOController:fsmRmtInvRslt
        managed object property"
    ::= { cucsEquipmentSystemIOControllerEntry 41 }

cucsEquipmentSystemIOControllerFsmStageDescr OBJECT-TYPE
    SYNTAX       SnmpAdminString
    MAX-ACCESS   read-only
    STATUS       current
    DESCRIPTION
        "Cisco UCS equipment:SystemIOController:fsmStageDescr
        managed object property"
    ::= { cucsEquipmentSystemIOControllerEntry 42 }

cucsEquipmentSystemIOControllerFsmStamp OBJECT-TYPE
    SYNTAX       DateAndTime
    MAX-ACCESS   read-only
    STATUS       current
    DESCRIPTION
        "Cisco UCS equipment:SystemIOController:fsmStamp
        managed object property"
    ::= { cucsEquipmentSystemIOControllerEntry 43 }

cucsEquipmentSystemIOControllerFsmStatus OBJECT-TYPE
    SYNTAX       SnmpAdminString
    MAX-ACCESS   read-only
    STATUS       current
    DESCRIPTION
        "Cisco UCS equipment:SystemIOController:fsmStatus
        managed object property"
    ::= { cucsEquipmentSystemIOControllerEntry 44 }

cucsEquipmentSystemIOControllerFsmTry OBJECT-TYPE
    SYNTAX       Gauge32
    MAX-ACCESS   read-only
    STATUS       current
    DESCRIPTION
        "Cisco UCS equipment:SystemIOController:fsmTry
        managed object property"
    ::= { cucsEquipmentSystemIOControllerEntry 45 }

cucsEquipmentSystemIOControllerReInsert OBJECT-TYPE
    SYNTAX       TruthValue
    MAX-ACCESS   read-only
    STATUS       current
    DESCRIPTION
        "Cisco UCS equipment:SystemIOController:reInsert
        managed object property"
    ::= { cucsEquipmentSystemIOControllerEntry 46 }

cucsEquipmentSystemIOControllerAssetTag OBJECT-TYPE
    SYNTAX       SnmpAdminString
    MAX-ACCESS   read-only
    STATUS       current
    DESCRIPTION
        "Cisco UCS equipment:SystemIOController:assetTag
        managed object property"
    ::= { cucsEquipmentSystemIOControllerEntry 47 }

cucsEquipmentSystemIOControllerFsmTable OBJECT-TYPE
    SYNTAX           SEQUENCE OF CucsEquipmentSystemIOControllerFsmEntry
    MAX-ACCESS       not-accessible
    STATUS           current
    DESCRIPTION
        "Cisco UCS equipment:SystemIOControllerFsm managed object table"
    ::= { cucsEquipmentObjects 219 }

cucsEquipmentSystemIOControllerFsmEntry OBJECT-TYPE
    SYNTAX           CucsEquipmentSystemIOControllerFsmEntry
    MAX-ACCESS       not-accessible
    STATUS           current
    DESCRIPTION
        "Entry for the cucsEquipmentSystemIOControllerFsmTable table."
    INDEX { cucsEquipmentSystemIOControllerFsmInstanceId }
    ::= { cucsEquipmentSystemIOControllerFsmTable 1 }

CucsEquipmentSystemIOControllerFsmEntry ::= SEQUENCE {
    cucsEquipmentSystemIOControllerFsmInstanceId                     CucsManagedObjectId,
    cucsEquipmentSystemIOControllerFsmDn                             CucsManagedObjectDn,
    cucsEquipmentSystemIOControllerFsmRn                             SnmpAdminString,
    cucsEquipmentSystemIOControllerFsmCompletionTime                 DateAndTime,
    cucsEquipmentSystemIOControllerFsmCurrentFsm                     CucsEquipmentSystemIOControllerFsmCurrentFsm,
    cucsEquipmentSystemIOControllerFsmDescrData                      SnmpAdminString,
    cucsEquipmentSystemIOControllerFsmFsmStatus                      CucsFsmFsmStageStatus,
    cucsEquipmentSystemIOControllerFsmProgress                       Gauge32,
    cucsEquipmentSystemIOControllerFsmRmtErrCode                     Gauge32,
    cucsEquipmentSystemIOControllerFsmRmtErrDescr                    SnmpAdminString,
    cucsEquipmentSystemIOControllerFsmRmtRslt                        CucsConditionRemoteInvRslt
}

cucsEquipmentSystemIOControllerFsmInstanceId OBJECT-TYPE
    SYNTAX       CucsManagedObjectId
    MAX-ACCESS   not-accessible
    STATUS       current
    DESCRIPTION
        "Instance identifier of the managed object."
    ::= { cucsEquipmentSystemIOControllerFsmEntry 1 }

cucsEquipmentSystemIOControllerFsmDn OBJECT-TYPE
    SYNTAX       CucsManagedObjectDn
    MAX-ACCESS   read-only
    STATUS       current
    DESCRIPTION
        "Cisco UCS equipment:SystemIOControllerFsm:dn managed
        object property"
    ::= { cucsEquipmentSystemIOControllerFsmEntry 2 }

cucsEquipmentSystemIOControllerFsmRn OBJECT-TYPE
    SYNTAX       SnmpAdminString
    MAX-ACCESS   read-only
    STATUS       current
    DESCRIPTION
        "Cisco UCS equipment:SystemIOControllerFsm:rn managed
        object property"
    ::= { cucsEquipmentSystemIOControllerFsmEntry 3 }

cucsEquipmentSystemIOControllerFsmCompletionTime OBJECT-TYPE
    SYNTAX       DateAndTime
    MAX-ACCESS   read-only
    STATUS       current
    DESCRIPTION
        "Cisco UCS equipment:SystemIOControllerFsm:completionTime
        managed object property"
    ::= { cucsEquipmentSystemIOControllerFsmEntry 4 }

cucsEquipmentSystemIOControllerFsmCurrentFsm OBJECT-TYPE
    SYNTAX       CucsEquipmentSystemIOControllerFsmCurrentFsm
    MAX-ACCESS   read-only
    STATUS       current
    DESCRIPTION
        "Cisco UCS equipment:SystemIOControllerFsm:currentFsm
        managed object property"
    ::= { cucsEquipmentSystemIOControllerFsmEntry 5 }

cucsEquipmentSystemIOControllerFsmDescrData OBJECT-TYPE
    SYNTAX       SnmpAdminString
    MAX-ACCESS   read-only
    STATUS       current
    DESCRIPTION
        "Cisco UCS equipment:SystemIOControllerFsm:descr
        managed object property"
    ::= { cucsEquipmentSystemIOControllerFsmEntry 6 }

cucsEquipmentSystemIOControllerFsmFsmStatus OBJECT-TYPE
    SYNTAX       CucsFsmFsmStageStatus
    MAX-ACCESS   read-only
    STATUS       current
    DESCRIPTION
        "Cisco UCS equipment:SystemIOControllerFsm:fsmStatus
        managed object property"
    ::= { cucsEquipmentSystemIOControllerFsmEntry 7 }

cucsEquipmentSystemIOControllerFsmProgress OBJECT-TYPE
    SYNTAX       Gauge32
    MAX-ACCESS   read-only
    STATUS       current
    DESCRIPTION
        "Cisco UCS equipment:SystemIOControllerFsm:progress
        managed object property"
    ::= { cucsEquipmentSystemIOControllerFsmEntry 8 }

cucsEquipmentSystemIOControllerFsmRmtErrCode OBJECT-TYPE
    SYNTAX       Gauge32
    MAX-ACCESS   read-only
    STATUS       current
    DESCRIPTION
        "Cisco UCS equipment:SystemIOControllerFsm:rmtErrCode
        managed object property"
    ::= { cucsEquipmentSystemIOControllerFsmEntry 9 }

cucsEquipmentSystemIOControllerFsmRmtErrDescr OBJECT-TYPE
    SYNTAX       SnmpAdminString
    MAX-ACCESS   read-only
    STATUS       current
    DESCRIPTION
        "Cisco UCS equipment:SystemIOControllerFsm:rmtErrDescr
        managed object property"
    ::= { cucsEquipmentSystemIOControllerFsmEntry 10 }

cucsEquipmentSystemIOControllerFsmRmtRslt OBJECT-TYPE
    SYNTAX       CucsConditionRemoteInvRslt
    MAX-ACCESS   read-only
    STATUS       current
    DESCRIPTION
        "Cisco UCS equipment:SystemIOControllerFsm:rmtRslt
        managed object property"
    ::= { cucsEquipmentSystemIOControllerFsmEntry 11 }

cucsEquipmentSystemIOControllerFsmStageTable OBJECT-TYPE
    SYNTAX           SEQUENCE OF CucsEquipmentSystemIOControllerFsmStageEntry
    MAX-ACCESS       not-accessible
    STATUS           current
    DESCRIPTION
        "Cisco UCS equipment:SystemIOControllerFsmStage
        managed object table"
    ::= { cucsEquipmentObjects 220 }

cucsEquipmentSystemIOControllerFsmStageEntry OBJECT-TYPE
    SYNTAX           CucsEquipmentSystemIOControllerFsmStageEntry
    MAX-ACCESS       not-accessible
    STATUS           current
    DESCRIPTION
        "Entry for the cucsEquipmentSystemIOControllerFsmStageTable table."
    INDEX { cucsEquipmentSystemIOControllerFsmStageInstanceId }
    ::= { cucsEquipmentSystemIOControllerFsmStageTable 1 }

CucsEquipmentSystemIOControllerFsmStageEntry ::= SEQUENCE {
    cucsEquipmentSystemIOControllerFsmStageInstanceId                CucsManagedObjectId,
    cucsEquipmentSystemIOControllerFsmStageDn                        CucsManagedObjectDn,
    cucsEquipmentSystemIOControllerFsmStageRn                        SnmpAdminString,
    cucsEquipmentSystemIOControllerFsmStageDescrData                 SnmpAdminString,
    cucsEquipmentSystemIOControllerFsmStageLastUpdateTime            DateAndTime,
    cucsEquipmentSystemIOControllerFsmStageName                      CucsEquipmentSystemIOControllerFsmStageName,
    cucsEquipmentSystemIOControllerFsmStageOrder                     Gauge32,
    cucsEquipmentSystemIOControllerFsmStageRetry                     Gauge32,
    cucsEquipmentSystemIOControllerFsmStageStageStatus               CucsFsmFsmStageStatus
}

cucsEquipmentSystemIOControllerFsmStageInstanceId OBJECT-TYPE
    SYNTAX       CucsManagedObjectId
    MAX-ACCESS   not-accessible
    STATUS       current
    DESCRIPTION
        "Instance identifier of the managed object."
    ::= { cucsEquipmentSystemIOControllerFsmStageEntry 1 }

cucsEquipmentSystemIOControllerFsmStageDn OBJECT-TYPE
    SYNTAX       CucsManagedObjectDn
    MAX-ACCESS   read-only
    STATUS       current
    DESCRIPTION
        "Cisco UCS equipment:SystemIOControllerFsmStage:dn
        managed object property"
    ::= { cucsEquipmentSystemIOControllerFsmStageEntry 2 }

cucsEquipmentSystemIOControllerFsmStageRn OBJECT-TYPE
    SYNTAX       SnmpAdminString
    MAX-ACCESS   read-only
    STATUS       current
    DESCRIPTION
        "Cisco UCS equipment:SystemIOControllerFsmStage:rn
        managed object property"
    ::= { cucsEquipmentSystemIOControllerFsmStageEntry 3 }

cucsEquipmentSystemIOControllerFsmStageDescrData OBJECT-TYPE
    SYNTAX       SnmpAdminString
    MAX-ACCESS   read-only
    STATUS       current
    DESCRIPTION
        "Cisco UCS equipment:SystemIOControllerFsmStage:descr
        managed object property"
    ::= { cucsEquipmentSystemIOControllerFsmStageEntry 4 }

cucsEquipmentSystemIOControllerFsmStageLastUpdateTime OBJECT-TYPE
    SYNTAX       DateAndTime
    MAX-ACCESS   read-only
    STATUS       current
    DESCRIPTION
        "Cisco UCS equipment:SystemIOControllerFsmStage:lastUpdateTime
        managed object property"
    ::= { cucsEquipmentSystemIOControllerFsmStageEntry 5 }

cucsEquipmentSystemIOControllerFsmStageName OBJECT-TYPE
    SYNTAX       CucsEquipmentSystemIOControllerFsmStageName
    MAX-ACCESS   read-only
    STATUS       current
    DESCRIPTION
        "Cisco UCS equipment:SystemIOControllerFsmStage:name
        managed object property"
    ::= { cucsEquipmentSystemIOControllerFsmStageEntry 6 }

cucsEquipmentSystemIOControllerFsmStageOrder OBJECT-TYPE
    SYNTAX       Gauge32
    MAX-ACCESS   read-only
    STATUS       current
    DESCRIPTION
        "Cisco UCS equipment:SystemIOControllerFsmStage:order
        managed object property"
    ::= { cucsEquipmentSystemIOControllerFsmStageEntry 7 }

cucsEquipmentSystemIOControllerFsmStageRetry OBJECT-TYPE
    SYNTAX       Gauge32
    MAX-ACCESS   read-only
    STATUS       current
    DESCRIPTION
        "Cisco UCS equipment:SystemIOControllerFsmStage:retry
        managed object property"
    ::= { cucsEquipmentSystemIOControllerFsmStageEntry 8 }

cucsEquipmentSystemIOControllerFsmStageStageStatus OBJECT-TYPE
    SYNTAX       CucsFsmFsmStageStatus
    MAX-ACCESS   read-only
    STATUS       current
    DESCRIPTION
        "Cisco UCS equipment:SystemIOControllerFsmStage:stageStatus
        managed object property"
    ::= { cucsEquipmentSystemIOControllerFsmStageEntry 9 }

cucsEquipmentSystemIOControllerFsmTaskTable OBJECT-TYPE
    SYNTAX           SEQUENCE OF CucsEquipmentSystemIOControllerFsmTaskEntry
    MAX-ACCESS       not-accessible
    STATUS           current
    DESCRIPTION
        "Cisco UCS equipment:SystemIOControllerFsmTask
        managed object table"
    ::= { cucsEquipmentObjects 221 }

cucsEquipmentSystemIOControllerFsmTaskEntry OBJECT-TYPE
    SYNTAX           CucsEquipmentSystemIOControllerFsmTaskEntry
    MAX-ACCESS       not-accessible
    STATUS           current
    DESCRIPTION
        "Entry for the cucsEquipmentSystemIOControllerFsmTaskTable table."
    INDEX { cucsEquipmentSystemIOControllerFsmTaskInstanceId }
    ::= { cucsEquipmentSystemIOControllerFsmTaskTable 1 }

CucsEquipmentSystemIOControllerFsmTaskEntry ::= SEQUENCE {
    cucsEquipmentSystemIOControllerFsmTaskInstanceId                 CucsManagedObjectId,
    cucsEquipmentSystemIOControllerFsmTaskDn                         CucsManagedObjectDn,
    cucsEquipmentSystemIOControllerFsmTaskRn                         SnmpAdminString,
    cucsEquipmentSystemIOControllerFsmTaskCompletion                 CucsFsmCompletion,
    cucsEquipmentSystemIOControllerFsmTaskFlags                      CucsFsmFlags,
    cucsEquipmentSystemIOControllerFsmTaskItem                       CucsEquipmentSystemIOControllerFsmTaskItem,
    cucsEquipmentSystemIOControllerFsmTaskSeqId                      Gauge32
}

cucsEquipmentSystemIOControllerFsmTaskInstanceId OBJECT-TYPE
    SYNTAX       CucsManagedObjectId
    MAX-ACCESS   not-accessible
    STATUS       current
    DESCRIPTION
        "Instance identifier of the managed object."
    ::= { cucsEquipmentSystemIOControllerFsmTaskEntry 1 }

cucsEquipmentSystemIOControllerFsmTaskDn OBJECT-TYPE
    SYNTAX       CucsManagedObjectDn
    MAX-ACCESS   read-only
    STATUS       current
    DESCRIPTION
        "Cisco UCS equipment:SystemIOControllerFsmTask:dn
        managed object property"
    ::= { cucsEquipmentSystemIOControllerFsmTaskEntry 2 }

cucsEquipmentSystemIOControllerFsmTaskRn OBJECT-TYPE
    SYNTAX       SnmpAdminString
    MAX-ACCESS   read-only
    STATUS       current
    DESCRIPTION
        "Cisco UCS equipment:SystemIOControllerFsmTask:rn
        managed object property"
    ::= { cucsEquipmentSystemIOControllerFsmTaskEntry 3 }

cucsEquipmentSystemIOControllerFsmTaskCompletion OBJECT-TYPE
    SYNTAX       CucsFsmCompletion
    MAX-ACCESS   read-only
    STATUS       current
    DESCRIPTION
        "Cisco UCS equipment:SystemIOControllerFsmTask:completion
        managed object property"
    ::= { cucsEquipmentSystemIOControllerFsmTaskEntry 4 }

cucsEquipmentSystemIOControllerFsmTaskFlags OBJECT-TYPE
    SYNTAX       CucsFsmFlags
    MAX-ACCESS   read-only
    STATUS       current
    DESCRIPTION
        "Cisco UCS equipment:SystemIOControllerFsmTask:flags
        managed object property"
    ::= { cucsEquipmentSystemIOControllerFsmTaskEntry 5 }

cucsEquipmentSystemIOControllerFsmTaskItem OBJECT-TYPE
    SYNTAX       CucsEquipmentSystemIOControllerFsmTaskItem
    MAX-ACCESS   read-only
    STATUS       current
    DESCRIPTION
        "Cisco UCS equipment:SystemIOControllerFsmTask:item
        managed object property"
    ::= { cucsEquipmentSystemIOControllerFsmTaskEntry 6 }

cucsEquipmentSystemIOControllerFsmTaskSeqId OBJECT-TYPE
    SYNTAX       Gauge32
    MAX-ACCESS   read-only
    STATUS       current
    DESCRIPTION
        "Cisco UCS equipment:SystemIOControllerFsmTask:seqId
        managed object property"
    ::= { cucsEquipmentSystemIOControllerFsmTaskEntry 7 }

cucsEquipmentTierTable OBJECT-TYPE
    SYNTAX           SEQUENCE OF CucsEquipmentTierEntry
    MAX-ACCESS       not-accessible
    STATUS           current
    DESCRIPTION
        "Cisco UCS equipment:Tier managed object table"
    ::= { cucsEquipmentObjects 202 }

cucsEquipmentTierEntry OBJECT-TYPE
    SYNTAX           CucsEquipmentTierEntry
    MAX-ACCESS       not-accessible
    STATUS           current
    DESCRIPTION
        "Entry for the cucsEquipmentTierTable table."
    INDEX { cucsEquipmentTierInstanceId }
    ::= { cucsEquipmentTierTable 1 }

CucsEquipmentTierEntry ::= SEQUENCE {
    cucsEquipmentTierInstanceId                                      CucsManagedObjectId,
    cucsEquipmentTierDn                                              CucsManagedObjectDn,
    cucsEquipmentTierRn                                              SnmpAdminString,
    cucsEquipmentTierApply                                           CucsEquipmentApply,
    cucsEquipmentTierDescr                                           SnmpAdminString,
    cucsEquipmentTierIntId                                           SnmpAdminString,
    cucsEquipmentTierName                                            SnmpAdminString,
    cucsEquipmentTierPolicyLevel                                     Gauge32,
    cucsEquipmentTierPolicyOwner                                     CucsPolicyPolicyOwner,
    cucsEquipmentTierSrcTemplName                                    SnmpAdminString
}

cucsEquipmentTierInstanceId OBJECT-TYPE
    SYNTAX       CucsManagedObjectId
    MAX-ACCESS   not-accessible
    STATUS       current
    DESCRIPTION
        "Instance identifier of the managed object."
    ::= { cucsEquipmentTierEntry 1 }

cucsEquipmentTierDn OBJECT-TYPE
    SYNTAX       CucsManagedObjectDn
    MAX-ACCESS   read-only
    STATUS       current
    DESCRIPTION
        "Cisco UCS equipment:Tier:dn managed object property"
    ::= { cucsEquipmentTierEntry 2 }

cucsEquipmentTierRn OBJECT-TYPE
    SYNTAX       SnmpAdminString
    MAX-ACCESS   read-only
    STATUS       current
    DESCRIPTION
        "Cisco UCS equipment:Tier:rn managed object property"
    ::= { cucsEquipmentTierEntry 3 }

cucsEquipmentTierApply OBJECT-TYPE
    SYNTAX       CucsEquipmentApply
    MAX-ACCESS   read-only
    STATUS       current
    DESCRIPTION
        "Cisco UCS equipment:Tier:apply managed object property"
    ::= { cucsEquipmentTierEntry 4 }

cucsEquipmentTierDescr OBJECT-TYPE
    SYNTAX       SnmpAdminString
    MAX-ACCESS   read-only
    STATUS       current
    DESCRIPTION
        "Cisco UCS equipment:Tier:descr managed object property"
    ::= { cucsEquipmentTierEntry 5 }

cucsEquipmentTierIntId OBJECT-TYPE
    SYNTAX       SnmpAdminString
    MAX-ACCESS   read-only
    STATUS       current
    DESCRIPTION
        "Cisco UCS equipment:Tier:intId managed object property"
    ::= { cucsEquipmentTierEntry 6 }

cucsEquipmentTierName OBJECT-TYPE
    SYNTAX       SnmpAdminString
    MAX-ACCESS   read-only
    STATUS       current
    DESCRIPTION
        "Cisco UCS equipment:Tier:name managed object property"
    ::= { cucsEquipmentTierEntry 7 }

cucsEquipmentTierPolicyLevel OBJECT-TYPE
    SYNTAX       Gauge32
    MAX-ACCESS   read-only
    STATUS       current
    DESCRIPTION
        "Cisco UCS equipment:Tier:policyLevel managed object property"
    ::= { cucsEquipmentTierEntry 8 }

cucsEquipmentTierPolicyOwner OBJECT-TYPE
    SYNTAX       CucsPolicyPolicyOwner
    MAX-ACCESS   read-only
    STATUS       current
    DESCRIPTION
        "Cisco UCS equipment:Tier:policyOwner managed object property"
    ::= { cucsEquipmentTierEntry 9 }

cucsEquipmentTierSrcTemplName OBJECT-TYPE
    SYNTAX       SnmpAdminString
    MAX-ACCESS   read-only
    STATUS       current
    DESCRIPTION
        "Cisco UCS equipment:Tier:srcTemplName managed object property"
    ::= { cucsEquipmentTierEntry 10 }

cucsEquipmentTpmTable OBJECT-TYPE
    SYNTAX           SEQUENCE OF CucsEquipmentTpmEntry
    MAX-ACCESS       not-accessible
    STATUS           current
    DESCRIPTION
        "Cisco UCS equipment:Tpm managed object table"
    ::= { cucsEquipmentObjects 122 }

cucsEquipmentTpmEntry OBJECT-TYPE
    SYNTAX           CucsEquipmentTpmEntry
    MAX-ACCESS       not-accessible
    STATUS           current
    DESCRIPTION
        "Entry for the cucsEquipmentTpmTable table."
    INDEX { cucsEquipmentTpmInstanceId }
    ::= { cucsEquipmentTpmTable 1 }

CucsEquipmentTpmEntry ::= SEQUENCE {
    cucsEquipmentTpmInstanceId                                       CucsManagedObjectId,
    cucsEquipmentTpmDn                                               CucsManagedObjectDn,
    cucsEquipmentTpmRn                                               SnmpAdminString,
    cucsEquipmentTpmActiveStatus                                     CucsEquipmentActiveStatus,
    cucsEquipmentTpmEnabledStatus                                    CucsEquipmentEnabledStatus,
    cucsEquipmentTpmId                                               Gauge32,
    cucsEquipmentTpmModel                                            SnmpAdminString,
    cucsEquipmentTpmOwnership                                        CucsEquipmentOwnership,
    cucsEquipmentTpmPasswordState                                    CucsEquipmentPasswordState,
    cucsEquipmentTpmPresence                                         CucsEquipmentPresence,
    cucsEquipmentTpmRevision                                         SnmpAdminString,
    cucsEquipmentTpmSerial                                           SnmpAdminString,
    cucsEquipmentTpmTpmRevision                                      SnmpAdminString,
    cucsEquipmentTpmType                                             CucsEquipmentTpmType,
    cucsEquipmentTpmVendor                                           SnmpAdminString,
    cucsEquipmentTpmAdminAction                                      CucsEquipmentAdminActionType,
    cucsEquipmentTpmConfigState                                      CucsEquipmentConfigState
}

cucsEquipmentTpmInstanceId OBJECT-TYPE
    SYNTAX       CucsManagedObjectId
    MAX-ACCESS   not-accessible
    STATUS       current
    DESCRIPTION
        "Instance identifier of the managed object."
    ::= { cucsEquipmentTpmEntry 1 }

cucsEquipmentTpmDn OBJECT-TYPE
    SYNTAX       CucsManagedObjectDn
    MAX-ACCESS   read-only
    STATUS       current
    DESCRIPTION
        "Cisco UCS equipment:Tpm:dn managed object property"
    ::= { cucsEquipmentTpmEntry 2 }

cucsEquipmentTpmRn OBJECT-TYPE
    SYNTAX       SnmpAdminString
    MAX-ACCESS   read-only
    STATUS       current
    DESCRIPTION
        "Cisco UCS equipment:Tpm:rn managed object property"
    ::= { cucsEquipmentTpmEntry 3 }

cucsEquipmentTpmActiveStatus OBJECT-TYPE
    SYNTAX       CucsEquipmentActiveStatus
    MAX-ACCESS   read-only
    STATUS       current
    DESCRIPTION
        "Cisco UCS equipment:Tpm:activeStatus managed object property"
    ::= { cucsEquipmentTpmEntry 4 }

cucsEquipmentTpmEnabledStatus OBJECT-TYPE
    SYNTAX       CucsEquipmentEnabledStatus
    MAX-ACCESS   read-only
    STATUS       current
    DESCRIPTION
        "Cisco UCS equipment:Tpm:enabledStatus managed object property"
    ::= { cucsEquipmentTpmEntry 5 }

cucsEquipmentTpmId OBJECT-TYPE
    SYNTAX       Gauge32
    MAX-ACCESS   read-only
    STATUS       current
    DESCRIPTION
        "Cisco UCS equipment:Tpm:id managed object property"
    ::= { cucsEquipmentTpmEntry 6 }

cucsEquipmentTpmModel OBJECT-TYPE
    SYNTAX       SnmpAdminString
    MAX-ACCESS   read-only
    STATUS       current
    DESCRIPTION
        "Cisco UCS equipment:Tpm:model managed object property"
    ::= { cucsEquipmentTpmEntry 7 }

cucsEquipmentTpmOwnership OBJECT-TYPE
    SYNTAX       CucsEquipmentOwnership
    MAX-ACCESS   read-only
    STATUS       current
    DESCRIPTION
        "Cisco UCS equipment:Tpm:ownership managed object property"
    ::= { cucsEquipmentTpmEntry 8 }

cucsEquipmentTpmPasswordState OBJECT-TYPE
    SYNTAX       CucsEquipmentPasswordState
    MAX-ACCESS   read-only
    STATUS       current
    DESCRIPTION
        "Cisco UCS equipment:Tpm:passwordState managed object property"
    ::= { cucsEquipmentTpmEntry 9 }

cucsEquipmentTpmPresence OBJECT-TYPE
    SYNTAX       CucsEquipmentPresence
    MAX-ACCESS   read-only
    STATUS       current
    DESCRIPTION
        "Cisco UCS equipment:Tpm:presence managed object property"
    ::= { cucsEquipmentTpmEntry 10 }

cucsEquipmentTpmRevision OBJECT-TYPE
    SYNTAX       SnmpAdminString
    MAX-ACCESS   read-only
    STATUS       current
    DESCRIPTION
        "Cisco UCS equipment:Tpm:revision managed object property"
    ::= { cucsEquipmentTpmEntry 11 }

cucsEquipmentTpmSerial OBJECT-TYPE
    SYNTAX       SnmpAdminString
    MAX-ACCESS   read-only
    STATUS       current
    DESCRIPTION
        "Cisco UCS equipment:Tpm:serial managed object property"
    ::= { cucsEquipmentTpmEntry 12 }

cucsEquipmentTpmTpmRevision OBJECT-TYPE
    SYNTAX       SnmpAdminString
    MAX-ACCESS   read-only
    STATUS       current
    DESCRIPTION
        "Cisco UCS equipment:Tpm:tpmRevision managed object property"
    ::= { cucsEquipmentTpmEntry 13 }

cucsEquipmentTpmType OBJECT-TYPE
    SYNTAX       CucsEquipmentTpmType
    MAX-ACCESS   read-only
    STATUS       current
    DESCRIPTION
        "Cisco UCS equipment:Tpm:type managed object property"
    ::= { cucsEquipmentTpmEntry 14 }

cucsEquipmentTpmVendor OBJECT-TYPE
    SYNTAX       SnmpAdminString
    MAX-ACCESS   read-only
    STATUS       current
    DESCRIPTION
        "Cisco UCS equipment:Tpm:vendor managed object property"
    ::= { cucsEquipmentTpmEntry 15 }

cucsEquipmentTpmAdminAction OBJECT-TYPE
    SYNTAX       CucsEquipmentAdminActionType
    MAX-ACCESS   read-only
    STATUS       current
    DESCRIPTION
        "Cisco UCS equipment:Tpm:adminAction managed object property"
    ::= { cucsEquipmentTpmEntry 16 }

cucsEquipmentTpmConfigState OBJECT-TYPE
    SYNTAX       CucsEquipmentConfigState
    MAX-ACCESS   read-only
    STATUS       current
    DESCRIPTION
        "Cisco UCS equipment:Tpm:configState managed object property"
    ::= { cucsEquipmentTpmEntry 17 }

cucsEquipmentTpmCapProviderTable OBJECT-TYPE
    SYNTAX           SEQUENCE OF CucsEquipmentTpmCapProviderEntry
    MAX-ACCESS       not-accessible
    STATUS           current
    DESCRIPTION
        "Cisco UCS equipment:TpmCapProvider managed object table"
    ::= { cucsEquipmentObjects 123 }

cucsEquipmentTpmCapProviderEntry OBJECT-TYPE
    SYNTAX           CucsEquipmentTpmCapProviderEntry
    MAX-ACCESS       not-accessible
    STATUS           current
    DESCRIPTION
        "Entry for the cucsEquipmentTpmCapProviderTable table."
    INDEX { cucsEquipmentTpmCapProviderInstanceId }
    ::= { cucsEquipmentTpmCapProviderTable 1 }

CucsEquipmentTpmCapProviderEntry ::= SEQUENCE {
    cucsEquipmentTpmCapProviderInstanceId                            CucsManagedObjectId,
    cucsEquipmentTpmCapProviderDn                                    CucsManagedObjectDn,
    cucsEquipmentTpmCapProviderRn                                    SnmpAdminString,
    cucsEquipmentTpmCapProviderDeleted                               TruthValue,
    cucsEquipmentTpmCapProviderDeprecated                            TruthValue,
    cucsEquipmentTpmCapProviderElementLoadFailures                   Gauge32,
    cucsEquipmentTpmCapProviderElementsLoaded                        Gauge32,
    cucsEquipmentTpmCapProviderGencount                              Gauge32,
    cucsEquipmentTpmCapProviderLoadErrors                            Gauge32,
    cucsEquipmentTpmCapProviderLoadWarnings                          Gauge32,
    cucsEquipmentTpmCapProviderMgmtPlaneVer                          SnmpAdminString,
    cucsEquipmentTpmCapProviderModel                                 SnmpAdminString,
    cucsEquipmentTpmCapProviderPromCardType                          Gauge32,
    cucsEquipmentTpmCapProviderRevision                              SnmpAdminString,
    cucsEquipmentTpmCapProviderVendor                                SnmpAdminString
}

cucsEquipmentTpmCapProviderInstanceId OBJECT-TYPE
    SYNTAX       CucsManagedObjectId
    MAX-ACCESS   not-accessible
    STATUS       current
    DESCRIPTION
        "Instance identifier of the managed object."
    ::= { cucsEquipmentTpmCapProviderEntry 1 }

cucsEquipmentTpmCapProviderDn OBJECT-TYPE
    SYNTAX       CucsManagedObjectDn
    MAX-ACCESS   read-only
    STATUS       current
    DESCRIPTION
        "Cisco UCS equipment:TpmCapProvider:dn managed object property"
    ::= { cucsEquipmentTpmCapProviderEntry 2 }

cucsEquipmentTpmCapProviderRn OBJECT-TYPE
    SYNTAX       SnmpAdminString
    MAX-ACCESS   read-only
    STATUS       current
    DESCRIPTION
        "Cisco UCS equipment:TpmCapProvider:rn managed object property"
    ::= { cucsEquipmentTpmCapProviderEntry 3 }

cucsEquipmentTpmCapProviderDeleted OBJECT-TYPE
    SYNTAX       TruthValue
    MAX-ACCESS   read-only
    STATUS       current
    DESCRIPTION
        "Cisco UCS equipment:TpmCapProvider:deleted managed
        object property"
    ::= { cucsEquipmentTpmCapProviderEntry 4 }

cucsEquipmentTpmCapProviderDeprecated OBJECT-TYPE
    SYNTAX       TruthValue
    MAX-ACCESS   read-only
    STATUS       current
    DESCRIPTION
        "Cisco UCS equipment:TpmCapProvider:deprecated
        managed object property"
    ::= { cucsEquipmentTpmCapProviderEntry 5 }

cucsEquipmentTpmCapProviderElementLoadFailures OBJECT-TYPE
    SYNTAX       Gauge32
    MAX-ACCESS   read-only
    STATUS       current
    DESCRIPTION
        "Cisco UCS equipment:TpmCapProvider:elementLoadFailures
        managed object property"
    ::= { cucsEquipmentTpmCapProviderEntry 6 }

cucsEquipmentTpmCapProviderElementsLoaded OBJECT-TYPE
    SYNTAX       Gauge32
    MAX-ACCESS   read-only
    STATUS       current
    DESCRIPTION
        "Cisco UCS equipment:TpmCapProvider:elementsLoaded
        managed object property"
    ::= { cucsEquipmentTpmCapProviderEntry 7 }

cucsEquipmentTpmCapProviderGencount OBJECT-TYPE
    SYNTAX       Gauge32
    MAX-ACCESS   read-only
    STATUS       current
    DESCRIPTION
        "Cisco UCS equipment:TpmCapProvider:gencount managed
        object property"
    ::= { cucsEquipmentTpmCapProviderEntry 8 }

cucsEquipmentTpmCapProviderLoadErrors OBJECT-TYPE
    SYNTAX       Gauge32
    MAX-ACCESS   read-only
    STATUS       current
    DESCRIPTION
        "Cisco UCS equipment:TpmCapProvider:loadErrors
        managed object property"
    ::= { cucsEquipmentTpmCapProviderEntry 9 }

cucsEquipmentTpmCapProviderLoadWarnings OBJECT-TYPE
    SYNTAX       Gauge32
    MAX-ACCESS   read-only
    STATUS       current
    DESCRIPTION
        "Cisco UCS equipment:TpmCapProvider:loadWarnings
        managed object property"
    ::= { cucsEquipmentTpmCapProviderEntry 10 }

cucsEquipmentTpmCapProviderMgmtPlaneVer OBJECT-TYPE
    SYNTAX       SnmpAdminString
    MAX-ACCESS   read-only
    STATUS       current
    DESCRIPTION
        "Cisco UCS equipment:TpmCapProvider:mgmtPlaneVer
        managed object property"
    ::= { cucsEquipmentTpmCapProviderEntry 11 }

cucsEquipmentTpmCapProviderModel OBJECT-TYPE
    SYNTAX       SnmpAdminString
    MAX-ACCESS   read-only
    STATUS       current
    DESCRIPTION
        "Cisco UCS equipment:TpmCapProvider:model managed object property"
    ::= { cucsEquipmentTpmCapProviderEntry 12 }

cucsEquipmentTpmCapProviderPromCardType OBJECT-TYPE
    SYNTAX       Gauge32
    MAX-ACCESS   read-only
    STATUS       current
    DESCRIPTION
        "Cisco UCS equipment:TpmCapProvider:promCardType
        managed object property"
    ::= { cucsEquipmentTpmCapProviderEntry 13 }

cucsEquipmentTpmCapProviderRevision OBJECT-TYPE
    SYNTAX       SnmpAdminString
    MAX-ACCESS   read-only
    STATUS       current
    DESCRIPTION
        "Cisco UCS equipment:TpmCapProvider:revision managed
        object property"
    ::= { cucsEquipmentTpmCapProviderEntry 14 }

cucsEquipmentTpmCapProviderVendor OBJECT-TYPE
    SYNTAX       SnmpAdminString
    MAX-ACCESS   read-only
    STATUS       current
    DESCRIPTION
        "Cisco UCS equipment:TpmCapProvider:vendor managed
        object property"
    ::= { cucsEquipmentTpmCapProviderEntry 15 }

cucsEquipmentUnifiedPortCapProviderTable OBJECT-TYPE
    SYNTAX           SEQUENCE OF CucsEquipmentUnifiedPortCapProviderEntry
    MAX-ACCESS       not-accessible
    STATUS           current
    DESCRIPTION
        "Cisco UCS equipment:UnifiedPortCapProvider managed object table"
    ::= { cucsEquipmentObjects 94 }

cucsEquipmentUnifiedPortCapProviderEntry OBJECT-TYPE
    SYNTAX           CucsEquipmentUnifiedPortCapProviderEntry
    MAX-ACCESS       not-accessible
    STATUS           current
    DESCRIPTION
        "Entry for the cucsEquipmentUnifiedPortCapProviderTable table."
    INDEX { cucsEquipmentUnifiedPortCapProviderInstanceId }
    ::= { cucsEquipmentUnifiedPortCapProviderTable 1 }

CucsEquipmentUnifiedPortCapProviderEntry ::= SEQUENCE {
    cucsEquipmentUnifiedPortCapProviderInstanceId                    CucsManagedObjectId,
    cucsEquipmentUnifiedPortCapProviderDn                            CucsManagedObjectDn,
    cucsEquipmentUnifiedPortCapProviderRn                            SnmpAdminString,
    cucsEquipmentUnifiedPortCapProviderDescr                         SnmpAdminString,
    cucsEquipmentUnifiedPortCapProviderIntId                         SnmpAdminString,
    cucsEquipmentUnifiedPortCapProviderName                          SnmpAdminString,
    cucsEquipmentUnifiedPortCapProviderSupportedAlgorithm            CucsEquipmentUnifiedPortAlgorithm,
    cucsEquipmentUnifiedPortCapProviderPolicyLevel                   Gauge32,
    cucsEquipmentUnifiedPortCapProviderPolicyOwner                   CucsPolicyPolicyOwner,
    cucsEquipmentUnifiedPortCapProviderEndPortId                     Gauge32,
    cucsEquipmentUnifiedPortCapProviderStartPortId                   Gauge32,
    cucsEquipmentUnifiedPortCapProviderFcSpeedCap                    CucsPortSpeedBitmask
}

cucsEquipmentUnifiedPortCapProviderInstanceId OBJECT-TYPE
    SYNTAX       CucsManagedObjectId
    MAX-ACCESS   not-accessible
    STATUS       current
    DESCRIPTION
        "Instance identifier of the managed object."
    ::= { cucsEquipmentUnifiedPortCapProviderEntry 1 }

cucsEquipmentUnifiedPortCapProviderDn OBJECT-TYPE
    SYNTAX       CucsManagedObjectDn
    MAX-ACCESS   read-only
    STATUS       current
    DESCRIPTION
        "Cisco UCS equipment:UnifiedPortCapProvider:dn
        managed object property"
    ::= { cucsEquipmentUnifiedPortCapProviderEntry 2 }

cucsEquipmentUnifiedPortCapProviderRn OBJECT-TYPE
    SYNTAX       SnmpAdminString
    MAX-ACCESS   read-only
    STATUS       current
    DESCRIPTION
        "Cisco UCS equipment:UnifiedPortCapProvider:rn
        managed object property"
    ::= { cucsEquipmentUnifiedPortCapProviderEntry 3 }

cucsEquipmentUnifiedPortCapProviderDescr OBJECT-TYPE
    SYNTAX       SnmpAdminString
    MAX-ACCESS   read-only
    STATUS       current
    DESCRIPTION
        "Cisco UCS equipment:UnifiedPortCapProvider:descr
        managed object property"
    ::= { cucsEquipmentUnifiedPortCapProviderEntry 4 }

cucsEquipmentUnifiedPortCapProviderIntId OBJECT-TYPE
    SYNTAX       SnmpAdminString
    MAX-ACCESS   read-only
    STATUS       current
    DESCRIPTION
        "Cisco UCS equipment:UnifiedPortCapProvider:intId
        managed object property"
    ::= { cucsEquipmentUnifiedPortCapProviderEntry 5 }

cucsEquipmentUnifiedPortCapProviderName OBJECT-TYPE
    SYNTAX       SnmpAdminString
    MAX-ACCESS   read-only
    STATUS       current
    DESCRIPTION
        "Cisco UCS equipment:UnifiedPortCapProvider:name
        managed object property"
    ::= { cucsEquipmentUnifiedPortCapProviderEntry 6 }

cucsEquipmentUnifiedPortCapProviderSupportedAlgorithm OBJECT-TYPE
    SYNTAX       CucsEquipmentUnifiedPortAlgorithm
    MAX-ACCESS   read-only
    STATUS       current
    DESCRIPTION
        "Cisco UCS equipment:UnifiedPortCapProvider:supportedAlgorithm
        managed object property"
    ::= { cucsEquipmentUnifiedPortCapProviderEntry 7 }

cucsEquipmentUnifiedPortCapProviderPolicyLevel OBJECT-TYPE
    SYNTAX       Gauge32
    MAX-ACCESS   read-only
    STATUS       current
    DESCRIPTION
        "Cisco UCS equipment:UnifiedPortCapProvider:policyLevel
        managed object property"
    ::= { cucsEquipmentUnifiedPortCapProviderEntry 8 }

cucsEquipmentUnifiedPortCapProviderPolicyOwner OBJECT-TYPE
    SYNTAX       CucsPolicyPolicyOwner
    MAX-ACCESS   read-only
    STATUS       current
    DESCRIPTION
        "Cisco UCS equipment:UnifiedPortCapProvider:policyOwner
        managed object property"
    ::= { cucsEquipmentUnifiedPortCapProviderEntry 9 }

cucsEquipmentUnifiedPortCapProviderEndPortId OBJECT-TYPE
    SYNTAX       Gauge32
    MAX-ACCESS   read-only
    STATUS       current
    DESCRIPTION
        "Cisco UCS equipment:UnifiedPortCapProvider:endPortId
        managed object property"
    ::= { cucsEquipmentUnifiedPortCapProviderEntry 10 }

cucsEquipmentUnifiedPortCapProviderStartPortId OBJECT-TYPE
    SYNTAX       Gauge32
    MAX-ACCESS   read-only
    STATUS       current
    DESCRIPTION
        "Cisco UCS equipment:UnifiedPortCapProvider:startPortId
        managed object property"
    ::= { cucsEquipmentUnifiedPortCapProviderEntry 11 }

cucsEquipmentUnifiedPortCapProviderFcSpeedCap OBJECT-TYPE
    SYNTAX       CucsPortSpeedBitmask
    MAX-ACCESS   read-only
    STATUS       current
    DESCRIPTION
        "Cisco UCS equipment:UnifiedPortCapProvider:fcSpeedCap
        managed object property"
    ::= { cucsEquipmentUnifiedPortCapProviderEntry 14 }

cucsEquipmentUuidFeatureCapTable OBJECT-TYPE
    SYNTAX           SEQUENCE OF CucsEquipmentUuidFeatureCapEntry
    MAX-ACCESS       not-accessible
    STATUS           current
    DESCRIPTION
        "Cisco UCS equipment:UuidFeatureCap managed object table"
    ::= { cucsEquipmentObjects 141 }

cucsEquipmentUuidFeatureCapEntry OBJECT-TYPE
    SYNTAX           CucsEquipmentUuidFeatureCapEntry
    MAX-ACCESS       not-accessible
    STATUS           current
    DESCRIPTION
        "Entry for the cucsEquipmentUuidFeatureCapTable table."
    INDEX { cucsEquipmentUuidFeatureCapInstanceId }
    ::= { cucsEquipmentUuidFeatureCapTable 1 }

CucsEquipmentUuidFeatureCapEntry ::= SEQUENCE {
    cucsEquipmentUuidFeatureCapInstanceId                            CucsManagedObjectId,
    cucsEquipmentUuidFeatureCapDn                                    CucsManagedObjectDn,
    cucsEquipmentUuidFeatureCapRn                                    SnmpAdminString,
    cucsEquipmentUuidFeatureCapUuidSupportMode                       CucsEquipmentUuidFeatureCapUuidSupportMode
}

cucsEquipmentUuidFeatureCapInstanceId OBJECT-TYPE
    SYNTAX       CucsManagedObjectId
    MAX-ACCESS   not-accessible
    STATUS       current
    DESCRIPTION
        "Instance identifier of the managed object."
    ::= { cucsEquipmentUuidFeatureCapEntry 1 }

cucsEquipmentUuidFeatureCapDn OBJECT-TYPE
    SYNTAX       CucsManagedObjectDn
    MAX-ACCESS   read-only
    STATUS       current
    DESCRIPTION
        "Cisco UCS equipment:UuidFeatureCap:dn managed object property"
    ::= { cucsEquipmentUuidFeatureCapEntry 2 }

cucsEquipmentUuidFeatureCapRn OBJECT-TYPE
    SYNTAX       SnmpAdminString
    MAX-ACCESS   read-only
    STATUS       current
    DESCRIPTION
        "Cisco UCS equipment:UuidFeatureCap:rn managed object property"
    ::= { cucsEquipmentUuidFeatureCapEntry 3 }

cucsEquipmentUuidFeatureCapUuidSupportMode OBJECT-TYPE
    SYNTAX       CucsEquipmentUuidFeatureCapUuidSupportMode
    MAX-ACCESS   read-only
    STATUS       current
    DESCRIPTION
        "Cisco UCS equipment:UuidFeatureCap:uuidSupportMode
        managed object property"
    ::= { cucsEquipmentUuidFeatureCapEntry 4 }

cucsEquipmentVersionConstraintTable OBJECT-TYPE
    SYNTAX           SEQUENCE OF CucsEquipmentVersionConstraintEntry
    MAX-ACCESS       not-accessible
    STATUS           current
    DESCRIPTION
        "Cisco UCS equipment:VersionConstraint managed object table"
    ::= { cucsEquipmentObjects 116 }

cucsEquipmentVersionConstraintEntry OBJECT-TYPE
    SYNTAX           CucsEquipmentVersionConstraintEntry
    MAX-ACCESS       not-accessible
    STATUS           current
    DESCRIPTION
        "Entry for the cucsEquipmentVersionConstraintTable table."
    INDEX { cucsEquipmentVersionConstraintInstanceId }
    ::= { cucsEquipmentVersionConstraintTable 1 }

CucsEquipmentVersionConstraintEntry ::= SEQUENCE {
    cucsEquipmentVersionConstraintInstanceId                         CucsManagedObjectId,
    cucsEquipmentVersionConstraintDn                                 CucsManagedObjectDn,
    cucsEquipmentVersionConstraintRn                                 SnmpAdminString,
    cucsEquipmentVersionConstraintMinVer1                            SnmpAdminString
}

cucsEquipmentVersionConstraintInstanceId OBJECT-TYPE
    SYNTAX       CucsManagedObjectId
    MAX-ACCESS   not-accessible
    STATUS       current
    DESCRIPTION
        "Instance identifier of the managed object."
    ::= { cucsEquipmentVersionConstraintEntry 1 }

cucsEquipmentVersionConstraintDn OBJECT-TYPE
    SYNTAX       CucsManagedObjectDn
    MAX-ACCESS   read-only
    STATUS       current
    DESCRIPTION
        "Cisco UCS equipment:VersionConstraint:dn managed object property"
    ::= { cucsEquipmentVersionConstraintEntry 2 }

cucsEquipmentVersionConstraintRn OBJECT-TYPE
    SYNTAX       SnmpAdminString
    MAX-ACCESS   read-only
    STATUS       current
    DESCRIPTION
        "Cisco UCS equipment:VersionConstraint:rn managed object property"
    ::= { cucsEquipmentVersionConstraintEntry 3 }

cucsEquipmentVersionConstraintMinVer1 OBJECT-TYPE
    SYNTAX       SnmpAdminString
    MAX-ACCESS   read-only
    STATUS       current
    DESCRIPTION
        "Cisco UCS equipment:VersionConstraint:minVer1
        managed object property"
    ::= { cucsEquipmentVersionConstraintEntry 4 }

cucsEquipmentXcvrTable OBJECT-TYPE
    SYNTAX           SEQUENCE OF CucsEquipmentXcvrEntry
    MAX-ACCESS       not-accessible
    STATUS           current
    DESCRIPTION
        "Cisco UCS equipment:Xcvr managed object table"
    ::= { cucsEquipmentObjects 76 }

cucsEquipmentXcvrEntry OBJECT-TYPE
    SYNTAX           CucsEquipmentXcvrEntry
    MAX-ACCESS       not-accessible
    STATUS           current
    DESCRIPTION
        "Entry for the cucsEquipmentXcvrTable table."
    INDEX { cucsEquipmentXcvrInstanceId }
    ::= { cucsEquipmentXcvrTable 1 }

CucsEquipmentXcvrEntry ::= SEQUENCE {
    cucsEquipmentXcvrInstanceId                                      CucsManagedObjectId,
    cucsEquipmentXcvrDn                                              CucsManagedObjectDn,
    cucsEquipmentXcvrRn                                              SnmpAdminString,
    cucsEquipmentXcvrId                                              CucsEquipmentXcvrId,
    cucsEquipmentXcvrModel                                           SnmpAdminString,
    cucsEquipmentXcvrRevision                                        SnmpAdminString,
    cucsEquipmentXcvrSerial                                          SnmpAdminString,
    cucsEquipmentXcvrType                                            CucsEquipmentXcvrType,
    cucsEquipmentXcvrVendor                                          SnmpAdminString,
    cucsEquipmentXcvrTs                                              DateAndTime
}

cucsEquipmentXcvrInstanceId OBJECT-TYPE
    SYNTAX       CucsManagedObjectId
    MAX-ACCESS   not-accessible
    STATUS       current
    DESCRIPTION
        "Instance identifier of the managed object."
    ::= { cucsEquipmentXcvrEntry 1 }

cucsEquipmentXcvrDn OBJECT-TYPE
    SYNTAX       CucsManagedObjectDn
    MAX-ACCESS   read-only
    STATUS       current
    DESCRIPTION
        "Cisco UCS equipment:Xcvr:dn managed object property"
    ::= { cucsEquipmentXcvrEntry 2 }

cucsEquipmentXcvrRn OBJECT-TYPE
    SYNTAX       SnmpAdminString
    MAX-ACCESS   read-only
    STATUS       current
    DESCRIPTION
        "Cisco UCS equipment:Xcvr:rn managed object property"
    ::= { cucsEquipmentXcvrEntry 3 }

cucsEquipmentXcvrId OBJECT-TYPE
    SYNTAX       CucsEquipmentXcvrId
    MAX-ACCESS   read-only
    STATUS       current
    DESCRIPTION
        "Cisco UCS equipment:Xcvr:id managed object property"
    ::= { cucsEquipmentXcvrEntry 4 }

cucsEquipmentXcvrModel OBJECT-TYPE
    SYNTAX       SnmpAdminString
    MAX-ACCESS   read-only
    STATUS       current
    DESCRIPTION
        "Cisco UCS equipment:Xcvr:model managed object property"
    ::= { cucsEquipmentXcvrEntry 5 }

cucsEquipmentXcvrRevision OBJECT-TYPE
    SYNTAX       SnmpAdminString
    MAX-ACCESS   read-only
    STATUS       current
    DESCRIPTION
        "Cisco UCS equipment:Xcvr:revision managed object property"
    ::= { cucsEquipmentXcvrEntry 6 }

cucsEquipmentXcvrSerial OBJECT-TYPE
    SYNTAX       SnmpAdminString
    MAX-ACCESS   read-only
    STATUS       current
    DESCRIPTION
        "Cisco UCS equipment:Xcvr:serial managed object property"
    ::= { cucsEquipmentXcvrEntry 7 }

cucsEquipmentXcvrType OBJECT-TYPE
    SYNTAX       CucsEquipmentXcvrType
    MAX-ACCESS   read-only
    STATUS       current
    DESCRIPTION
        "Cisco UCS equipment:Xcvr:type managed object property"
    ::= { cucsEquipmentXcvrEntry 8 }

cucsEquipmentXcvrVendor OBJECT-TYPE
    SYNTAX       SnmpAdminString
    MAX-ACCESS   read-only
    STATUS       current
    DESCRIPTION
        "Cisco UCS equipment:Xcvr:vendor managed object property"
    ::= { cucsEquipmentXcvrEntry 9 }

cucsEquipmentXcvrTs OBJECT-TYPE
    SYNTAX       DateAndTime
    MAX-ACCESS   read-only
    STATUS       current
    DESCRIPTION
        "Cisco UCS equipment:Xcvr:ts managed object property"
    ::= { cucsEquipmentXcvrEntry 10 }

END
