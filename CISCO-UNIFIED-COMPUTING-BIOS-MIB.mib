-- *********************************************************************
-- CISCO-UNIFIED-COMPUTING-BIOS-MIB.my
--
-- MIB representation of the Cisco Unified Computing System
-- BIOS management information model package
--
-- Created July 2018 by Charles Bullis
--
-- Copyright (c) 2005-2018 Cisco Systems, Inc. All rights reserved.
--
-- *********************************************************************

CISCO-UNIFIED-COMPUTING-BIOS-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsBiosBootDevErrorCode,
    CucsBiosBootDevGrpType,
    CucsBiosBootDevOrder,
    CucsBiosDefaultAction,
    CucsBiosSupportedAction,
    CucsBiosVfACPI10SupportVpACPI10Support,
    CucsBiosVfASPMSupportVpASPMSupport,
    CucsBiosVfAllUSBDevicesVpAllUSBDevices,
    CucsBiosVfAltitudeVpAltitude,
    CucsBiosVfAssertNMIOnPERRVpAssertNMIOnPERR,
    CucsBiosVfAssertNMIOnSERRVpAssertNMIOnSERR,
    CucsBiosVfBootOptionRetryVpBootOptionRetry,
    CucsBiosVfCPUHardwarePowerManagementVpCPUHardwarePowerManagement,
    CucsBiosVfCPUPerformanceVpCPUPerformance,
    CucsBiosVfConsistentDeviceNameControlVpCDNControl,
    CucsBiosVfConsoleRedirectionVpBaudRate,
    CucsBiosVfConsoleRedirectionVpConsoleRedirection,
    CucsBiosVfConsoleRedirectionVpFlowControl,
    CucsBiosVfConsoleRedirectionVpLegacyOSRedirection,
    CucsBiosVfConsoleRedirectionVpPuttyKeyPad,
    CucsBiosVfConsoleRedirectionVpTerminalType,
    CucsBiosVfCoreMultiProcessingVpCoreMultiProcessing,
    CucsBiosVfDDR3VoltageSelectionVpDDR3VoltageSelection,
    CucsBiosVfDRAMClockThrottlingVpDRAMClockThrottling,
    CucsBiosVfDirectCacheAccessVpDirectCacheAccess,
    CucsBiosVfDramRefreshRateVpDramRefreshRate,
    CucsBiosVfEnergyPerformanceTuningVpPwrPerfTuning,
    CucsBiosVfEnhancedIntelSpeedStepTechVpEnhancedIntelSpeedStepTech,
    CucsBiosVfEnhancedPowerCappingSupportVpEnhancedPowerCapping,
    CucsBiosVfExecuteDisableBitVpExecuteDisableBit,
    CucsBiosVfFRB2TimerVpFRB2Timer,
    CucsBiosVfFrequencyFloorOverrideVpFrequencyFloorOverride,
    CucsBiosVfFrontPanelLockoutVpFrontPanelLockout,
    CucsBiosVfIOEMezz1OptionROMVpIOEMezz1OptionROM,
    CucsBiosVfIOENVMe1OptionROMVpIOENVMe1OptionROM,
    CucsBiosVfIOENVMe2OptionROMVpIOENVMe2OptionROM,
    CucsBiosVfIOESlot1OptionROMVpIOESlot1OptionROM,
    CucsBiosVfIOESlot2OptionROMVpIOESlot2OptionROM,
    CucsBiosVfIntegratedGraphicsApertureSizeVpIntgtGraphApertureSize,
    CucsBiosVfIntegratedGraphicsVpIntegratedGraphics,
    CucsBiosVfIntelEntrySASRAIDModuleVpSASRAID,
    CucsBiosVfIntelEntrySASRAIDModuleVpSASRAIDModule,
    CucsBiosVfIntelHyperThreadingTechVpIntelHyperThreadingTech,
    CucsBiosVfIntelTrustedExecutionTechnologyVpIntelTstdExecTechSup,
    CucsBiosVfIntelTurboBoostTechVpIntelTurboBoostTech,
    CucsBiosVfIntelVTForDirectedIOVpIntelVTDATSSupport,
    CucsBiosVfIntelVTForDirectedIOVpIntelVTDCoherencySupport,
    CucsBiosVfIntelVTForDirectedIOVpIntelVTDInterruptRemapping,
    CucsBiosVfIntelVTForDirectedIOVpIntelVTDPassThroughDMASupport,
    CucsBiosVfIntelVTForDirectedIOVpIntelVTForDirectedIO,
    CucsBiosVfInterleaveConfigurationVpChannelInterleaving,
    CucsBiosVfInterleaveConfigurationVpMemoryInterleaving,
    CucsBiosVfInterleaveConfigurationVpRankInterleaving,
    CucsBiosVfLocalX2ApicVpLocalX2Apic,
    CucsBiosVfLvDIMMSupportVpLvDDRMode,
    CucsBiosVfMaxVariableMTRRSettingVpProcessorMtrr,
    CucsBiosVfMaximumMemoryBelow4GBVpMaximumMemoryBelow4GB,
    CucsBiosVfMemoryMappedIOAbove4GBVpMemoryMappedIOAbove4GB,
    CucsBiosVfMirroringModeVpMirroringMode,
    CucsBiosVfNUMAOptimizedVpNUMAOptimized,
    CucsBiosVfOSBootWatchdogTimerPolicyVpOSBootWatchdogTimerPolicy,
    CucsBiosVfOSBootWatchdogTimerTimeoutVpOSBootWatchdogTimerTimeout,
    CucsBiosVfOSBootWatchdogTimerVpOSBootWatchdogTimer,
    CucsBiosVfOnboardGraphicsVpOnboardGraphics,
    CucsBiosVfOnboardSATAControllerVpOnboardSATAController,
    CucsBiosVfOnboardSATAControllerVpSATAMode,
    CucsBiosVfOnboardStorageVpOnboardSCUStorageSupport,
    CucsBiosVfOptionROMEnableVpState,
    CucsBiosVfOptionROMLoadVpLoad,
    CucsBiosVfOutOfBandManagementVpComSpcrEnable,
    CucsBiosVfPCHSATAModeVpSATAMode,
    CucsBiosVfPCILOMPortsConfigurationVpPCIe10GLOM2Link,
    CucsBiosVfPCIROMCLPVpPCIROMCLP,
    CucsBiosVfPCISlotLinkSpeedVpPCIeSlot10LinkSpeed,
    CucsBiosVfPCISlotLinkSpeedVpPCIeSlot1LinkSpeed,
    CucsBiosVfPCISlotLinkSpeedVpPCIeSlot2LinkSpeed,
    CucsBiosVfPCISlotLinkSpeedVpPCIeSlot3LinkSpeed,
    CucsBiosVfPCISlotLinkSpeedVpPCIeSlot4LinkSpeed,
    CucsBiosVfPCISlotLinkSpeedVpPCIeSlot5LinkSpeed,
    CucsBiosVfPCISlotLinkSpeedVpPCIeSlot6LinkSpeed,
    CucsBiosVfPCISlotLinkSpeedVpPCIeSlot7LinkSpeed,
    CucsBiosVfPCISlotLinkSpeedVpPCIeSlot8LinkSpeed,
    CucsBiosVfPCISlotLinkSpeedVpPCIeSlot9LinkSpeed,
    CucsBiosVfPCISlotOptionROMEnableVpPCIeSlotHBAOptionROM,
    CucsBiosVfPCISlotOptionROMEnableVpPCIeSlotMLOMOptionROM,
    CucsBiosVfPCISlotOptionROMEnableVpPCIeSlotN1OptionROM,
    CucsBiosVfPCISlotOptionROMEnableVpPCIeSlotN2OptionROM,
    CucsBiosVfPCISlotOptionROMEnableVpPCIeSlotSASOptionROM,
    CucsBiosVfPCISlotOptionROMEnableVpSlot10State,
    CucsBiosVfPCISlotOptionROMEnableVpSlot1State,
    CucsBiosVfPCISlotOptionROMEnableVpSlot2State,
    CucsBiosVfPCISlotOptionROMEnableVpSlot3State,
    CucsBiosVfPCISlotOptionROMEnableVpSlot4State,
    CucsBiosVfPCISlotOptionROMEnableVpSlot5State,
    CucsBiosVfPCISlotOptionROMEnableVpSlot6State,
    CucsBiosVfPCISlotOptionROMEnableVpSlot7State,
    CucsBiosVfPCISlotOptionROMEnableVpSlot8State,
    CucsBiosVfPCISlotOptionROMEnableVpSlot9State,
    CucsBiosVfPCISlotOptionROMEnableVpSlotMezzState,
    CucsBiosVfPOSTErrorPauseVpPOSTErrorPause,
    CucsBiosVfPSTATECoordinationVpPSTATECoordination,
    CucsBiosVfPackageCStateLimitVpPackageCStateLimit,
    CucsBiosVfProcessorC1EVpProcessorC1E,
    CucsBiosVfProcessorC3ReportVpProcessorC3Report,
    CucsBiosVfProcessorC6ReportVpProcessorC6Report,
    CucsBiosVfProcessorC7ReportVpProcessorC7Report,
    CucsBiosVfProcessorCMCIVpProcessorCMCI,
    CucsBiosVfProcessorCStateVpProcessorCState,
    CucsBiosVfProcessorEnergyConfigurationVpEnergyPerformance,
    CucsBiosVfProcessorEnergyConfigurationVpPowerTechnology,
    CucsBiosVfProcessorPrefetchConfigVpAdjacentCacheLinePrefetcher,
    CucsBiosVfProcessorPrefetchConfigVpDCUIPPrefetcher,
    CucsBiosVfProcessorPrefetchConfigVpDCUStreamerPrefetch,
    CucsBiosVfProcessorPrefetchConfigVpHardwarePrefetcher,
    CucsBiosVfQPILinkFrequencySelectVpQPILinkFrequencySelect,
    CucsBiosVfQPISnoopModeVpQPISnoopMode,
    CucsBiosVfQuietBootVpQuietBoot,
    CucsBiosVfRedirectionAfterBIOSPOSTVpRedirectionAfterPOST,
    CucsBiosVfResumeOnACPowerLossVpResumeOnACPowerLoss,
    CucsBiosVfSBMezz1OptionROMVpSBMezz1OptionROM,
    CucsBiosVfSBNVMe1OptionROMVpSBNVMe1OptionROM,
    CucsBiosVfSIOC1OptionROMVpSIOC1OptionROM,
    CucsBiosVfSIOC2OptionROMVpSIOC2OptionROM,
    CucsBiosVfScrubPoliciesVpDemandScrub,
    CucsBiosVfScrubPoliciesVpPatrolScrub,
    CucsBiosVfSerialPortAEnableVpSerialPortAEnable,
    CucsBiosVfSparingModeVpSparingMode,
    CucsBiosVfSriovConfigVpSriov,
    CucsBiosVfTPMPendingOperationVpTPMPendingOperation,
    CucsBiosVfTPMSupportVpTPMSupport,
    CucsBiosVfTrustedPlatformModuleVpTrustedPlatformModuleSupport,
    CucsBiosVfUCSMBootModeControlVpUEFIBootMode,
    CucsBiosVfUCSMBootOrderRuleControlVpUCSMBootOrderRule,
    CucsBiosVfUEFIOSUseLegacyVideoVpUEFIOSUseLegacyVideo,
    CucsBiosVfUSBBootConfigVpLegacyUSBSupport,
    CucsBiosVfUSBBootConfigVpMakeDeviceNonBootable,
    CucsBiosVfUSBConfigurationVpLegacyUSBSupport,
    CucsBiosVfUSBConfigurationVpXHCIMode,
    CucsBiosVfUSBFrontPanelAccessLockVpUSBFrontPanelLock,
    CucsBiosVfUSBPortConfigurationVpPort6064Emulation,
    CucsBiosVfUSBPortConfigurationVpUSBPortFront,
    CucsBiosVfUSBPortConfigurationVpUSBPortInternal,
    CucsBiosVfUSBPortConfigurationVpUSBPortKVM,
    CucsBiosVfUSBPortConfigurationVpUSBPortRear,
    CucsBiosVfUSBPortConfigurationVpUSBPortSDCard,
    CucsBiosVfUSBPortConfigurationVpUSBPortVMedia,
    CucsBiosVfUSBSysIdlePowerOptimizingSettingVpUSBIdlePowerOptimize,
    CucsBiosVfVGAPriorityVpVGAPriority,
    CucsBiosVfWorkloadConfigurationVpWorkloadConfiguration,
    CucsBiosVpIntelVirtualizationTechnology,
    CucsBiosVpSelectMemoryRASConfiguration,
    CucsPolicyPolicyOwner
        FROM CISCO-UNIFIED-COMPUTING-TC-MIB;

cucsBiosObjects MODULE-IDENTITY
    LAST-UPDATED    "201807260000Z"
    ORGANIZATION    "Cisco Systems Inc."
    CONTACT-INFO
        "Cisco Systems
        Customer Service

        Postal: 170 W Tasman Drive
        San Jose, CA  95134
        USA

        Tel: +1 800 553 -NETS

        E-mail: cs-san@cisco.com, cs-lan-switch-snmp@cisco.com"
    DESCRIPTION
        "MIB representation of the Cisco Unified Computing System
        BIOS management information model package"
    ::= { ciscoUnifiedComputingMIBObjects 4 }

cucsBiosBOTTable OBJECT-TYPE
    SYNTAX           SEQUENCE OF CucsBiosBOTEntry
    MAX-ACCESS       not-accessible
    STATUS           current
    DESCRIPTION
        "Cisco UCS bios:BOT managed object table"
    ::= { cucsBiosObjects 1 }

cucsBiosBOTEntry OBJECT-TYPE
    SYNTAX           CucsBiosBOTEntry
    MAX-ACCESS       not-accessible
    STATUS           current
    DESCRIPTION
        "Entry for the cucsBiosBOTTable table."
    INDEX { cucsBiosBOTInstanceId }
    ::= { cucsBiosBOTTable 1 }

CucsBiosBOTEntry ::= SEQUENCE {
    cucsBiosBOTInstanceId                                            CucsManagedObjectId,
    cucsBiosBOTDn                                                    CucsManagedObjectDn,
    cucsBiosBOTRn                                                    SnmpAdminString,
    cucsBiosBOTLastUpdate                                            DateAndTime
}

cucsBiosBOTInstanceId OBJECT-TYPE
    SYNTAX       CucsManagedObjectId
    MAX-ACCESS   not-accessible
    STATUS       current
    DESCRIPTION
        "Instance identifier of the managed object."
    ::= { cucsBiosBOTEntry 1 }

cucsBiosBOTDn OBJECT-TYPE
    SYNTAX       CucsManagedObjectDn
    MAX-ACCESS   read-only
    STATUS       current
    DESCRIPTION
        "Cisco UCS bios:BOT:dn managed object property"
    ::= { cucsBiosBOTEntry 2 }

cucsBiosBOTRn OBJECT-TYPE
    SYNTAX       SnmpAdminString
    MAX-ACCESS   read-only
    STATUS       current
    DESCRIPTION
        "Cisco UCS bios:BOT:rn managed object property"
    ::= { cucsBiosBOTEntry 3 }

cucsBiosBOTLastUpdate OBJECT-TYPE
    SYNTAX       DateAndTime
    MAX-ACCESS   read-only
    STATUS       current
    DESCRIPTION
        "Cisco UCS bios:BOT:lastUpdate managed object property"
    ::= { cucsBiosBOTEntry 4 }

cucsBiosBootDevTable OBJECT-TYPE
    SYNTAX           SEQUENCE OF CucsBiosBootDevEntry
    MAX-ACCESS       not-accessible
    STATUS           current
    DESCRIPTION
        "Cisco UCS bios:BootDev managed object table"
    ::= { cucsBiosObjects 2 }

cucsBiosBootDevEntry OBJECT-TYPE
    SYNTAX           CucsBiosBootDevEntry
    MAX-ACCESS       not-accessible
    STATUS           current
    DESCRIPTION
        "Entry for the cucsBiosBootDevTable table."
    INDEX { cucsBiosBootDevInstanceId }
    ::= { cucsBiosBootDevTable 1 }

CucsBiosBootDevEntry ::= SEQUENCE {
    cucsBiosBootDevInstanceId                                        CucsManagedObjectId,
    cucsBiosBootDevDn                                                CucsManagedObjectDn,
    cucsBiosBootDevRn                                                SnmpAdminString,
    cucsBiosBootDevDescr                                             SnmpAdminString,
    cucsBiosBootDevOrder                                             CucsBiosBootDevOrder,
    cucsBiosBootDevDeviceName                                        SnmpAdminString,
    cucsBiosBootDevErrValue                                          CucsBiosBootDevErrorCode
}

cucsBiosBootDevInstanceId OBJECT-TYPE
    SYNTAX       CucsManagedObjectId
    MAX-ACCESS   not-accessible
    STATUS       current
    DESCRIPTION
        "Instance identifier of the managed object."
    ::= { cucsBiosBootDevEntry 1 }

cucsBiosBootDevDn OBJECT-TYPE
    SYNTAX       CucsManagedObjectDn
    MAX-ACCESS   read-only
    STATUS       current
    DESCRIPTION
        "Cisco UCS bios:BootDev:dn managed object property"
    ::= { cucsBiosBootDevEntry 2 }

cucsBiosBootDevRn OBJECT-TYPE
    SYNTAX       SnmpAdminString
    MAX-ACCESS   read-only
    STATUS       current
    DESCRIPTION
        "Cisco UCS bios:BootDev:rn managed object property"
    ::= { cucsBiosBootDevEntry 3 }

cucsBiosBootDevDescr OBJECT-TYPE
    SYNTAX       SnmpAdminString
    MAX-ACCESS   read-only
    STATUS       current
    DESCRIPTION
        "Cisco UCS bios:BootDev:descr managed object property"
    ::= { cucsBiosBootDevEntry 4 }

cucsBiosBootDevOrder OBJECT-TYPE
    SYNTAX       CucsBiosBootDevOrder
    MAX-ACCESS   read-only
    STATUS       current
    DESCRIPTION
        "Cisco UCS bios:BootDev:order managed object property"
    ::= { cucsBiosBootDevEntry 5 }

cucsBiosBootDevDeviceName OBJECT-TYPE
    SYNTAX       SnmpAdminString
    MAX-ACCESS   read-only
    STATUS       current
    DESCRIPTION
        "Cisco UCS bios:BootDev:deviceName managed object property"
    ::= { cucsBiosBootDevEntry 6 }

cucsBiosBootDevErrValue OBJECT-TYPE
    SYNTAX       CucsBiosBootDevErrorCode
    MAX-ACCESS   read-only
    STATUS       current
    DESCRIPTION
        "Cisco UCS bios:BootDev:errValue managed object property"
    ::= { cucsBiosBootDevEntry 7 }

cucsBiosBootDevGrpTable OBJECT-TYPE
    SYNTAX           SEQUENCE OF CucsBiosBootDevGrpEntry
    MAX-ACCESS       not-accessible
    STATUS           current
    DESCRIPTION
        "Cisco UCS bios:BootDevGrp managed object table"
    ::= { cucsBiosObjects 3 }

cucsBiosBootDevGrpEntry OBJECT-TYPE
    SYNTAX           CucsBiosBootDevGrpEntry
    MAX-ACCESS       not-accessible
    STATUS           current
    DESCRIPTION
        "Entry for the cucsBiosBootDevGrpTable table."
    INDEX { cucsBiosBootDevGrpInstanceId }
    ::= { cucsBiosBootDevGrpTable 1 }

CucsBiosBootDevGrpEntry ::= SEQUENCE {
    cucsBiosBootDevGrpInstanceId                                     CucsManagedObjectId,
    cucsBiosBootDevGrpDn                                             CucsManagedObjectDn,
    cucsBiosBootDevGrpRn                                             SnmpAdminString,
    cucsBiosBootDevGrpDescr                                          SnmpAdminString,
    cucsBiosBootDevGrpOrder                                          CucsBiosBootDevOrder,
    cucsBiosBootDevGrpType                                           CucsBiosBootDevGrpType,
    cucsBiosBootDevGrpDeviceName                                     SnmpAdminString,
    cucsBiosBootDevGrpErrVal                                         CucsBiosBootDevErrorCode
}

cucsBiosBootDevGrpInstanceId OBJECT-TYPE
    SYNTAX       CucsManagedObjectId
    MAX-ACCESS   not-accessible
    STATUS       current
    DESCRIPTION
        "Instance identifier of the managed object."
    ::= { cucsBiosBootDevGrpEntry 1 }

cucsBiosBootDevGrpDn OBJECT-TYPE
    SYNTAX       CucsManagedObjectDn
    MAX-ACCESS   read-only
    STATUS       current
    DESCRIPTION
        "Cisco UCS bios:BootDevGrp:dn managed object property"
    ::= { cucsBiosBootDevGrpEntry 2 }

cucsBiosBootDevGrpRn OBJECT-TYPE
    SYNTAX       SnmpAdminString
    MAX-ACCESS   read-only
    STATUS       current
    DESCRIPTION
        "Cisco UCS bios:BootDevGrp:rn managed object property"
    ::= { cucsBiosBootDevGrpEntry 3 }

cucsBiosBootDevGrpDescr OBJECT-TYPE
    SYNTAX       SnmpAdminString
    MAX-ACCESS   read-only
    STATUS       current
    DESCRIPTION
        "Cisco UCS bios:BootDevGrp:descr managed object property"
    ::= { cucsBiosBootDevGrpEntry 4 }

cucsBiosBootDevGrpOrder OBJECT-TYPE
    SYNTAX       CucsBiosBootDevOrder
    MAX-ACCESS   read-only
    STATUS       current
    DESCRIPTION
        "Cisco UCS bios:BootDevGrp:order managed object property"
    ::= { cucsBiosBootDevGrpEntry 5 }

cucsBiosBootDevGrpType OBJECT-TYPE
    SYNTAX       CucsBiosBootDevGrpType
    MAX-ACCESS   read-only
    STATUS       current
    DESCRIPTION
        "Cisco UCS bios:BootDevGrp:type managed object property"
    ::= { cucsBiosBootDevGrpEntry 6 }

cucsBiosBootDevGrpDeviceName OBJECT-TYPE
    SYNTAX       SnmpAdminString
    MAX-ACCESS   read-only
    STATUS       current
    DESCRIPTION
        "Cisco UCS bios:BootDevGrp:deviceName managed object property"
    ::= { cucsBiosBootDevGrpEntry 7 }

cucsBiosBootDevGrpErrVal OBJECT-TYPE
    SYNTAX       CucsBiosBootDevErrorCode
    MAX-ACCESS   read-only
    STATUS       current
    DESCRIPTION
        "Cisco UCS bios:BootDevGrp:errVal managed object property"
    ::= { cucsBiosBootDevGrpEntry 8 }

cucsBiosFeatureRefTable OBJECT-TYPE
    SYNTAX           SEQUENCE OF CucsBiosFeatureRefEntry
    MAX-ACCESS       not-accessible
    STATUS           current
    DESCRIPTION
        "Cisco UCS bios:FeatureRef managed object table"
    ::= { cucsBiosObjects 4 }

cucsBiosFeatureRefEntry OBJECT-TYPE
    SYNTAX           CucsBiosFeatureRefEntry
    MAX-ACCESS       not-accessible
    STATUS           current
    DESCRIPTION
        "Entry for the cucsBiosFeatureRefTable table."
    INDEX { cucsBiosFeatureRefInstanceId }
    ::= { cucsBiosFeatureRefTable 1 }

CucsBiosFeatureRefEntry ::= SEQUENCE {
    cucsBiosFeatureRefInstanceId                                     CucsManagedObjectId,
    cucsBiosFeatureRefDn                                             CucsManagedObjectDn,
    cucsBiosFeatureRefRn                                             SnmpAdminString,
    cucsBiosFeatureRefIsSupported                                    CucsBiosSupportedAction,
    cucsBiosFeatureRefName                                           SnmpAdminString,
    cucsBiosFeatureRefFtrMoClassName                                 SnmpAdminString
}

cucsBiosFeatureRefInstanceId OBJECT-TYPE
    SYNTAX       CucsManagedObjectId
    MAX-ACCESS   not-accessible
    STATUS       current
    DESCRIPTION
        "Instance identifier of the managed object."
    ::= { cucsBiosFeatureRefEntry 1 }

cucsBiosFeatureRefDn OBJECT-TYPE
    SYNTAX       CucsManagedObjectDn
    MAX-ACCESS   read-only
    STATUS       current
    DESCRIPTION
        "Cisco UCS bios:FeatureRef:dn managed object property"
    ::= { cucsBiosFeatureRefEntry 2 }

cucsBiosFeatureRefRn OBJECT-TYPE
    SYNTAX       SnmpAdminString
    MAX-ACCESS   read-only
    STATUS       current
    DESCRIPTION
        "Cisco UCS bios:FeatureRef:rn managed object property"
    ::= { cucsBiosFeatureRefEntry 3 }

cucsBiosFeatureRefIsSupported OBJECT-TYPE
    SYNTAX       CucsBiosSupportedAction
    MAX-ACCESS   read-only
    STATUS       current
    DESCRIPTION
        "Cisco UCS bios:FeatureRef:isSupported managed object property"
    ::= { cucsBiosFeatureRefEntry 4 }

cucsBiosFeatureRefName OBJECT-TYPE
    SYNTAX       SnmpAdminString
    MAX-ACCESS   read-only
    STATUS       current
    DESCRIPTION
        "Cisco UCS bios:FeatureRef:name managed object property"
    ::= { cucsBiosFeatureRefEntry 5 }

cucsBiosFeatureRefFtrMoClassName OBJECT-TYPE
    SYNTAX       SnmpAdminString
    MAX-ACCESS   read-only
    STATUS       current
    DESCRIPTION
        "Cisco UCS bios:FeatureRef:ftrMoClassName managed object property"
    ::= { cucsBiosFeatureRefEntry 6 }

cucsBiosParameterRefTable OBJECT-TYPE
    SYNTAX           SEQUENCE OF CucsBiosParameterRefEntry
    MAX-ACCESS       not-accessible
    STATUS           current
    DESCRIPTION
        "Cisco UCS bios:ParameterRef managed object table"
    ::= { cucsBiosObjects 5 }

cucsBiosParameterRefEntry OBJECT-TYPE
    SYNTAX           CucsBiosParameterRefEntry
    MAX-ACCESS       not-accessible
    STATUS           current
    DESCRIPTION
        "Entry for the cucsBiosParameterRefTable table."
    INDEX { cucsBiosParameterRefInstanceId }
    ::= { cucsBiosParameterRefTable 1 }

CucsBiosParameterRefEntry ::= SEQUENCE {
    cucsBiosParameterRefInstanceId                                   CucsManagedObjectId,
    cucsBiosParameterRefDn                                           CucsManagedObjectDn,
    cucsBiosParameterRefRn                                           SnmpAdminString,
    cucsBiosParameterRefIsSupported                                  CucsBiosSupportedAction,
    cucsBiosParameterRefName                                         SnmpAdminString,
    cucsBiosParameterRefPropertyName                                 SnmpAdminString
}

cucsBiosParameterRefInstanceId OBJECT-TYPE
    SYNTAX       CucsManagedObjectId
    MAX-ACCESS   not-accessible
    STATUS       current
    DESCRIPTION
        "Instance identifier of the managed object."
    ::= { cucsBiosParameterRefEntry 1 }

cucsBiosParameterRefDn OBJECT-TYPE
    SYNTAX       CucsManagedObjectDn
    MAX-ACCESS   read-only
    STATUS       current
    DESCRIPTION
        "Cisco UCS bios:ParameterRef:dn managed object property"
    ::= { cucsBiosParameterRefEntry 2 }

cucsBiosParameterRefRn OBJECT-TYPE
    SYNTAX       SnmpAdminString
    MAX-ACCESS   read-only
    STATUS       current
    DESCRIPTION
        "Cisco UCS bios:ParameterRef:rn managed object property"
    ::= { cucsBiosParameterRefEntry 3 }

cucsBiosParameterRefIsSupported OBJECT-TYPE
    SYNTAX       CucsBiosSupportedAction
    MAX-ACCESS   read-only
    STATUS       current
    DESCRIPTION
        "Cisco UCS bios:ParameterRef:isSupported managed object property"
    ::= { cucsBiosParameterRefEntry 4 }

cucsBiosParameterRefName OBJECT-TYPE
    SYNTAX       SnmpAdminString
    MAX-ACCESS   read-only
    STATUS       current
    DESCRIPTION
        "Cisco UCS bios:ParameterRef:name managed object property"
    ::= { cucsBiosParameterRefEntry 5 }

cucsBiosParameterRefPropertyName OBJECT-TYPE
    SYNTAX       SnmpAdminString
    MAX-ACCESS   read-only
    STATUS       current
    DESCRIPTION
        "Cisco UCS bios:ParameterRef:propertyName managed object property"
    ::= { cucsBiosParameterRefEntry 6 }

cucsBiosRefTable OBJECT-TYPE
    SYNTAX           SEQUENCE OF CucsBiosRefEntry
    MAX-ACCESS       not-accessible
    STATUS           current
    DESCRIPTION
        "Cisco UCS bios:Ref managed object table"
    ::= { cucsBiosObjects 6 }

cucsBiosRefEntry OBJECT-TYPE
    SYNTAX           CucsBiosRefEntry
    MAX-ACCESS       not-accessible
    STATUS           current
    DESCRIPTION
        "Entry for the cucsBiosRefTable table."
    INDEX { cucsBiosRefInstanceId }
    ::= { cucsBiosRefTable 1 }

CucsBiosRefEntry ::= SEQUENCE {
    cucsBiosRefInstanceId                                            CucsManagedObjectId,
    cucsBiosRefDn                                                    CucsManagedObjectDn,
    cucsBiosRefRn                                                    SnmpAdminString,
    cucsBiosRefIsSupported                                           CucsBiosSupportedAction
}

cucsBiosRefInstanceId OBJECT-TYPE
    SYNTAX       CucsManagedObjectId
    MAX-ACCESS   not-accessible
    STATUS       current
    DESCRIPTION
        "Instance identifier of the managed object."
    ::= { cucsBiosRefEntry 1 }

cucsBiosRefDn OBJECT-TYPE
    SYNTAX       CucsManagedObjectDn
    MAX-ACCESS   read-only
    STATUS       current
    DESCRIPTION
        "Cisco UCS bios:Ref:dn managed object property"
    ::= { cucsBiosRefEntry 2 }

cucsBiosRefRn OBJECT-TYPE
    SYNTAX       SnmpAdminString
    MAX-ACCESS   read-only
    STATUS       current
    DESCRIPTION
        "Cisco UCS bios:Ref:rn managed object property"
    ::= { cucsBiosRefEntry 3 }

cucsBiosRefIsSupported OBJECT-TYPE
    SYNTAX       CucsBiosSupportedAction
    MAX-ACCESS   read-only
    STATUS       current
    DESCRIPTION
        "Cisco UCS bios:Ref:isSupported managed object property"
    ::= { cucsBiosRefEntry 4 }

cucsBiosSettingRefTable OBJECT-TYPE
    SYNTAX           SEQUENCE OF CucsBiosSettingRefEntry
    MAX-ACCESS       not-accessible
    STATUS           current
    DESCRIPTION
        "Cisco UCS bios:SettingRef managed object table"
    ::= { cucsBiosObjects 7 }

cucsBiosSettingRefEntry OBJECT-TYPE
    SYNTAX           CucsBiosSettingRefEntry
    MAX-ACCESS       not-accessible
    STATUS           current
    DESCRIPTION
        "Entry for the cucsBiosSettingRefTable table."
    INDEX { cucsBiosSettingRefInstanceId }
    ::= { cucsBiosSettingRefTable 1 }

CucsBiosSettingRefEntry ::= SEQUENCE {
    cucsBiosSettingRefInstanceId                                     CucsManagedObjectId,
    cucsBiosSettingRefDn                                             CucsManagedObjectDn,
    cucsBiosSettingRefRn                                             SnmpAdminString,
    cucsBiosSettingRefIsDefault                                      CucsBiosDefaultAction,
    cucsBiosSettingRefIsSupported                                    CucsBiosSupportedAction,
    cucsBiosSettingRefName                                           SnmpAdminString,
    cucsBiosSettingRefConstantName                                   SnmpAdminString
}

cucsBiosSettingRefInstanceId OBJECT-TYPE
    SYNTAX       CucsManagedObjectId
    MAX-ACCESS   not-accessible
    STATUS       current
    DESCRIPTION
        "Instance identifier of the managed object."
    ::= { cucsBiosSettingRefEntry 1 }

cucsBiosSettingRefDn OBJECT-TYPE
    SYNTAX       CucsManagedObjectDn
    MAX-ACCESS   read-only
    STATUS       current
    DESCRIPTION
        "Cisco UCS bios:SettingRef:dn managed object property"
    ::= { cucsBiosSettingRefEntry 2 }

cucsBiosSettingRefRn OBJECT-TYPE
    SYNTAX       SnmpAdminString
    MAX-ACCESS   read-only
    STATUS       current
    DESCRIPTION
        "Cisco UCS bios:SettingRef:rn managed object property"
    ::= { cucsBiosSettingRefEntry 3 }

cucsBiosSettingRefIsDefault OBJECT-TYPE
    SYNTAX       CucsBiosDefaultAction
    MAX-ACCESS   read-only
    STATUS       current
    DESCRIPTION
        "Cisco UCS bios:SettingRef:isDefault managed object property"
    ::= { cucsBiosSettingRefEntry 4 }

cucsBiosSettingRefIsSupported OBJECT-TYPE
    SYNTAX       CucsBiosSupportedAction
    MAX-ACCESS   read-only
    STATUS       current
    DESCRIPTION
        "Cisco UCS bios:SettingRef:isSupported managed object property"
    ::= { cucsBiosSettingRefEntry 5 }

cucsBiosSettingRefName OBJECT-TYPE
    SYNTAX       SnmpAdminString
    MAX-ACCESS   read-only
    STATUS       current
    DESCRIPTION
        "Cisco UCS bios:SettingRef:name managed object property"
    ::= { cucsBiosSettingRefEntry 6 }

cucsBiosSettingRefConstantName OBJECT-TYPE
    SYNTAX       SnmpAdminString
    MAX-ACCESS   read-only
    STATUS       current
    DESCRIPTION
        "Cisco UCS bios:SettingRef:constantName managed object property"
    ::= { cucsBiosSettingRefEntry 7 }

cucsBiosSettingsTable OBJECT-TYPE
    SYNTAX           SEQUENCE OF CucsBiosSettingsEntry
    MAX-ACCESS       not-accessible
    STATUS           current
    DESCRIPTION
        "Cisco UCS bios:Settings managed object table"
    ::= { cucsBiosObjects 8 }

cucsBiosSettingsEntry OBJECT-TYPE
    SYNTAX           CucsBiosSettingsEntry
    MAX-ACCESS       not-accessible
    STATUS           current
    DESCRIPTION
        "Entry for the cucsBiosSettingsTable table."
    INDEX { cucsBiosSettingsInstanceId }
    ::= { cucsBiosSettingsTable 1 }

CucsBiosSettingsEntry ::= SEQUENCE {
    cucsBiosSettingsInstanceId                                       CucsManagedObjectId,
    cucsBiosSettingsDn                                               CucsManagedObjectDn,
    cucsBiosSettingsRn                                               SnmpAdminString,
    cucsBiosSettingsPropAcl                                          Unsigned64
}

cucsBiosSettingsInstanceId OBJECT-TYPE
    SYNTAX       CucsManagedObjectId
    MAX-ACCESS   not-accessible
    STATUS       current
    DESCRIPTION
        "Instance identifier of the managed object."
    ::= { cucsBiosSettingsEntry 1 }

cucsBiosSettingsDn OBJECT-TYPE
    SYNTAX       CucsManagedObjectDn
    MAX-ACCESS   read-only
    STATUS       current
    DESCRIPTION
        "Cisco UCS bios:Settings:dn managed object property"
    ::= { cucsBiosSettingsEntry 2 }

cucsBiosSettingsRn OBJECT-TYPE
    SYNTAX       SnmpAdminString
    MAX-ACCESS   read-only
    STATUS       current
    DESCRIPTION
        "Cisco UCS bios:Settings:rn managed object property"
    ::= { cucsBiosSettingsEntry 3 }

cucsBiosSettingsPropAcl OBJECT-TYPE
    SYNTAX       Unsigned64
    MAX-ACCESS   read-only
    STATUS       current
    DESCRIPTION
        "Cisco UCS bios:Settings:propAcl managed object property"
    ::= { cucsBiosSettingsEntry 4 }

cucsBiosTokenFeatureGroupTable OBJECT-TYPE
    SYNTAX           SEQUENCE OF CucsBiosTokenFeatureGroupEntry
    MAX-ACCESS       not-accessible
    STATUS           current
    DESCRIPTION
        "Cisco UCS bios:TokenFeatureGroup managed object table"
    ::= { cucsBiosObjects 111 }

cucsBiosTokenFeatureGroupEntry OBJECT-TYPE
    SYNTAX           CucsBiosTokenFeatureGroupEntry
    MAX-ACCESS       not-accessible
    STATUS           current
    DESCRIPTION
        "Entry for the cucsBiosTokenFeatureGroupTable table."
    INDEX { cucsBiosTokenFeatureGroupInstanceId }
    ::= { cucsBiosTokenFeatureGroupTable 1 }

CucsBiosTokenFeatureGroupEntry ::= SEQUENCE {
    cucsBiosTokenFeatureGroupInstanceId                              CucsManagedObjectId,
    cucsBiosTokenFeatureGroupDn                                      CucsManagedObjectDn,
    cucsBiosTokenFeatureGroupRn                                      SnmpAdminString,
    cucsBiosTokenFeatureGroupName                                    SnmpAdminString,
    cucsBiosTokenFeatureGroupSupportedByDefault                      CucsBiosSupportedAction
}

cucsBiosTokenFeatureGroupInstanceId OBJECT-TYPE
    SYNTAX       CucsManagedObjectId
    MAX-ACCESS   not-accessible
    STATUS       current
    DESCRIPTION
        "Instance identifier of the managed object."
    ::= { cucsBiosTokenFeatureGroupEntry 1 }

cucsBiosTokenFeatureGroupDn OBJECT-TYPE
    SYNTAX       CucsManagedObjectDn
    MAX-ACCESS   read-only
    STATUS       current
    DESCRIPTION
        "Cisco UCS bios:TokenFeatureGroup:dn managed object property"
    ::= { cucsBiosTokenFeatureGroupEntry 2 }

cucsBiosTokenFeatureGroupRn OBJECT-TYPE
    SYNTAX       SnmpAdminString
    MAX-ACCESS   read-only
    STATUS       current
    DESCRIPTION
        "Cisco UCS bios:TokenFeatureGroup:rn managed object property"
    ::= { cucsBiosTokenFeatureGroupEntry 3 }

cucsBiosTokenFeatureGroupName OBJECT-TYPE
    SYNTAX       SnmpAdminString
    MAX-ACCESS   read-only
    STATUS       current
    DESCRIPTION
        "Cisco UCS bios:TokenFeatureGroup:name managed object property"
    ::= { cucsBiosTokenFeatureGroupEntry 4 }

cucsBiosTokenFeatureGroupSupportedByDefault OBJECT-TYPE
    SYNTAX       CucsBiosSupportedAction
    MAX-ACCESS   read-only
    STATUS       current
    DESCRIPTION
        "Cisco UCS bios:TokenFeatureGroup:supportedByDefault
        managed object property"
    ::= { cucsBiosTokenFeatureGroupEntry 5 }

cucsBiosTokenParamTable OBJECT-TYPE
    SYNTAX           SEQUENCE OF CucsBiosTokenParamEntry
    MAX-ACCESS       not-accessible
    STATUS           current
    DESCRIPTION
        "Cisco UCS bios:TokenParam managed object table"
    ::= { cucsBiosObjects 112 }

cucsBiosTokenParamEntry OBJECT-TYPE
    SYNTAX           CucsBiosTokenParamEntry
    MAX-ACCESS       not-accessible
    STATUS           current
    DESCRIPTION
        "Entry for the cucsBiosTokenParamTable table."
    INDEX { cucsBiosTokenParamInstanceId }
    ::= { cucsBiosTokenParamTable 1 }

CucsBiosTokenParamEntry ::= SEQUENCE {
    cucsBiosTokenParamInstanceId                                     CucsManagedObjectId,
    cucsBiosTokenParamDn                                             CucsManagedObjectDn,
    cucsBiosTokenParamRn                                             SnmpAdminString,
    cucsBiosTokenParamLegacyPropId                                   SnmpAdminString,
    cucsBiosTokenParamParamName                                      SnmpAdminString,
    cucsBiosTokenParamTargetTokenName                                SnmpAdminString,
    cucsBiosTokenParamUiGroupName                                    SnmpAdminString
}

cucsBiosTokenParamInstanceId OBJECT-TYPE
    SYNTAX       CucsManagedObjectId
    MAX-ACCESS   not-accessible
    STATUS       current
    DESCRIPTION
        "Instance identifier of the managed object."
    ::= { cucsBiosTokenParamEntry 1 }

cucsBiosTokenParamDn OBJECT-TYPE
    SYNTAX       CucsManagedObjectDn
    MAX-ACCESS   read-only
    STATUS       current
    DESCRIPTION
        "Cisco UCS bios:TokenParam:dn managed object property"
    ::= { cucsBiosTokenParamEntry 2 }

cucsBiosTokenParamRn OBJECT-TYPE
    SYNTAX       SnmpAdminString
    MAX-ACCESS   read-only
    STATUS       current
    DESCRIPTION
        "Cisco UCS bios:TokenParam:rn managed object property"
    ::= { cucsBiosTokenParamEntry 3 }

cucsBiosTokenParamLegacyPropId OBJECT-TYPE
    SYNTAX       SnmpAdminString
    MAX-ACCESS   read-only
    STATUS       current
    DESCRIPTION
        "Cisco UCS bios:TokenParam:legacyPropId managed object property"
    ::= { cucsBiosTokenParamEntry 4 }

cucsBiosTokenParamParamName OBJECT-TYPE
    SYNTAX       SnmpAdminString
    MAX-ACCESS   read-only
    STATUS       current
    DESCRIPTION
        "Cisco UCS bios:TokenParam:paramName managed object property"
    ::= { cucsBiosTokenParamEntry 5 }

cucsBiosTokenParamTargetTokenName OBJECT-TYPE
    SYNTAX       SnmpAdminString
    MAX-ACCESS   read-only
    STATUS       current
    DESCRIPTION
        "Cisco UCS bios:TokenParam:targetTokenName managed
        object property"
    ::= { cucsBiosTokenParamEntry 6 }

cucsBiosTokenParamUiGroupName OBJECT-TYPE
    SYNTAX       SnmpAdminString
    MAX-ACCESS   read-only
    STATUS       current
    DESCRIPTION
        "Cisco UCS bios:TokenParam:uiGroupName managed object property"
    ::= { cucsBiosTokenParamEntry 7 }

cucsBiosTokenSettingsTable OBJECT-TYPE
    SYNTAX           SEQUENCE OF CucsBiosTokenSettingsEntry
    MAX-ACCESS       not-accessible
    STATUS           current
    DESCRIPTION
        "Cisco UCS bios:TokenSettings managed object table"
    ::= { cucsBiosObjects 113 }

cucsBiosTokenSettingsEntry OBJECT-TYPE
    SYNTAX           CucsBiosTokenSettingsEntry
    MAX-ACCESS       not-accessible
    STATUS           current
    DESCRIPTION
        "Entry for the cucsBiosTokenSettingsTable table."
    INDEX { cucsBiosTokenSettingsInstanceId }
    ::= { cucsBiosTokenSettingsTable 1 }

CucsBiosTokenSettingsEntry ::= SEQUENCE {
    cucsBiosTokenSettingsInstanceId                                  CucsManagedObjectId,
    cucsBiosTokenSettingsDn                                          CucsManagedObjectDn,
    cucsBiosTokenSettingsRn                                          SnmpAdminString,
    cucsBiosTokenSettingsBiosRetSettingName                          SnmpAdminString,
    cucsBiosTokenSettingsIsAssigned                                  TruthValue,
    cucsBiosTokenSettingsLegacyPropVal                               SnmpAdminString,
    cucsBiosTokenSettingsSettingsMoRn                                SnmpAdminString,
    cucsBiosTokenSettingsTargetTokenValue                            SnmpAdminString
}

cucsBiosTokenSettingsInstanceId OBJECT-TYPE
    SYNTAX       CucsManagedObjectId
    MAX-ACCESS   not-accessible
    STATUS       current
    DESCRIPTION
        "Instance identifier of the managed object."
    ::= { cucsBiosTokenSettingsEntry 1 }

cucsBiosTokenSettingsDn OBJECT-TYPE
    SYNTAX       CucsManagedObjectDn
    MAX-ACCESS   read-only
    STATUS       current
    DESCRIPTION
        "Cisco UCS bios:TokenSettings:dn managed object property"
    ::= { cucsBiosTokenSettingsEntry 2 }

cucsBiosTokenSettingsRn OBJECT-TYPE
    SYNTAX       SnmpAdminString
    MAX-ACCESS   read-only
    STATUS       current
    DESCRIPTION
        "Cisco UCS bios:TokenSettings:rn managed object property"
    ::= { cucsBiosTokenSettingsEntry 3 }

cucsBiosTokenSettingsBiosRetSettingName OBJECT-TYPE
    SYNTAX       SnmpAdminString
    MAX-ACCESS   read-only
    STATUS       current
    DESCRIPTION
        "Cisco UCS bios:TokenSettings:biosRetSettingName
        managed object property"
    ::= { cucsBiosTokenSettingsEntry 4 }

cucsBiosTokenSettingsIsAssigned OBJECT-TYPE
    SYNTAX       TruthValue
    MAX-ACCESS   read-only
    STATUS       current
    DESCRIPTION
        "Cisco UCS bios:TokenSettings:isAssigned managed object property"
    ::= { cucsBiosTokenSettingsEntry 5 }

cucsBiosTokenSettingsLegacyPropVal OBJECT-TYPE
    SYNTAX       SnmpAdminString
    MAX-ACCESS   read-only
    STATUS       current
    DESCRIPTION
        "Cisco UCS bios:TokenSettings:legacyPropVal managed
        object property"
    ::= { cucsBiosTokenSettingsEntry 6 }

cucsBiosTokenSettingsSettingsMoRn OBJECT-TYPE
    SYNTAX       SnmpAdminString
    MAX-ACCESS   read-only
    STATUS       current
    DESCRIPTION
        "Cisco UCS bios:TokenSettings:settingsMoRn managed
        object property"
    ::= { cucsBiosTokenSettingsEntry 7 }

cucsBiosTokenSettingsTargetTokenValue OBJECT-TYPE
    SYNTAX       SnmpAdminString
    MAX-ACCESS   read-only
    STATUS       current
    DESCRIPTION
        "Cisco UCS bios:TokenSettings:targetTokenValue
        managed object property"
    ::= { cucsBiosTokenSettingsEntry 8 }

cucsBiosUnitTable OBJECT-TYPE
    SYNTAX           SEQUENCE OF CucsBiosUnitEntry
    MAX-ACCESS       not-accessible
    STATUS           current
    DESCRIPTION
        "Cisco UCS bios:Unit managed object table"
    ::= { cucsBiosObjects 9 }

cucsBiosUnitEntry OBJECT-TYPE
    SYNTAX           CucsBiosUnitEntry
    MAX-ACCESS       not-accessible
    STATUS           current
    DESCRIPTION
        "Entry for the cucsBiosUnitTable table."
    INDEX { cucsBiosUnitInstanceId }
    ::= { cucsBiosUnitTable 1 }

CucsBiosUnitEntry ::= SEQUENCE {
    cucsBiosUnitInstanceId                                           CucsManagedObjectId,
    cucsBiosUnitDn                                                   CucsManagedObjectDn,
    cucsBiosUnitRn                                                   SnmpAdminString,
    cucsBiosUnitInitSeq                                              SnmpAdminString,
    cucsBiosUnitInitTs                                               DateAndTime,
    cucsBiosUnitModel                                                SnmpAdminString,
    cucsBiosUnitRevision                                             SnmpAdminString,
    cucsBiosUnitSerial                                               SnmpAdminString,
    cucsBiosUnitVendor                                               SnmpAdminString
}

cucsBiosUnitInstanceId OBJECT-TYPE
    SYNTAX       CucsManagedObjectId
    MAX-ACCESS   not-accessible
    STATUS       current
    DESCRIPTION
        "Instance identifier of the managed object."
    ::= { cucsBiosUnitEntry 1 }

cucsBiosUnitDn OBJECT-TYPE
    SYNTAX       CucsManagedObjectDn
    MAX-ACCESS   read-only
    STATUS       current
    DESCRIPTION
        "Cisco UCS bios:Unit:dn managed object property"
    ::= { cucsBiosUnitEntry 2 }

cucsBiosUnitRn OBJECT-TYPE
    SYNTAX       SnmpAdminString
    MAX-ACCESS   read-only
    STATUS       current
    DESCRIPTION
        "Cisco UCS bios:Unit:rn managed object property"
    ::= { cucsBiosUnitEntry 3 }

cucsBiosUnitInitSeq OBJECT-TYPE
    SYNTAX       SnmpAdminString
    MAX-ACCESS   read-only
    STATUS       current
    DESCRIPTION
        "Cisco UCS bios:Unit:initSeq managed object property"
    ::= { cucsBiosUnitEntry 4 }

cucsBiosUnitInitTs OBJECT-TYPE
    SYNTAX       DateAndTime
    MAX-ACCESS   read-only
    STATUS       current
    DESCRIPTION
        "Cisco UCS bios:Unit:initTs managed object property"
    ::= { cucsBiosUnitEntry 5 }

cucsBiosUnitModel OBJECT-TYPE
    SYNTAX       SnmpAdminString
    MAX-ACCESS   read-only
    STATUS       current
    DESCRIPTION
        "Cisco UCS bios:Unit:model managed object property"
    ::= { cucsBiosUnitEntry 6 }

cucsBiosUnitRevision OBJECT-TYPE
    SYNTAX       SnmpAdminString
    MAX-ACCESS   read-only
    STATUS       current
    DESCRIPTION
        "Cisco UCS bios:Unit:revision managed object property"
    ::= { cucsBiosUnitEntry 7 }

cucsBiosUnitSerial OBJECT-TYPE
    SYNTAX       SnmpAdminString
    MAX-ACCESS   read-only
    STATUS       current
    DESCRIPTION
        "Cisco UCS bios:Unit:serial managed object property"
    ::= { cucsBiosUnitEntry 8 }

cucsBiosUnitVendor OBJECT-TYPE
    SYNTAX       SnmpAdminString
    MAX-ACCESS   read-only
    STATUS       current
    DESCRIPTION
        "Cisco UCS bios:Unit:vendor managed object property"
    ::= { cucsBiosUnitEntry 9 }

cucsBiosVIdentityParamsTable OBJECT-TYPE
    SYNTAX           SEQUENCE OF CucsBiosVIdentityParamsEntry
    MAX-ACCESS       not-accessible
    STATUS           current
    DESCRIPTION
        "Cisco UCS bios:VIdentityParams managed object table"
    ::= { cucsBiosObjects 51 }

cucsBiosVIdentityParamsEntry OBJECT-TYPE
    SYNTAX           CucsBiosVIdentityParamsEntry
    MAX-ACCESS       not-accessible
    STATUS           current
    DESCRIPTION
        "Entry for the cucsBiosVIdentityParamsTable table."
    INDEX { cucsBiosVIdentityParamsInstanceId }
    ::= { cucsBiosVIdentityParamsTable 1 }

CucsBiosVIdentityParamsEntry ::= SEQUENCE {
    cucsBiosVIdentityParamsInstanceId                                CucsManagedObjectId,
    cucsBiosVIdentityParamsDn                                        CucsManagedObjectDn,
    cucsBiosVIdentityParamsRn                                        SnmpAdminString,
    cucsBiosVIdentityParamsLsServerName                              SnmpAdminString,
    cucsBiosVIdentityParamsLsServerTmplName                          SnmpAdminString,
    cucsBiosVIdentityParamsSysName                                   SnmpAdminString
}

cucsBiosVIdentityParamsInstanceId OBJECT-TYPE
    SYNTAX       CucsManagedObjectId
    MAX-ACCESS   not-accessible
    STATUS       current
    DESCRIPTION
        "Instance identifier of the managed object."
    ::= { cucsBiosVIdentityParamsEntry 1 }

cucsBiosVIdentityParamsDn OBJECT-TYPE
    SYNTAX       CucsManagedObjectDn
    MAX-ACCESS   read-only
    STATUS       current
    DESCRIPTION
        "Cisco UCS bios:VIdentityParams:dn managed object property"
    ::= { cucsBiosVIdentityParamsEntry 2 }

cucsBiosVIdentityParamsRn OBJECT-TYPE
    SYNTAX       SnmpAdminString
    MAX-ACCESS   read-only
    STATUS       current
    DESCRIPTION
        "Cisco UCS bios:VIdentityParams:rn managed object property"
    ::= { cucsBiosVIdentityParamsEntry 3 }

cucsBiosVIdentityParamsLsServerName OBJECT-TYPE
    SYNTAX       SnmpAdminString
    MAX-ACCESS   read-only
    STATUS       current
    DESCRIPTION
        "Cisco UCS bios:VIdentityParams:lsServerName managed
        object property"
    ::= { cucsBiosVIdentityParamsEntry 4 }

cucsBiosVIdentityParamsLsServerTmplName OBJECT-TYPE
    SYNTAX       SnmpAdminString
    MAX-ACCESS   read-only
    STATUS       current
    DESCRIPTION
        "Cisco UCS bios:VIdentityParams:lsServerTmplName
        managed object property"
    ::= { cucsBiosVIdentityParamsEntry 5 }

cucsBiosVIdentityParamsSysName OBJECT-TYPE
    SYNTAX       SnmpAdminString
    MAX-ACCESS   read-only
    STATUS       current
    DESCRIPTION
        "Cisco UCS bios:VIdentityParams:sysName managed object property"
    ::= { cucsBiosVIdentityParamsEntry 6 }

cucsBiosVProfileTable OBJECT-TYPE
    SYNTAX           SEQUENCE OF CucsBiosVProfileEntry
    MAX-ACCESS       not-accessible
    STATUS           current
    DESCRIPTION
        "Cisco UCS bios:VProfile managed object table"
    ::= { cucsBiosObjects 10 }

cucsBiosVProfileEntry OBJECT-TYPE
    SYNTAX           CucsBiosVProfileEntry
    MAX-ACCESS       not-accessible
    STATUS           current
    DESCRIPTION
        "Entry for the cucsBiosVProfileTable table."
    INDEX { cucsBiosVProfileInstanceId }
    ::= { cucsBiosVProfileTable 1 }

CucsBiosVProfileEntry ::= SEQUENCE {
    cucsBiosVProfileInstanceId                                       CucsManagedObjectId,
    cucsBiosVProfileDn                                               CucsManagedObjectDn,
    cucsBiosVProfileRn                                               SnmpAdminString,
    cucsBiosVProfileDescr                                            SnmpAdminString,
    cucsBiosVProfileIntId                                            SnmpAdminString,
    cucsBiosVProfileName                                             SnmpAdminString,
    cucsBiosVProfileRebootOnUpdate                                   TruthValue,
    cucsBiosVProfilePolicyLevel                                      Gauge32,
    cucsBiosVProfilePolicyOwner                                      CucsPolicyPolicyOwner
}

cucsBiosVProfileInstanceId OBJECT-TYPE
    SYNTAX       CucsManagedObjectId
    MAX-ACCESS   not-accessible
    STATUS       current
    DESCRIPTION
        "Instance identifier of the managed object."
    ::= { cucsBiosVProfileEntry 1 }

cucsBiosVProfileDn OBJECT-TYPE
    SYNTAX       CucsManagedObjectDn
    MAX-ACCESS   read-only
    STATUS       current
    DESCRIPTION
        "Cisco UCS bios:VProfile:dn managed object property"
    ::= { cucsBiosVProfileEntry 2 }

cucsBiosVProfileRn OBJECT-TYPE
    SYNTAX       SnmpAdminString
    MAX-ACCESS   read-only
    STATUS       current
    DESCRIPTION
        "Cisco UCS bios:VProfile:rn managed object property"
    ::= { cucsBiosVProfileEntry 3 }

cucsBiosVProfileDescr OBJECT-TYPE
    SYNTAX       SnmpAdminString
    MAX-ACCESS   read-only
    STATUS       current
    DESCRIPTION
        "Cisco UCS bios:VProfile:descr managed object property"
    ::= { cucsBiosVProfileEntry 4 }

cucsBiosVProfileIntId OBJECT-TYPE
    SYNTAX       SnmpAdminString
    MAX-ACCESS   read-only
    STATUS       current
    DESCRIPTION
        "Cisco UCS bios:VProfile:intId managed object property"
    ::= { cucsBiosVProfileEntry 5 }

cucsBiosVProfileName OBJECT-TYPE
    SYNTAX       SnmpAdminString
    MAX-ACCESS   read-only
    STATUS       current
    DESCRIPTION
        "Cisco UCS bios:VProfile:name managed object property"
    ::= { cucsBiosVProfileEntry 6 }

cucsBiosVProfileRebootOnUpdate OBJECT-TYPE
    SYNTAX       TruthValue
    MAX-ACCESS   read-only
    STATUS       current
    DESCRIPTION
        "Cisco UCS bios:VProfile:rebootOnUpdate managed object property"
    ::= { cucsBiosVProfileEntry 7 }

cucsBiosVProfilePolicyLevel OBJECT-TYPE
    SYNTAX       Gauge32
    MAX-ACCESS   read-only
    STATUS       current
    DESCRIPTION
        "Cisco UCS bios:VProfile:policyLevel managed object property"
    ::= { cucsBiosVProfileEntry 8 }

cucsBiosVProfilePolicyOwner OBJECT-TYPE
    SYNTAX       CucsPolicyPolicyOwner
    MAX-ACCESS   read-only
    STATUS       current
    DESCRIPTION
        "Cisco UCS bios:VProfile:policyOwner managed object property"
    ::= { cucsBiosVProfileEntry 9 }

cucsBiosVfACPI10SupportTable OBJECT-TYPE
    SYNTAX           SEQUENCE OF CucsBiosVfACPI10SupportEntry
    MAX-ACCESS       not-accessible
    STATUS           current
    DESCRIPTION
        "Cisco UCS bios:VfACPI10Support managed object table"
    ::= { cucsBiosObjects 27 }

cucsBiosVfACPI10SupportEntry OBJECT-TYPE
    SYNTAX           CucsBiosVfACPI10SupportEntry
    MAX-ACCESS       not-accessible
    STATUS           current
    DESCRIPTION
        "Entry for the cucsBiosVfACPI10SupportTable table."
    INDEX { cucsBiosVfACPI10SupportInstanceId }
    ::= { cucsBiosVfACPI10SupportTable 1 }

CucsBiosVfACPI10SupportEntry ::= SEQUENCE {
    cucsBiosVfACPI10SupportInstanceId                                CucsManagedObjectId,
    cucsBiosVfACPI10SupportDn                                        CucsManagedObjectDn,
    cucsBiosVfACPI10SupportRn                                        SnmpAdminString,
    cucsBiosVfACPI10SupportVpACPI10Support                           CucsBiosVfACPI10SupportVpACPI10Support,
    cucsBiosVfACPI10SupportPropAcl                                   Unsigned64,
    cucsBiosVfACPI10SupportSupportedByDefault                        CucsBiosSupportedAction
}

cucsBiosVfACPI10SupportInstanceId OBJECT-TYPE
    SYNTAX       CucsManagedObjectId
    MAX-ACCESS   not-accessible
    STATUS       current
    DESCRIPTION
        "Instance identifier of the managed object."
    ::= { cucsBiosVfACPI10SupportEntry 1 }

cucsBiosVfACPI10SupportDn OBJECT-TYPE
    SYNTAX       CucsManagedObjectDn
    MAX-ACCESS   read-only
    STATUS       current
    DESCRIPTION
        "Cisco UCS bios:VfACPI10Support:dn managed object property"
    ::= { cucsBiosVfACPI10SupportEntry 2 }

cucsBiosVfACPI10SupportRn OBJECT-TYPE
    SYNTAX       SnmpAdminString
    MAX-ACCESS   read-only
    STATUS       current
    DESCRIPTION
        "Cisco UCS bios:VfACPI10Support:rn managed object property"
    ::= { cucsBiosVfACPI10SupportEntry 3 }

cucsBiosVfACPI10SupportVpACPI10Support OBJECT-TYPE
    SYNTAX       CucsBiosVfACPI10SupportVpACPI10Support
    MAX-ACCESS   read-only
    STATUS       current
    DESCRIPTION
        "Cisco UCS bios:VfACPI10Support:vpACPI10Support
        managed object property"
    ::= { cucsBiosVfACPI10SupportEntry 4 }

cucsBiosVfACPI10SupportPropAcl OBJECT-TYPE
    SYNTAX       Unsigned64
    MAX-ACCESS   read-only
    STATUS       current
    DESCRIPTION
        "Cisco UCS bios:VfACPI10Support:propAcl managed object property"
    ::= { cucsBiosVfACPI10SupportEntry 5 }

cucsBiosVfACPI10SupportSupportedByDefault OBJECT-TYPE
    SYNTAX       CucsBiosSupportedAction
    MAX-ACCESS   read-only
    STATUS       current
    DESCRIPTION
        "Cisco UCS bios:VfACPI10Support:supportedByDefault
        managed object property"
    ::= { cucsBiosVfACPI10SupportEntry 6 }

cucsBiosVfASPMSupportTable OBJECT-TYPE
    SYNTAX           SEQUENCE OF CucsBiosVfASPMSupportEntry
    MAX-ACCESS       not-accessible
    STATUS           current
    DESCRIPTION
        "Cisco UCS bios:VfASPMSupport managed object table"
    ::= { cucsBiosObjects 85 }

cucsBiosVfASPMSupportEntry OBJECT-TYPE
    SYNTAX           CucsBiosVfASPMSupportEntry
    MAX-ACCESS       not-accessible
    STATUS           current
    DESCRIPTION
        "Entry for the cucsBiosVfASPMSupportTable table."
    INDEX { cucsBiosVfASPMSupportInstanceId }
    ::= { cucsBiosVfASPMSupportTable 1 }

CucsBiosVfASPMSupportEntry ::= SEQUENCE {
    cucsBiosVfASPMSupportInstanceId                                  CucsManagedObjectId,
    cucsBiosVfASPMSupportDn                                          CucsManagedObjectDn,
    cucsBiosVfASPMSupportRn                                          SnmpAdminString,
    cucsBiosVfASPMSupportVpASPMSupport                               CucsBiosVfASPMSupportVpASPMSupport,
    cucsBiosVfASPMSupportSupportedByDefault                          CucsBiosSupportedAction,
    cucsBiosVfASPMSupportPropAcl                                     Unsigned64
}

cucsBiosVfASPMSupportInstanceId OBJECT-TYPE
    SYNTAX       CucsManagedObjectId
    MAX-ACCESS   not-accessible
    STATUS       current
    DESCRIPTION
        "Instance identifier of the managed object."
    ::= { cucsBiosVfASPMSupportEntry 1 }

cucsBiosVfASPMSupportDn OBJECT-TYPE
    SYNTAX       CucsManagedObjectDn
    MAX-ACCESS   read-only
    STATUS       current
    DESCRIPTION
        "Cisco UCS bios:VfASPMSupport:dn managed object property"
    ::= { cucsBiosVfASPMSupportEntry 2 }

cucsBiosVfASPMSupportRn OBJECT-TYPE
    SYNTAX       SnmpAdminString
    MAX-ACCESS   read-only
    STATUS       current
    DESCRIPTION
        "Cisco UCS bios:VfASPMSupport:rn managed object property"
    ::= { cucsBiosVfASPMSupportEntry 3 }

cucsBiosVfASPMSupportVpASPMSupport OBJECT-TYPE
    SYNTAX       CucsBiosVfASPMSupportVpASPMSupport
    MAX-ACCESS   read-only
    STATUS       current
    DESCRIPTION
        "Cisco UCS bios:VfASPMSupport:vpASPMSupport managed
        object property"
    ::= { cucsBiosVfASPMSupportEntry 4 }

cucsBiosVfASPMSupportSupportedByDefault OBJECT-TYPE
    SYNTAX       CucsBiosSupportedAction
    MAX-ACCESS   read-only
    STATUS       current
    DESCRIPTION
        "Cisco UCS bios:VfASPMSupport:supportedByDefault
        managed object property"
    ::= { cucsBiosVfASPMSupportEntry 5 }

cucsBiosVfASPMSupportPropAcl OBJECT-TYPE
    SYNTAX       Unsigned64
    MAX-ACCESS   read-only
    STATUS       current
    DESCRIPTION
        "Cisco UCS bios:VfASPMSupport:propAcl managed object property"
    ::= { cucsBiosVfASPMSupportEntry 6 }

cucsBiosVfAllUSBDevicesTable OBJECT-TYPE
    SYNTAX           SEQUENCE OF CucsBiosVfAllUSBDevicesEntry
    MAX-ACCESS       not-accessible
    STATUS           current
    DESCRIPTION
        "Cisco UCS bios:VfAllUSBDevices managed object table"
    ::= { cucsBiosObjects 64 }

cucsBiosVfAllUSBDevicesEntry OBJECT-TYPE
    SYNTAX           CucsBiosVfAllUSBDevicesEntry
    MAX-ACCESS       not-accessible
    STATUS           current
    DESCRIPTION
        "Entry for the cucsBiosVfAllUSBDevicesTable table."
    INDEX { cucsBiosVfAllUSBDevicesInstanceId }
    ::= { cucsBiosVfAllUSBDevicesTable 1 }

CucsBiosVfAllUSBDevicesEntry ::= SEQUENCE {
    cucsBiosVfAllUSBDevicesInstanceId                                CucsManagedObjectId,
    cucsBiosVfAllUSBDevicesDn                                        CucsManagedObjectDn,
    cucsBiosVfAllUSBDevicesRn                                        SnmpAdminString,
    cucsBiosVfAllUSBDevicesVpAllUSBDevices                           CucsBiosVfAllUSBDevicesVpAllUSBDevices,
    cucsBiosVfAllUSBDevicesPropAcl                                   Unsigned64,
    cucsBiosVfAllUSBDevicesSupportedByDefault                        CucsBiosSupportedAction
}

cucsBiosVfAllUSBDevicesInstanceId OBJECT-TYPE
    SYNTAX       CucsManagedObjectId
    MAX-ACCESS   not-accessible
    STATUS       current
    DESCRIPTION
        "Instance identifier of the managed object."
    ::= { cucsBiosVfAllUSBDevicesEntry 1 }

cucsBiosVfAllUSBDevicesDn OBJECT-TYPE
    SYNTAX       CucsManagedObjectDn
    MAX-ACCESS   read-only
    STATUS       current
    DESCRIPTION
        "Cisco UCS bios:VfAllUSBDevices:dn managed object property"
    ::= { cucsBiosVfAllUSBDevicesEntry 2 }

cucsBiosVfAllUSBDevicesRn OBJECT-TYPE
    SYNTAX       SnmpAdminString
    MAX-ACCESS   read-only
    STATUS       current
    DESCRIPTION
        "Cisco UCS bios:VfAllUSBDevices:rn managed object property"
    ::= { cucsBiosVfAllUSBDevicesEntry 3 }

cucsBiosVfAllUSBDevicesVpAllUSBDevices OBJECT-TYPE
    SYNTAX       CucsBiosVfAllUSBDevicesVpAllUSBDevices
    MAX-ACCESS   read-only
    STATUS       current
    DESCRIPTION
        "Cisco UCS bios:VfAllUSBDevices:vpAllUSBDevices
        managed object property"
    ::= { cucsBiosVfAllUSBDevicesEntry 4 }

cucsBiosVfAllUSBDevicesPropAcl OBJECT-TYPE
    SYNTAX       Unsigned64
    MAX-ACCESS   read-only
    STATUS       current
    DESCRIPTION
        "Cisco UCS bios:VfAllUSBDevices:propAcl managed object property"
    ::= { cucsBiosVfAllUSBDevicesEntry 5 }

cucsBiosVfAllUSBDevicesSupportedByDefault OBJECT-TYPE
    SYNTAX       CucsBiosSupportedAction
    MAX-ACCESS   read-only
    STATUS       current
    DESCRIPTION
        "Cisco UCS bios:VfAllUSBDevices:supportedByDefault
        managed object property"
    ::= { cucsBiosVfAllUSBDevicesEntry 6 }

cucsBiosVfAltitudeTable OBJECT-TYPE
    SYNTAX           SEQUENCE OF CucsBiosVfAltitudeEntry
    MAX-ACCESS       not-accessible
    STATUS           current
    DESCRIPTION
        "Cisco UCS bios:VfAltitude managed object table"
    ::= { cucsBiosObjects 78 }

cucsBiosVfAltitudeEntry OBJECT-TYPE
    SYNTAX           CucsBiosVfAltitudeEntry
    MAX-ACCESS       not-accessible
    STATUS           current
    DESCRIPTION
        "Entry for the cucsBiosVfAltitudeTable table."
    INDEX { cucsBiosVfAltitudeInstanceId }
    ::= { cucsBiosVfAltitudeTable 1 }

CucsBiosVfAltitudeEntry ::= SEQUENCE {
    cucsBiosVfAltitudeInstanceId                                     CucsManagedObjectId,
    cucsBiosVfAltitudeDn                                             CucsManagedObjectDn,
    cucsBiosVfAltitudeRn                                             SnmpAdminString,
    cucsBiosVfAltitudeVpAltitude                                     CucsBiosVfAltitudeVpAltitude,
    cucsBiosVfAltitudePropAcl                                        Unsigned64,
    cucsBiosVfAltitudeSupportedByDefault                             CucsBiosSupportedAction
}

cucsBiosVfAltitudeInstanceId OBJECT-TYPE
    SYNTAX       CucsManagedObjectId
    MAX-ACCESS   not-accessible
    STATUS       current
    DESCRIPTION
        "Instance identifier of the managed object."
    ::= { cucsBiosVfAltitudeEntry 1 }

cucsBiosVfAltitudeDn OBJECT-TYPE
    SYNTAX       CucsManagedObjectDn
    MAX-ACCESS   read-only
    STATUS       current
    DESCRIPTION
        "Cisco UCS bios:VfAltitude:dn managed object property"
    ::= { cucsBiosVfAltitudeEntry 2 }

cucsBiosVfAltitudeRn OBJECT-TYPE
    SYNTAX       SnmpAdminString
    MAX-ACCESS   read-only
    STATUS       current
    DESCRIPTION
        "Cisco UCS bios:VfAltitude:rn managed object property"
    ::= { cucsBiosVfAltitudeEntry 3 }

cucsBiosVfAltitudeVpAltitude OBJECT-TYPE
    SYNTAX       CucsBiosVfAltitudeVpAltitude
    MAX-ACCESS   read-only
    STATUS       current
    DESCRIPTION
        "Cisco UCS bios:VfAltitude:vpAltitude managed object property"
    ::= { cucsBiosVfAltitudeEntry 4 }

cucsBiosVfAltitudePropAcl OBJECT-TYPE
    SYNTAX       Unsigned64
    MAX-ACCESS   read-only
    STATUS       current
    DESCRIPTION
        "Cisco UCS bios:VfAltitude:propAcl managed object property"
    ::= { cucsBiosVfAltitudeEntry 5 }

cucsBiosVfAltitudeSupportedByDefault OBJECT-TYPE
    SYNTAX       CucsBiosSupportedAction
    MAX-ACCESS   read-only
    STATUS       current
    DESCRIPTION
        "Cisco UCS bios:VfAltitude:supportedByDefault managed
        object property"
    ::= { cucsBiosVfAltitudeEntry 6 }

cucsBiosVfAssertNMIOnPERRTable OBJECT-TYPE
    SYNTAX           SEQUENCE OF CucsBiosVfAssertNMIOnPERREntry
    MAX-ACCESS       not-accessible
    STATUS           current
    DESCRIPTION
        "Cisco UCS bios:VfAssertNMIOnPERR managed object table"
    ::= { cucsBiosObjects 28 }

cucsBiosVfAssertNMIOnPERREntry OBJECT-TYPE
    SYNTAX           CucsBiosVfAssertNMIOnPERREntry
    MAX-ACCESS       not-accessible
    STATUS           current
    DESCRIPTION
        "Entry for the cucsBiosVfAssertNMIOnPERRTable table."
    INDEX { cucsBiosVfAssertNMIOnPERRInstanceId }
    ::= { cucsBiosVfAssertNMIOnPERRTable 1 }

CucsBiosVfAssertNMIOnPERREntry ::= SEQUENCE {
    cucsBiosVfAssertNMIOnPERRInstanceId                              CucsManagedObjectId,
    cucsBiosVfAssertNMIOnPERRDn                                      CucsManagedObjectDn,
    cucsBiosVfAssertNMIOnPERRRn                                      SnmpAdminString,
    cucsBiosVfAssertNMIOnPERRVpAssertNMIOnPERR                       CucsBiosVfAssertNMIOnPERRVpAssertNMIOnPERR,
    cucsBiosVfAssertNMIOnPERRPropAcl                                 Unsigned64,
    cucsBiosVfAssertNMIOnPERRSupportedByDefault                      CucsBiosSupportedAction
}

cucsBiosVfAssertNMIOnPERRInstanceId OBJECT-TYPE
    SYNTAX       CucsManagedObjectId
    MAX-ACCESS   not-accessible
    STATUS       current
    DESCRIPTION
        "Instance identifier of the managed object."
    ::= { cucsBiosVfAssertNMIOnPERREntry 1 }

cucsBiosVfAssertNMIOnPERRDn OBJECT-TYPE
    SYNTAX       CucsManagedObjectDn
    MAX-ACCESS   read-only
    STATUS       current
    DESCRIPTION
        "Cisco UCS bios:VfAssertNMIOnPERR:dn managed object property"
    ::= { cucsBiosVfAssertNMIOnPERREntry 2 }

cucsBiosVfAssertNMIOnPERRRn OBJECT-TYPE
    SYNTAX       SnmpAdminString
    MAX-ACCESS   read-only
    STATUS       current
    DESCRIPTION
        "Cisco UCS bios:VfAssertNMIOnPERR:rn managed object property"
    ::= { cucsBiosVfAssertNMIOnPERREntry 3 }

cucsBiosVfAssertNMIOnPERRVpAssertNMIOnPERR OBJECT-TYPE
    SYNTAX       CucsBiosVfAssertNMIOnPERRVpAssertNMIOnPERR
    MAX-ACCESS   read-only
    STATUS       current
    DESCRIPTION
        "Cisco UCS bios:VfAssertNMIOnPERR:vpAssertNMIOnPERR
        managed object property"
    ::= { cucsBiosVfAssertNMIOnPERREntry 4 }

cucsBiosVfAssertNMIOnPERRPropAcl OBJECT-TYPE
    SYNTAX       Unsigned64
    MAX-ACCESS   read-only
    STATUS       current
    DESCRIPTION
        "Cisco UCS bios:VfAssertNMIOnPERR:propAcl managed object property"
    ::= { cucsBiosVfAssertNMIOnPERREntry 5 }

cucsBiosVfAssertNMIOnPERRSupportedByDefault OBJECT-TYPE
    SYNTAX       CucsBiosSupportedAction
    MAX-ACCESS   read-only
    STATUS       current
    DESCRIPTION
        "Cisco UCS bios:VfAssertNMIOnPERR:supportedByDefault
        managed object property"
    ::= { cucsBiosVfAssertNMIOnPERREntry 6 }

cucsBiosVfAssertNMIOnSERRTable OBJECT-TYPE
    SYNTAX           SEQUENCE OF CucsBiosVfAssertNMIOnSERREntry
    MAX-ACCESS       not-accessible
    STATUS           current
    DESCRIPTION
        "Cisco UCS bios:VfAssertNMIOnSERR managed object table"
    ::= { cucsBiosObjects 29 }

cucsBiosVfAssertNMIOnSERREntry OBJECT-TYPE
    SYNTAX           CucsBiosVfAssertNMIOnSERREntry
    MAX-ACCESS       not-accessible
    STATUS           current
    DESCRIPTION
        "Entry for the cucsBiosVfAssertNMIOnSERRTable table."
    INDEX { cucsBiosVfAssertNMIOnSERRInstanceId }
    ::= { cucsBiosVfAssertNMIOnSERRTable 1 }

CucsBiosVfAssertNMIOnSERREntry ::= SEQUENCE {
    cucsBiosVfAssertNMIOnSERRInstanceId                              CucsManagedObjectId,
    cucsBiosVfAssertNMIOnSERRDn                                      CucsManagedObjectDn,
    cucsBiosVfAssertNMIOnSERRRn                                      SnmpAdminString,
    cucsBiosVfAssertNMIOnSERRVpAssertNMIOnSERR                       CucsBiosVfAssertNMIOnSERRVpAssertNMIOnSERR,
    cucsBiosVfAssertNMIOnSERRPropAcl                                 Unsigned64,
    cucsBiosVfAssertNMIOnSERRSupportedByDefault                      CucsBiosSupportedAction
}

cucsBiosVfAssertNMIOnSERRInstanceId OBJECT-TYPE
    SYNTAX       CucsManagedObjectId
    MAX-ACCESS   not-accessible
    STATUS       current
    DESCRIPTION
        "Instance identifier of the managed object."
    ::= { cucsBiosVfAssertNMIOnSERREntry 1 }

cucsBiosVfAssertNMIOnSERRDn OBJECT-TYPE
    SYNTAX       CucsManagedObjectDn
    MAX-ACCESS   read-only
    STATUS       current
    DESCRIPTION
        "Cisco UCS bios:VfAssertNMIOnSERR:dn managed object property"
    ::= { cucsBiosVfAssertNMIOnSERREntry 2 }

cucsBiosVfAssertNMIOnSERRRn OBJECT-TYPE
    SYNTAX       SnmpAdminString
    MAX-ACCESS   read-only
    STATUS       current
    DESCRIPTION
        "Cisco UCS bios:VfAssertNMIOnSERR:rn managed object property"
    ::= { cucsBiosVfAssertNMIOnSERREntry 3 }

cucsBiosVfAssertNMIOnSERRVpAssertNMIOnSERR OBJECT-TYPE
    SYNTAX       CucsBiosVfAssertNMIOnSERRVpAssertNMIOnSERR
    MAX-ACCESS   read-only
    STATUS       current
    DESCRIPTION
        "Cisco UCS bios:VfAssertNMIOnSERR:vpAssertNMIOnSERR
        managed object property"
    ::= { cucsBiosVfAssertNMIOnSERREntry 4 }

cucsBiosVfAssertNMIOnSERRPropAcl OBJECT-TYPE
    SYNTAX       Unsigned64
    MAX-ACCESS   read-only
    STATUS       current
    DESCRIPTION
        "Cisco UCS bios:VfAssertNMIOnSERR:propAcl managed object property"
    ::= { cucsBiosVfAssertNMIOnSERREntry 5 }

cucsBiosVfAssertNMIOnSERRSupportedByDefault OBJECT-TYPE
    SYNTAX       CucsBiosSupportedAction
    MAX-ACCESS   read-only
    STATUS       current
    DESCRIPTION
        "Cisco UCS bios:VfAssertNMIOnSERR:supportedByDefault
        managed object property"
    ::= { cucsBiosVfAssertNMIOnSERREntry 6 }

cucsBiosVfBootOptionRetryTable OBJECT-TYPE
    SYNTAX           SEQUENCE OF CucsBiosVfBootOptionRetryEntry
    MAX-ACCESS       not-accessible
    STATUS           current
    DESCRIPTION
        "Cisco UCS bios:VfBootOptionRetry managed object table"
    ::= { cucsBiosObjects 31 }

cucsBiosVfBootOptionRetryEntry OBJECT-TYPE
    SYNTAX           CucsBiosVfBootOptionRetryEntry
    MAX-ACCESS       not-accessible
    STATUS           current
    DESCRIPTION
        "Entry for the cucsBiosVfBootOptionRetryTable table."
    INDEX { cucsBiosVfBootOptionRetryInstanceId }
    ::= { cucsBiosVfBootOptionRetryTable 1 }

CucsBiosVfBootOptionRetryEntry ::= SEQUENCE {
    cucsBiosVfBootOptionRetryInstanceId                              CucsManagedObjectId,
    cucsBiosVfBootOptionRetryDn                                      CucsManagedObjectDn,
    cucsBiosVfBootOptionRetryRn                                      SnmpAdminString,
    cucsBiosVfBootOptionRetryVpBootOptionRetry                       CucsBiosVfBootOptionRetryVpBootOptionRetry,
    cucsBiosVfBootOptionRetryPropAcl                                 Unsigned64,
    cucsBiosVfBootOptionRetrySupportedByDefault                      CucsBiosSupportedAction
}

cucsBiosVfBootOptionRetryInstanceId OBJECT-TYPE
    SYNTAX       CucsManagedObjectId
    MAX-ACCESS   not-accessible
    STATUS       current
    DESCRIPTION
        "Instance identifier of the managed object."
    ::= { cucsBiosVfBootOptionRetryEntry 1 }

cucsBiosVfBootOptionRetryDn OBJECT-TYPE
    SYNTAX       CucsManagedObjectDn
    MAX-ACCESS   read-only
    STATUS       current
    DESCRIPTION
        "Cisco UCS bios:VfBootOptionRetry:dn managed object property"
    ::= { cucsBiosVfBootOptionRetryEntry 2 }

cucsBiosVfBootOptionRetryRn OBJECT-TYPE
    SYNTAX       SnmpAdminString
    MAX-ACCESS   read-only
    STATUS       current
    DESCRIPTION
        "Cisco UCS bios:VfBootOptionRetry:rn managed object property"
    ::= { cucsBiosVfBootOptionRetryEntry 3 }

cucsBiosVfBootOptionRetryVpBootOptionRetry OBJECT-TYPE
    SYNTAX       CucsBiosVfBootOptionRetryVpBootOptionRetry
    MAX-ACCESS   read-only
    STATUS       current
    DESCRIPTION
        "Cisco UCS bios:VfBootOptionRetry:vpBootOptionRetry
        managed object property"
    ::= { cucsBiosVfBootOptionRetryEntry 4 }

cucsBiosVfBootOptionRetryPropAcl OBJECT-TYPE
    SYNTAX       Unsigned64
    MAX-ACCESS   read-only
    STATUS       current
    DESCRIPTION
        "Cisco UCS bios:VfBootOptionRetry:propAcl managed object property"
    ::= { cucsBiosVfBootOptionRetryEntry 5 }

cucsBiosVfBootOptionRetrySupportedByDefault OBJECT-TYPE
    SYNTAX       CucsBiosSupportedAction
    MAX-ACCESS   read-only
    STATUS       current
    DESCRIPTION
        "Cisco UCS bios:VfBootOptionRetry:supportedByDefault
        managed object property"
    ::= { cucsBiosVfBootOptionRetryEntry 6 }

cucsBiosVfCPUHardwarePowerManagementTable OBJECT-TYPE
    SYNTAX           SEQUENCE OF CucsBiosVfCPUHardwarePowerManagementEntry
    MAX-ACCESS       not-accessible
    STATUS           current
    DESCRIPTION
        "Cisco UCS bios:VfCPUHardwarePowerManagement managed object table"
    ::= { cucsBiosObjects 92 }

cucsBiosVfCPUHardwarePowerManagementEntry OBJECT-TYPE
    SYNTAX           CucsBiosVfCPUHardwarePowerManagementEntry
    MAX-ACCESS       not-accessible
    STATUS           current
    DESCRIPTION
        "Entry for the cucsBiosVfCPUHardwarePowerManagementTable table."
    INDEX { cucsBiosVfCPUHardwarePowerManagementInstanceId }
    ::= { cucsBiosVfCPUHardwarePowerManagementTable 1 }

CucsBiosVfCPUHardwarePowerManagementEntry ::= SEQUENCE {
    cucsBiosVfCPUHardwarePowerManagementInstanceId                   CucsManagedObjectId,
    cucsBiosVfCPUHardwarePowerManagementDn                           CucsManagedObjectDn,
    cucsBiosVfCPUHardwarePowerManagementRn                           SnmpAdminString,
    cucsBiosVfCPUHardwarePowerManagementSupportedByDefault           CucsBiosSupportedAction,
    cucsBiosVfCPUHardwarePowerManagementVpCPUHardwarePowerManagement CucsBiosVfCPUHardwarePowerManagementVpCPUHardwarePowerManagement,
    cucsBiosVfCPUHardwarePowerManagementPropAcl                      Unsigned64
}

cucsBiosVfCPUHardwarePowerManagementInstanceId OBJECT-TYPE
    SYNTAX       CucsManagedObjectId
    MAX-ACCESS   not-accessible
    STATUS       current
    DESCRIPTION
        "Instance identifier of the managed object."
    ::= { cucsBiosVfCPUHardwarePowerManagementEntry 1 }

cucsBiosVfCPUHardwarePowerManagementDn OBJECT-TYPE
    SYNTAX       CucsManagedObjectDn
    MAX-ACCESS   read-only
    STATUS       current
    DESCRIPTION
        "Cisco UCS bios:VfCPUHardwarePowerManagement:dn
        managed object property"
    ::= { cucsBiosVfCPUHardwarePowerManagementEntry 2 }

cucsBiosVfCPUHardwarePowerManagementRn OBJECT-TYPE
    SYNTAX       SnmpAdminString
    MAX-ACCESS   read-only
    STATUS       current
    DESCRIPTION
        "Cisco UCS bios:VfCPUHardwarePowerManagement:rn
        managed object property"
    ::= { cucsBiosVfCPUHardwarePowerManagementEntry 3 }

cucsBiosVfCPUHardwarePowerManagementSupportedByDefault OBJECT-TYPE
    SYNTAX       CucsBiosSupportedAction
    MAX-ACCESS   read-only
    STATUS       current
    DESCRIPTION
        "Cisco UCS bios:VfCPUHardwarePowerManagement:supportedByDefault
        managed object property"
    ::= { cucsBiosVfCPUHardwarePowerManagementEntry 4 }

cucsBiosVfCPUHardwarePowerManagementVpCPUHardwarePowerManagement OBJECT-TYPE
    SYNTAX       CucsBiosVfCPUHardwarePowerManagementVpCPUHardwarePowerManagement
    MAX-ACCESS   read-only
    STATUS       current
    DESCRIPTION
        "Cisco UCS bios:VfCPUHardwarePowerManagement:vpCPUHardwarePowerMan
        agement managed object property"
    ::= { cucsBiosVfCPUHardwarePowerManagementEntry 5 }

cucsBiosVfCPUHardwarePowerManagementPropAcl OBJECT-TYPE
    SYNTAX       Unsigned64
    MAX-ACCESS   read-only
    STATUS       current
    DESCRIPTION
        "Cisco UCS bios:VfCPUHardwarePowerManagement:propAcl
        managed object property"
    ::= { cucsBiosVfCPUHardwarePowerManagementEntry 6 }

cucsBiosVfCPUPerformanceTable OBJECT-TYPE
    SYNTAX           SEQUENCE OF CucsBiosVfCPUPerformanceEntry
    MAX-ACCESS       not-accessible
    STATUS           current
    DESCRIPTION
        "Cisco UCS bios:VfCPUPerformance managed object table"
    ::= { cucsBiosObjects 30 }

cucsBiosVfCPUPerformanceEntry OBJECT-TYPE
    SYNTAX           CucsBiosVfCPUPerformanceEntry
    MAX-ACCESS       not-accessible
    STATUS           current
    DESCRIPTION
        "Entry for the cucsBiosVfCPUPerformanceTable table."
    INDEX { cucsBiosVfCPUPerformanceInstanceId }
    ::= { cucsBiosVfCPUPerformanceTable 1 }

CucsBiosVfCPUPerformanceEntry ::= SEQUENCE {
    cucsBiosVfCPUPerformanceInstanceId                               CucsManagedObjectId,
    cucsBiosVfCPUPerformanceDn                                       CucsManagedObjectDn,
    cucsBiosVfCPUPerformanceRn                                       SnmpAdminString,
    cucsBiosVfCPUPerformanceVpCPUPerformance                         CucsBiosVfCPUPerformanceVpCPUPerformance,
    cucsBiosVfCPUPerformancePropAcl                                  Unsigned64,
    cucsBiosVfCPUPerformanceSupportedByDefault                       CucsBiosSupportedAction
}

cucsBiosVfCPUPerformanceInstanceId OBJECT-TYPE
    SYNTAX       CucsManagedObjectId
    MAX-ACCESS   not-accessible
    STATUS       current
    DESCRIPTION
        "Instance identifier of the managed object."
    ::= { cucsBiosVfCPUPerformanceEntry 1 }

cucsBiosVfCPUPerformanceDn OBJECT-TYPE
    SYNTAX       CucsManagedObjectDn
    MAX-ACCESS   read-only
    STATUS       current
    DESCRIPTION
        "Cisco UCS bios:VfCPUPerformance:dn managed object property"
    ::= { cucsBiosVfCPUPerformanceEntry 2 }

cucsBiosVfCPUPerformanceRn OBJECT-TYPE
    SYNTAX       SnmpAdminString
    MAX-ACCESS   read-only
    STATUS       current
    DESCRIPTION
        "Cisco UCS bios:VfCPUPerformance:rn managed object property"
    ::= { cucsBiosVfCPUPerformanceEntry 3 }

cucsBiosVfCPUPerformanceVpCPUPerformance OBJECT-TYPE
    SYNTAX       CucsBiosVfCPUPerformanceVpCPUPerformance
    MAX-ACCESS   read-only
    STATUS       current
    DESCRIPTION
        "Cisco UCS bios:VfCPUPerformance:vpCPUPerformance
        managed object property"
    ::= { cucsBiosVfCPUPerformanceEntry 4 }

cucsBiosVfCPUPerformancePropAcl OBJECT-TYPE
    SYNTAX       Unsigned64
    MAX-ACCESS   read-only
    STATUS       current
    DESCRIPTION
        "Cisco UCS bios:VfCPUPerformance:propAcl managed object property"
    ::= { cucsBiosVfCPUPerformanceEntry 5 }

cucsBiosVfCPUPerformanceSupportedByDefault OBJECT-TYPE
    SYNTAX       CucsBiosSupportedAction
    MAX-ACCESS   read-only
    STATUS       current
    DESCRIPTION
        "Cisco UCS bios:VfCPUPerformance:supportedByDefault
        managed object property"
    ::= { cucsBiosVfCPUPerformanceEntry 6 }

cucsBiosVfConsistentDeviceNameControlTable OBJECT-TYPE
    SYNTAX           SEQUENCE OF CucsBiosVfConsistentDeviceNameControlEntry
    MAX-ACCESS       not-accessible
    STATUS           current
    DESCRIPTION
        "Cisco UCS bios:VfConsistentDeviceNameControl managed
        object table"
    ::= { cucsBiosObjects 87 }

cucsBiosVfConsistentDeviceNameControlEntry OBJECT-TYPE
    SYNTAX           CucsBiosVfConsistentDeviceNameControlEntry
    MAX-ACCESS       not-accessible
    STATUS           current
    DESCRIPTION
        "Entry for the cucsBiosVfConsistentDeviceNameControlTable table."
    INDEX { cucsBiosVfConsistentDeviceNameControlInstanceId }
    ::= { cucsBiosVfConsistentDeviceNameControlTable 1 }

CucsBiosVfConsistentDeviceNameControlEntry ::= SEQUENCE {
    cucsBiosVfConsistentDeviceNameControlInstanceId                  CucsManagedObjectId,
    cucsBiosVfConsistentDeviceNameControlDn                          CucsManagedObjectDn,
    cucsBiosVfConsistentDeviceNameControlRn                          SnmpAdminString,
    cucsBiosVfConsistentDeviceNameControlVpCDNControl                CucsBiosVfConsistentDeviceNameControlVpCDNControl,
    cucsBiosVfConsistentDeviceNameControlSupportedByDefault          CucsBiosSupportedAction,
    cucsBiosVfConsistentDeviceNameControlPropAcl                     Unsigned64
}

cucsBiosVfConsistentDeviceNameControlInstanceId OBJECT-TYPE
    SYNTAX       CucsManagedObjectId
    MAX-ACCESS   not-accessible
    STATUS       current
    DESCRIPTION
        "Instance identifier of the managed object."
    ::= { cucsBiosVfConsistentDeviceNameControlEntry 1 }

cucsBiosVfConsistentDeviceNameControlDn OBJECT-TYPE
    SYNTAX       CucsManagedObjectDn
    MAX-ACCESS   read-only
    STATUS       current
    DESCRIPTION
        "Cisco UCS bios:VfConsistentDeviceNameControl:dn
        managed object property"
    ::= { cucsBiosVfConsistentDeviceNameControlEntry 2 }

cucsBiosVfConsistentDeviceNameControlRn OBJECT-TYPE
    SYNTAX       SnmpAdminString
    MAX-ACCESS   read-only
    STATUS       current
    DESCRIPTION
        "Cisco UCS bios:VfConsistentDeviceNameControl:rn
        managed object property"
    ::= { cucsBiosVfConsistentDeviceNameControlEntry 3 }

cucsBiosVfConsistentDeviceNameControlVpCDNControl OBJECT-TYPE
    SYNTAX       CucsBiosVfConsistentDeviceNameControlVpCDNControl
    MAX-ACCESS   read-only
    STATUS       current
    DESCRIPTION
        "Cisco UCS bios:VfConsistentDeviceNameControl:vpCDNControl
        managed object property"
    ::= { cucsBiosVfConsistentDeviceNameControlEntry 4 }

cucsBiosVfConsistentDeviceNameControlSupportedByDefault OBJECT-TYPE
    SYNTAX       CucsBiosSupportedAction
    MAX-ACCESS   read-only
    STATUS       current
    DESCRIPTION
        "Cisco UCS bios:VfConsistentDeviceNameControl:supportedByDefault
        managed object property"
    ::= { cucsBiosVfConsistentDeviceNameControlEntry 5 }

cucsBiosVfConsistentDeviceNameControlPropAcl OBJECT-TYPE
    SYNTAX       Unsigned64
    MAX-ACCESS   read-only
    STATUS       current
    DESCRIPTION
        "Cisco UCS bios:VfConsistentDeviceNameControl:propAcl
        managed object property"
    ::= { cucsBiosVfConsistentDeviceNameControlEntry 6 }

cucsBiosVfConsoleRedirectionTable OBJECT-TYPE
    SYNTAX           SEQUENCE OF CucsBiosVfConsoleRedirectionEntry
    MAX-ACCESS       not-accessible
    STATUS           current
    DESCRIPTION
        "Cisco UCS bios:VfConsoleRedirection managed object table"
    ::= { cucsBiosObjects 11 }

cucsBiosVfConsoleRedirectionEntry OBJECT-TYPE
    SYNTAX           CucsBiosVfConsoleRedirectionEntry
    MAX-ACCESS       not-accessible
    STATUS           current
    DESCRIPTION
        "Entry for the cucsBiosVfConsoleRedirectionTable table."
    INDEX { cucsBiosVfConsoleRedirectionInstanceId }
    ::= { cucsBiosVfConsoleRedirectionTable 1 }

CucsBiosVfConsoleRedirectionEntry ::= SEQUENCE {
    cucsBiosVfConsoleRedirectionInstanceId                           CucsManagedObjectId,
    cucsBiosVfConsoleRedirectionDn                                   CucsManagedObjectDn,
    cucsBiosVfConsoleRedirectionRn                                   SnmpAdminString,
    cucsBiosVfConsoleRedirectionVpBaudRate                           CucsBiosVfConsoleRedirectionVpBaudRate,
    cucsBiosVfConsoleRedirectionVpConsoleRedirection                 CucsBiosVfConsoleRedirectionVpConsoleRedirection,
    cucsBiosVfConsoleRedirectionVpFlowControl                        CucsBiosVfConsoleRedirectionVpFlowControl,
    cucsBiosVfConsoleRedirectionVpLegacyOSRedirection                CucsBiosVfConsoleRedirectionVpLegacyOSRedirection,
    cucsBiosVfConsoleRedirectionVpTerminalType                       CucsBiosVfConsoleRedirectionVpTerminalType,
    cucsBiosVfConsoleRedirectionVpPuttyKeyPad                        CucsBiosVfConsoleRedirectionVpPuttyKeyPad,
    cucsBiosVfConsoleRedirectionPropAcl                              Unsigned64,
    cucsBiosVfConsoleRedirectionSupportedByDefault                   CucsBiosSupportedAction
}

cucsBiosVfConsoleRedirectionInstanceId OBJECT-TYPE
    SYNTAX       CucsManagedObjectId
    MAX-ACCESS   not-accessible
    STATUS       current
    DESCRIPTION
        "Instance identifier of the managed object."
    ::= { cucsBiosVfConsoleRedirectionEntry 1 }

cucsBiosVfConsoleRedirectionDn OBJECT-TYPE
    SYNTAX       CucsManagedObjectDn
    MAX-ACCESS   read-only
    STATUS       current
    DESCRIPTION
        "Cisco UCS bios:VfConsoleRedirection:dn managed object property"
    ::= { cucsBiosVfConsoleRedirectionEntry 2 }

cucsBiosVfConsoleRedirectionRn OBJECT-TYPE
    SYNTAX       SnmpAdminString
    MAX-ACCESS   read-only
    STATUS       current
    DESCRIPTION
        "Cisco UCS bios:VfConsoleRedirection:rn managed object property"
    ::= { cucsBiosVfConsoleRedirectionEntry 3 }

cucsBiosVfConsoleRedirectionVpBaudRate OBJECT-TYPE
    SYNTAX       CucsBiosVfConsoleRedirectionVpBaudRate
    MAX-ACCESS   read-only
    STATUS       current
    DESCRIPTION
        "Cisco UCS bios:VfConsoleRedirection:vpBaudRate
        managed object property"
    ::= { cucsBiosVfConsoleRedirectionEntry 4 }

cucsBiosVfConsoleRedirectionVpConsoleRedirection OBJECT-TYPE
    SYNTAX       CucsBiosVfConsoleRedirectionVpConsoleRedirection
    MAX-ACCESS   read-only
    STATUS       current
    DESCRIPTION
        "Cisco UCS bios:VfConsoleRedirection:vpConsoleRedirection
        managed object property"
    ::= { cucsBiosVfConsoleRedirectionEntry 5 }

cucsBiosVfConsoleRedirectionVpFlowControl OBJECT-TYPE
    SYNTAX       CucsBiosVfConsoleRedirectionVpFlowControl
    MAX-ACCESS   read-only
    STATUS       current
    DESCRIPTION
        "Cisco UCS bios:VfConsoleRedirection:vpFlowControl
        managed object property"
    ::= { cucsBiosVfConsoleRedirectionEntry 6 }

cucsBiosVfConsoleRedirectionVpLegacyOSRedirection OBJECT-TYPE
    SYNTAX       CucsBiosVfConsoleRedirectionVpLegacyOSRedirection
    MAX-ACCESS   read-only
    STATUS       current
    DESCRIPTION
        "Cisco UCS bios:VfConsoleRedirection:vpLegacyOSRedirection
        managed object property"
    ::= { cucsBiosVfConsoleRedirectionEntry 7 }

cucsBiosVfConsoleRedirectionVpTerminalType OBJECT-TYPE
    SYNTAX       CucsBiosVfConsoleRedirectionVpTerminalType
    MAX-ACCESS   read-only
    STATUS       current
    DESCRIPTION
        "Cisco UCS bios:VfConsoleRedirection:vpTerminalType
        managed object property"
    ::= { cucsBiosVfConsoleRedirectionEntry 8 }

cucsBiosVfConsoleRedirectionVpPuttyKeyPad OBJECT-TYPE
    SYNTAX       CucsBiosVfConsoleRedirectionVpPuttyKeyPad
    MAX-ACCESS   read-only
    STATUS       current
    DESCRIPTION
        "Cisco UCS bios:VfConsoleRedirection:vpPuttyKeyPad
        managed object property"
    ::= { cucsBiosVfConsoleRedirectionEntry 9 }

cucsBiosVfConsoleRedirectionPropAcl OBJECT-TYPE
    SYNTAX       Unsigned64
    MAX-ACCESS   read-only
    STATUS       current
    DESCRIPTION
        "Cisco UCS bios:VfConsoleRedirection:propAcl managed
        object property"
    ::= { cucsBiosVfConsoleRedirectionEntry 10 }

cucsBiosVfConsoleRedirectionSupportedByDefault OBJECT-TYPE
    SYNTAX       CucsBiosSupportedAction
    MAX-ACCESS   read-only
    STATUS       current
    DESCRIPTION
        "Cisco UCS bios:VfConsoleRedirection:supportedByDefault
        managed object property"
    ::= { cucsBiosVfConsoleRedirectionEntry 11 }

cucsBiosVfCoreMultiProcessingTable OBJECT-TYPE
    SYNTAX           SEQUENCE OF CucsBiosVfCoreMultiProcessingEntry
    MAX-ACCESS       not-accessible
    STATUS           current
    DESCRIPTION
        "Cisco UCS bios:VfCoreMultiProcessing managed object table"
    ::= { cucsBiosObjects 33 }

cucsBiosVfCoreMultiProcessingEntry OBJECT-TYPE
    SYNTAX           CucsBiosVfCoreMultiProcessingEntry
    MAX-ACCESS       not-accessible
    STATUS           current
    DESCRIPTION
        "Entry for the cucsBiosVfCoreMultiProcessingTable table."
    INDEX { cucsBiosVfCoreMultiProcessingInstanceId }
    ::= { cucsBiosVfCoreMultiProcessingTable 1 }

CucsBiosVfCoreMultiProcessingEntry ::= SEQUENCE {
    cucsBiosVfCoreMultiProcessingInstanceId                          CucsManagedObjectId,
    cucsBiosVfCoreMultiProcessingDn                                  CucsManagedObjectDn,
    cucsBiosVfCoreMultiProcessingRn                                  SnmpAdminString,
    cucsBiosVfCoreMultiProcessingVpCoreMultiProcessing               CucsBiosVfCoreMultiProcessingVpCoreMultiProcessing,
    cucsBiosVfCoreMultiProcessingPropAcl                             Unsigned64,
    cucsBiosVfCoreMultiProcessingSupportedByDefault                  CucsBiosSupportedAction
}

cucsBiosVfCoreMultiProcessingInstanceId OBJECT-TYPE
    SYNTAX       CucsManagedObjectId
    MAX-ACCESS   not-accessible
    STATUS       current
    DESCRIPTION
        "Instance identifier of the managed object."
    ::= { cucsBiosVfCoreMultiProcessingEntry 1 }

cucsBiosVfCoreMultiProcessingDn OBJECT-TYPE
    SYNTAX       CucsManagedObjectDn
    MAX-ACCESS   read-only
    STATUS       current
    DESCRIPTION
        "Cisco UCS bios:VfCoreMultiProcessing:dn managed object property"
    ::= { cucsBiosVfCoreMultiProcessingEntry 2 }

cucsBiosVfCoreMultiProcessingRn OBJECT-TYPE
    SYNTAX       SnmpAdminString
    MAX-ACCESS   read-only
    STATUS       current
    DESCRIPTION
        "Cisco UCS bios:VfCoreMultiProcessing:rn managed object property"
    ::= { cucsBiosVfCoreMultiProcessingEntry 3 }

cucsBiosVfCoreMultiProcessingVpCoreMultiProcessing OBJECT-TYPE
    SYNTAX       CucsBiosVfCoreMultiProcessingVpCoreMultiProcessing
    MAX-ACCESS   read-only
    STATUS       current
    DESCRIPTION
        "Cisco UCS bios:VfCoreMultiProcessing:vpCoreMultiProcessing
        managed object property"
    ::= { cucsBiosVfCoreMultiProcessingEntry 4 }

cucsBiosVfCoreMultiProcessingPropAcl OBJECT-TYPE
    SYNTAX       Unsigned64
    MAX-ACCESS   read-only
    STATUS       current
    DESCRIPTION
        "Cisco UCS bios:VfCoreMultiProcessing:propAcl managed
        object property"
    ::= { cucsBiosVfCoreMultiProcessingEntry 5 }

cucsBiosVfCoreMultiProcessingSupportedByDefault OBJECT-TYPE
    SYNTAX       CucsBiosSupportedAction
    MAX-ACCESS   read-only
    STATUS       current
    DESCRIPTION
        "Cisco UCS bios:VfCoreMultiProcessing:supportedByDefault
        managed object property"
    ::= { cucsBiosVfCoreMultiProcessingEntry 6 }

cucsBiosVfDDR3VoltageSelectionTable OBJECT-TYPE
    SYNTAX           SEQUENCE OF CucsBiosVfDDR3VoltageSelectionEntry
    MAX-ACCESS       not-accessible
    STATUS           current
    DESCRIPTION
        "Cisco UCS bios:VfDDR3VoltageSelection managed object table"
    ::= { cucsBiosObjects 86 }

cucsBiosVfDDR3VoltageSelectionEntry OBJECT-TYPE
    SYNTAX           CucsBiosVfDDR3VoltageSelectionEntry
    MAX-ACCESS       not-accessible
    STATUS           current
    DESCRIPTION
        "Entry for the cucsBiosVfDDR3VoltageSelectionTable table."
    INDEX { cucsBiosVfDDR3VoltageSelectionInstanceId }
    ::= { cucsBiosVfDDR3VoltageSelectionTable 1 }

CucsBiosVfDDR3VoltageSelectionEntry ::= SEQUENCE {
    cucsBiosVfDDR3VoltageSelectionInstanceId                         CucsManagedObjectId,
    cucsBiosVfDDR3VoltageSelectionDn                                 CucsManagedObjectDn,
    cucsBiosVfDDR3VoltageSelectionRn                                 SnmpAdminString,
    cucsBiosVfDDR3VoltageSelectionVpDDR3VoltageSelection             CucsBiosVfDDR3VoltageSelectionVpDDR3VoltageSelection,
    cucsBiosVfDDR3VoltageSelectionSupportedByDefault                 CucsBiosSupportedAction,
    cucsBiosVfDDR3VoltageSelectionPropAcl                            Unsigned64
}

cucsBiosVfDDR3VoltageSelectionInstanceId OBJECT-TYPE
    SYNTAX       CucsManagedObjectId
    MAX-ACCESS   not-accessible
    STATUS       current
    DESCRIPTION
        "Instance identifier of the managed object."
    ::= { cucsBiosVfDDR3VoltageSelectionEntry 1 }

cucsBiosVfDDR3VoltageSelectionDn OBJECT-TYPE
    SYNTAX       CucsManagedObjectDn
    MAX-ACCESS   read-only
    STATUS       current
    DESCRIPTION
        "Cisco UCS bios:VfDDR3VoltageSelection:dn managed object property"
    ::= { cucsBiosVfDDR3VoltageSelectionEntry 2 }

cucsBiosVfDDR3VoltageSelectionRn OBJECT-TYPE
    SYNTAX       SnmpAdminString
    MAX-ACCESS   read-only
    STATUS       current
    DESCRIPTION
        "Cisco UCS bios:VfDDR3VoltageSelection:rn managed object property"
    ::= { cucsBiosVfDDR3VoltageSelectionEntry 3 }

cucsBiosVfDDR3VoltageSelectionVpDDR3VoltageSelection OBJECT-TYPE
    SYNTAX       CucsBiosVfDDR3VoltageSelectionVpDDR3VoltageSelection
    MAX-ACCESS   read-only
    STATUS       current
    DESCRIPTION
        "Cisco UCS bios:VfDDR3VoltageSelection:vpDDR3VoltageSelection
        managed object property"
    ::= { cucsBiosVfDDR3VoltageSelectionEntry 4 }

cucsBiosVfDDR3VoltageSelectionSupportedByDefault OBJECT-TYPE
    SYNTAX       CucsBiosSupportedAction
    MAX-ACCESS   read-only
    STATUS       current
    DESCRIPTION
        "Cisco UCS bios:VfDDR3VoltageSelection:supportedByDefault
        managed object property"
    ::= { cucsBiosVfDDR3VoltageSelectionEntry 5 }

cucsBiosVfDDR3VoltageSelectionPropAcl OBJECT-TYPE
    SYNTAX       Unsigned64
    MAX-ACCESS   read-only
    STATUS       current
    DESCRIPTION
        "Cisco UCS bios:VfDDR3VoltageSelection:propAcl
        managed object property"
    ::= { cucsBiosVfDDR3VoltageSelectionEntry 6 }

cucsBiosVfDRAMClockThrottlingTable OBJECT-TYPE
    SYNTAX           SEQUENCE OF CucsBiosVfDRAMClockThrottlingEntry
    MAX-ACCESS       not-accessible
    STATUS           current
    DESCRIPTION
        "Cisco UCS bios:VfDRAMClockThrottling managed object table"
    ::= { cucsBiosObjects 65 }

cucsBiosVfDRAMClockThrottlingEntry OBJECT-TYPE
    SYNTAX           CucsBiosVfDRAMClockThrottlingEntry
    MAX-ACCESS       not-accessible
    STATUS           current
    DESCRIPTION
        "Entry for the cucsBiosVfDRAMClockThrottlingTable table."
    INDEX { cucsBiosVfDRAMClockThrottlingInstanceId }
    ::= { cucsBiosVfDRAMClockThrottlingTable 1 }

CucsBiosVfDRAMClockThrottlingEntry ::= SEQUENCE {
    cucsBiosVfDRAMClockThrottlingInstanceId                          CucsManagedObjectId,
    cucsBiosVfDRAMClockThrottlingDn                                  CucsManagedObjectDn,
    cucsBiosVfDRAMClockThrottlingRn                                  SnmpAdminString,
    cucsBiosVfDRAMClockThrottlingVpDRAMClockThrottling               CucsBiosVfDRAMClockThrottlingVpDRAMClockThrottling,
    cucsBiosVfDRAMClockThrottlingPropAcl                             Unsigned64,
    cucsBiosVfDRAMClockThrottlingSupportedByDefault                  CucsBiosSupportedAction
}

cucsBiosVfDRAMClockThrottlingInstanceId OBJECT-TYPE
    SYNTAX       CucsManagedObjectId
    MAX-ACCESS   not-accessible
    STATUS       current
    DESCRIPTION
        "Instance identifier of the managed object."
    ::= { cucsBiosVfDRAMClockThrottlingEntry 1 }

cucsBiosVfDRAMClockThrottlingDn OBJECT-TYPE
    SYNTAX       CucsManagedObjectDn
    MAX-ACCESS   read-only
    STATUS       current
    DESCRIPTION
        "Cisco UCS bios:VfDRAMClockThrottling:dn managed object property"
    ::= { cucsBiosVfDRAMClockThrottlingEntry 2 }

cucsBiosVfDRAMClockThrottlingRn OBJECT-TYPE
    SYNTAX       SnmpAdminString
    MAX-ACCESS   read-only
    STATUS       current
    DESCRIPTION
        "Cisco UCS bios:VfDRAMClockThrottling:rn managed object property"
    ::= { cucsBiosVfDRAMClockThrottlingEntry 3 }

cucsBiosVfDRAMClockThrottlingVpDRAMClockThrottling OBJECT-TYPE
    SYNTAX       CucsBiosVfDRAMClockThrottlingVpDRAMClockThrottling
    MAX-ACCESS   read-only
    STATUS       current
    DESCRIPTION
        "Cisco UCS bios:VfDRAMClockThrottling:vpDRAMClockThrottling
        managed object property"
    ::= { cucsBiosVfDRAMClockThrottlingEntry 4 }

cucsBiosVfDRAMClockThrottlingPropAcl OBJECT-TYPE
    SYNTAX       Unsigned64
    MAX-ACCESS   read-only
    STATUS       current
    DESCRIPTION
        "Cisco UCS bios:VfDRAMClockThrottling:propAcl managed
        object property"
    ::= { cucsBiosVfDRAMClockThrottlingEntry 5 }

cucsBiosVfDRAMClockThrottlingSupportedByDefault OBJECT-TYPE
    SYNTAX       CucsBiosSupportedAction
    MAX-ACCESS   read-only
    STATUS       current
    DESCRIPTION
        "Cisco UCS bios:VfDRAMClockThrottling:supportedByDefault
        managed object property"
    ::= { cucsBiosVfDRAMClockThrottlingEntry 6 }

cucsBiosVfDirectCacheAccessTable OBJECT-TYPE
    SYNTAX           SEQUENCE OF CucsBiosVfDirectCacheAccessEntry
    MAX-ACCESS       not-accessible
    STATUS           current
    DESCRIPTION
        "Cisco UCS bios:VfDirectCacheAccess managed object table"
    ::= { cucsBiosObjects 35 }

cucsBiosVfDirectCacheAccessEntry OBJECT-TYPE
    SYNTAX           CucsBiosVfDirectCacheAccessEntry
    MAX-ACCESS       not-accessible
    STATUS           current
    DESCRIPTION
        "Entry for the cucsBiosVfDirectCacheAccessTable table."
    INDEX { cucsBiosVfDirectCacheAccessInstanceId }
    ::= { cucsBiosVfDirectCacheAccessTable 1 }

CucsBiosVfDirectCacheAccessEntry ::= SEQUENCE {
    cucsBiosVfDirectCacheAccessInstanceId                            CucsManagedObjectId,
    cucsBiosVfDirectCacheAccessDn                                    CucsManagedObjectDn,
    cucsBiosVfDirectCacheAccessRn                                    SnmpAdminString,
    cucsBiosVfDirectCacheAccessVpDirectCacheAccess                   CucsBiosVfDirectCacheAccessVpDirectCacheAccess,
    cucsBiosVfDirectCacheAccessPropAcl                               Unsigned64,
    cucsBiosVfDirectCacheAccessSupportedByDefault                    CucsBiosSupportedAction
}

cucsBiosVfDirectCacheAccessInstanceId OBJECT-TYPE
    SYNTAX       CucsManagedObjectId
    MAX-ACCESS   not-accessible
    STATUS       current
    DESCRIPTION
        "Instance identifier of the managed object."
    ::= { cucsBiosVfDirectCacheAccessEntry 1 }

cucsBiosVfDirectCacheAccessDn OBJECT-TYPE
    SYNTAX       CucsManagedObjectDn
    MAX-ACCESS   read-only
    STATUS       current
    DESCRIPTION
        "Cisco UCS bios:VfDirectCacheAccess:dn managed object property"
    ::= { cucsBiosVfDirectCacheAccessEntry 2 }

cucsBiosVfDirectCacheAccessRn OBJECT-TYPE
    SYNTAX       SnmpAdminString
    MAX-ACCESS   read-only
    STATUS       current
    DESCRIPTION
        "Cisco UCS bios:VfDirectCacheAccess:rn managed object property"
    ::= { cucsBiosVfDirectCacheAccessEntry 3 }

cucsBiosVfDirectCacheAccessVpDirectCacheAccess OBJECT-TYPE
    SYNTAX       CucsBiosVfDirectCacheAccessVpDirectCacheAccess
    MAX-ACCESS   read-only
    STATUS       current
    DESCRIPTION
        "Cisco UCS bios:VfDirectCacheAccess:vpDirectCacheAccess
        managed object property"
    ::= { cucsBiosVfDirectCacheAccessEntry 4 }

cucsBiosVfDirectCacheAccessPropAcl OBJECT-TYPE
    SYNTAX       Unsigned64
    MAX-ACCESS   read-only
    STATUS       current
    DESCRIPTION
        "Cisco UCS bios:VfDirectCacheAccess:propAcl managed
        object property"
    ::= { cucsBiosVfDirectCacheAccessEntry 5 }

cucsBiosVfDirectCacheAccessSupportedByDefault OBJECT-TYPE
    SYNTAX       CucsBiosSupportedAction
    MAX-ACCESS   read-only
    STATUS       current
    DESCRIPTION
        "Cisco UCS bios:VfDirectCacheAccess:supportedByDefault
        managed object property"
    ::= { cucsBiosVfDirectCacheAccessEntry 6 }

cucsBiosVfDramRefreshRateTable OBJECT-TYPE
    SYNTAX           SEQUENCE OF CucsBiosVfDramRefreshRateEntry
    MAX-ACCESS       not-accessible
    STATUS           current
    DESCRIPTION
        "Cisco UCS bios:VfDramRefreshRate managed object table"
    ::= { cucsBiosObjects 61 }

cucsBiosVfDramRefreshRateEntry OBJECT-TYPE
    SYNTAX           CucsBiosVfDramRefreshRateEntry
    MAX-ACCESS       not-accessible
    STATUS           current
    DESCRIPTION
        "Entry for the cucsBiosVfDramRefreshRateTable table."
    INDEX { cucsBiosVfDramRefreshRateInstanceId }
    ::= { cucsBiosVfDramRefreshRateTable 1 }

CucsBiosVfDramRefreshRateEntry ::= SEQUENCE {
    cucsBiosVfDramRefreshRateInstanceId                              CucsManagedObjectId,
    cucsBiosVfDramRefreshRateDn                                      CucsManagedObjectDn,
    cucsBiosVfDramRefreshRateRn                                      SnmpAdminString,
    cucsBiosVfDramRefreshRateVpDramRefreshRate                       CucsBiosVfDramRefreshRateVpDramRefreshRate,
    cucsBiosVfDramRefreshRatePropAcl                                 Unsigned64,
    cucsBiosVfDramRefreshRateSupportedByDefault                      CucsBiosSupportedAction
}

cucsBiosVfDramRefreshRateInstanceId OBJECT-TYPE
    SYNTAX       CucsManagedObjectId
    MAX-ACCESS   not-accessible
    STATUS       current
    DESCRIPTION
        "Instance identifier of the managed object."
    ::= { cucsBiosVfDramRefreshRateEntry 1 }

cucsBiosVfDramRefreshRateDn OBJECT-TYPE
    SYNTAX       CucsManagedObjectDn
    MAX-ACCESS   read-only
    STATUS       current
    DESCRIPTION
        "Cisco UCS bios:VfDramRefreshRate:dn managed object property"
    ::= { cucsBiosVfDramRefreshRateEntry 2 }

cucsBiosVfDramRefreshRateRn OBJECT-TYPE
    SYNTAX       SnmpAdminString
    MAX-ACCESS   read-only
    STATUS       current
    DESCRIPTION
        "Cisco UCS bios:VfDramRefreshRate:rn managed object property"
    ::= { cucsBiosVfDramRefreshRateEntry 3 }

cucsBiosVfDramRefreshRateVpDramRefreshRate OBJECT-TYPE
    SYNTAX       CucsBiosVfDramRefreshRateVpDramRefreshRate
    MAX-ACCESS   read-only
    STATUS       current
    DESCRIPTION
        "Cisco UCS bios:VfDramRefreshRate:vpDramRefreshRate
        managed object property"
    ::= { cucsBiosVfDramRefreshRateEntry 4 }

cucsBiosVfDramRefreshRatePropAcl OBJECT-TYPE
    SYNTAX       Unsigned64
    MAX-ACCESS   read-only
    STATUS       current
    DESCRIPTION
        "Cisco UCS bios:VfDramRefreshRate:propAcl managed object property"
    ::= { cucsBiosVfDramRefreshRateEntry 5 }

cucsBiosVfDramRefreshRateSupportedByDefault OBJECT-TYPE
    SYNTAX       CucsBiosSupportedAction
    MAX-ACCESS   read-only
    STATUS       current
    DESCRIPTION
        "Cisco UCS bios:VfDramRefreshRate:supportedByDefault
        managed object property"
    ::= { cucsBiosVfDramRefreshRateEntry 6 }

cucsBiosVfEnergyPerformanceTuningTable OBJECT-TYPE
    SYNTAX           SEQUENCE OF CucsBiosVfEnergyPerformanceTuningEntry
    MAX-ACCESS       not-accessible
    STATUS           current
    DESCRIPTION
        "Cisco UCS bios:VfEnergyPerformanceTuning managed object table"
    ::= { cucsBiosObjects 97 }

cucsBiosVfEnergyPerformanceTuningEntry OBJECT-TYPE
    SYNTAX           CucsBiosVfEnergyPerformanceTuningEntry
    MAX-ACCESS       not-accessible
    STATUS           current
    DESCRIPTION
        "Entry for the cucsBiosVfEnergyPerformanceTuningTable table."
    INDEX { cucsBiosVfEnergyPerformanceTuningInstanceId }
    ::= { cucsBiosVfEnergyPerformanceTuningTable 1 }

CucsBiosVfEnergyPerformanceTuningEntry ::= SEQUENCE {
    cucsBiosVfEnergyPerformanceTuningInstanceId                      CucsManagedObjectId,
    cucsBiosVfEnergyPerformanceTuningDn                              CucsManagedObjectDn,
    cucsBiosVfEnergyPerformanceTuningRn                              SnmpAdminString,
    cucsBiosVfEnergyPerformanceTuningPropAcl                         Unsigned64,
    cucsBiosVfEnergyPerformanceTuningSupportedByDefault              CucsBiosSupportedAction,
    cucsBiosVfEnergyPerformanceTuningVpPwrPerfTuning                 CucsBiosVfEnergyPerformanceTuningVpPwrPerfTuning
}

cucsBiosVfEnergyPerformanceTuningInstanceId OBJECT-TYPE
    SYNTAX       CucsManagedObjectId
    MAX-ACCESS   not-accessible
    STATUS       current
    DESCRIPTION
        "Instance identifier of the managed object."
    ::= { cucsBiosVfEnergyPerformanceTuningEntry 1 }

cucsBiosVfEnergyPerformanceTuningDn OBJECT-TYPE
    SYNTAX       CucsManagedObjectDn
    MAX-ACCESS   read-only
    STATUS       current
    DESCRIPTION
        "Cisco UCS bios:VfEnergyPerformanceTuning:dn managed
        object property"
    ::= { cucsBiosVfEnergyPerformanceTuningEntry 2 }

cucsBiosVfEnergyPerformanceTuningRn OBJECT-TYPE
    SYNTAX       SnmpAdminString
    MAX-ACCESS   read-only
    STATUS       current
    DESCRIPTION
        "Cisco UCS bios:VfEnergyPerformanceTuning:rn managed
        object property"
    ::= { cucsBiosVfEnergyPerformanceTuningEntry 3 }

cucsBiosVfEnergyPerformanceTuningPropAcl OBJECT-TYPE
    SYNTAX       Unsigned64
    MAX-ACCESS   read-only
    STATUS       current
    DESCRIPTION
        "Cisco UCS bios:VfEnergyPerformanceTuning:propAcl
        managed object property"
    ::= { cucsBiosVfEnergyPerformanceTuningEntry 4 }

cucsBiosVfEnergyPerformanceTuningSupportedByDefault OBJECT-TYPE
    SYNTAX       CucsBiosSupportedAction
    MAX-ACCESS   read-only
    STATUS       current
    DESCRIPTION
        "Cisco UCS bios:VfEnergyPerformanceTuning:supportedByDefault
        managed object property"
    ::= { cucsBiosVfEnergyPerformanceTuningEntry 5 }

cucsBiosVfEnergyPerformanceTuningVpPwrPerfTuning OBJECT-TYPE
    SYNTAX       CucsBiosVfEnergyPerformanceTuningVpPwrPerfTuning
    MAX-ACCESS   read-only
    STATUS       current
    DESCRIPTION
        "Cisco UCS bios:VfEnergyPerformanceTuning:vpPwrPerfTuning
        managed object property"
    ::= { cucsBiosVfEnergyPerformanceTuningEntry 6 }

cucsBiosVfEnhancedIntelSpeedStepTechTable OBJECT-TYPE
    SYNTAX           SEQUENCE OF CucsBiosVfEnhancedIntelSpeedStepTechEntry
    MAX-ACCESS       not-accessible
    STATUS           current
    DESCRIPTION
        "Cisco UCS bios:VfEnhancedIntelSpeedStepTech managed object table"
    ::= { cucsBiosObjects 13 }

cucsBiosVfEnhancedIntelSpeedStepTechEntry OBJECT-TYPE
    SYNTAX           CucsBiosVfEnhancedIntelSpeedStepTechEntry
    MAX-ACCESS       not-accessible
    STATUS           current
    DESCRIPTION
        "Entry for the cucsBiosVfEnhancedIntelSpeedStepTechTable table."
    INDEX { cucsBiosVfEnhancedIntelSpeedStepTechInstanceId }
    ::= { cucsBiosVfEnhancedIntelSpeedStepTechTable 1 }

CucsBiosVfEnhancedIntelSpeedStepTechEntry ::= SEQUENCE {
    cucsBiosVfEnhancedIntelSpeedStepTechInstanceId                   CucsManagedObjectId,
    cucsBiosVfEnhancedIntelSpeedStepTechDn                           CucsManagedObjectDn,
    cucsBiosVfEnhancedIntelSpeedStepTechRn                           SnmpAdminString,
    cucsBiosVfEnhancedIntelSpeedStepTechVpEnhancedIntelSpeedStepTech CucsBiosVfEnhancedIntelSpeedStepTechVpEnhancedIntelSpeedStepTech,
    cucsBiosVfEnhancedIntelSpeedStepTechPropAcl                      Unsigned64,
    cucsBiosVfEnhancedIntelSpeedStepTechSupportedByDefault           CucsBiosSupportedAction
}

cucsBiosVfEnhancedIntelSpeedStepTechInstanceId OBJECT-TYPE
    SYNTAX       CucsManagedObjectId
    MAX-ACCESS   not-accessible
    STATUS       current
    DESCRIPTION
        "Instance identifier of the managed object."
    ::= { cucsBiosVfEnhancedIntelSpeedStepTechEntry 1 }

cucsBiosVfEnhancedIntelSpeedStepTechDn OBJECT-TYPE
    SYNTAX       CucsManagedObjectDn
    MAX-ACCESS   read-only
    STATUS       current
    DESCRIPTION
        "Cisco UCS bios:VfEnhancedIntelSpeedStepTech:dn
        managed object property"
    ::= { cucsBiosVfEnhancedIntelSpeedStepTechEntry 2 }

cucsBiosVfEnhancedIntelSpeedStepTechRn OBJECT-TYPE
    SYNTAX       SnmpAdminString
    MAX-ACCESS   read-only
    STATUS       current
    DESCRIPTION
        "Cisco UCS bios:VfEnhancedIntelSpeedStepTech:rn
        managed object property"
    ::= { cucsBiosVfEnhancedIntelSpeedStepTechEntry 3 }

cucsBiosVfEnhancedIntelSpeedStepTechVpEnhancedIntelSpeedStepTech OBJECT-TYPE
    SYNTAX       CucsBiosVfEnhancedIntelSpeedStepTechVpEnhancedIntelSpeedStepTech
    MAX-ACCESS   read-only
    STATUS       current
    DESCRIPTION
        "Cisco UCS bios:VfEnhancedIntelSpeedStepTech:vpEnhancedIntelSpeedS
        tepTech managed object property"
    ::= { cucsBiosVfEnhancedIntelSpeedStepTechEntry 4 }

cucsBiosVfEnhancedIntelSpeedStepTechPropAcl OBJECT-TYPE
    SYNTAX       Unsigned64
    MAX-ACCESS   read-only
    STATUS       current
    DESCRIPTION
        "Cisco UCS bios:VfEnhancedIntelSpeedStepTech:propAcl
        managed object property"
    ::= { cucsBiosVfEnhancedIntelSpeedStepTechEntry 5 }

cucsBiosVfEnhancedIntelSpeedStepTechSupportedByDefault OBJECT-TYPE
    SYNTAX       CucsBiosSupportedAction
    MAX-ACCESS   read-only
    STATUS       current
    DESCRIPTION
        "Cisco UCS bios:VfEnhancedIntelSpeedStepTech:supportedByDefault
        managed object property"
    ::= { cucsBiosVfEnhancedIntelSpeedStepTechEntry 6 }

cucsBiosVfEnhancedPowerCappingSupportTable OBJECT-TYPE
    SYNTAX           SEQUENCE OF CucsBiosVfEnhancedPowerCappingSupportEntry
    MAX-ACCESS       not-accessible
    STATUS           current
    DESCRIPTION
        "Cisco UCS bios:VfEnhancedPowerCappingSupport managed
        object table"
    ::= { cucsBiosObjects 83 }

cucsBiosVfEnhancedPowerCappingSupportEntry OBJECT-TYPE
    SYNTAX           CucsBiosVfEnhancedPowerCappingSupportEntry
    MAX-ACCESS       not-accessible
    STATUS           current
    DESCRIPTION
        "Entry for the cucsBiosVfEnhancedPowerCappingSupportTable table."
    INDEX { cucsBiosVfEnhancedPowerCappingSupportInstanceId }
    ::= { cucsBiosVfEnhancedPowerCappingSupportTable 1 }

CucsBiosVfEnhancedPowerCappingSupportEntry ::= SEQUENCE {
    cucsBiosVfEnhancedPowerCappingSupportInstanceId                  CucsManagedObjectId,
    cucsBiosVfEnhancedPowerCappingSupportDn                          CucsManagedObjectDn,
    cucsBiosVfEnhancedPowerCappingSupportRn                          SnmpAdminString,
    cucsBiosVfEnhancedPowerCappingSupportPropAcl                     Unsigned64,
    cucsBiosVfEnhancedPowerCappingSupportSupportedByDefault          CucsBiosSupportedAction,
    cucsBiosVfEnhancedPowerCappingSupportVpEnhancedPowerCapping      CucsBiosVfEnhancedPowerCappingSupportVpEnhancedPowerCapping
}

cucsBiosVfEnhancedPowerCappingSupportInstanceId OBJECT-TYPE
    SYNTAX       CucsManagedObjectId
    MAX-ACCESS   not-accessible
    STATUS       current
    DESCRIPTION
        "Instance identifier of the managed object."
    ::= { cucsBiosVfEnhancedPowerCappingSupportEntry 1 }

cucsBiosVfEnhancedPowerCappingSupportDn OBJECT-TYPE
    SYNTAX       CucsManagedObjectDn
    MAX-ACCESS   read-only
    STATUS       current
    DESCRIPTION
        "Cisco UCS bios:VfEnhancedPowerCappingSupport:dn
        managed object property"
    ::= { cucsBiosVfEnhancedPowerCappingSupportEntry 2 }

cucsBiosVfEnhancedPowerCappingSupportRn OBJECT-TYPE
    SYNTAX       SnmpAdminString
    MAX-ACCESS   read-only
    STATUS       current
    DESCRIPTION
        "Cisco UCS bios:VfEnhancedPowerCappingSupport:rn
        managed object property"
    ::= { cucsBiosVfEnhancedPowerCappingSupportEntry 3 }

cucsBiosVfEnhancedPowerCappingSupportPropAcl OBJECT-TYPE
    SYNTAX       Unsigned64
    MAX-ACCESS   read-only
    STATUS       current
    DESCRIPTION
        "Cisco UCS bios:VfEnhancedPowerCappingSupport:propAcl
        managed object property"
    ::= { cucsBiosVfEnhancedPowerCappingSupportEntry 4 }

cucsBiosVfEnhancedPowerCappingSupportSupportedByDefault OBJECT-TYPE
    SYNTAX       CucsBiosSupportedAction
    MAX-ACCESS   read-only
    STATUS       current
    DESCRIPTION
        "Cisco UCS bios:VfEnhancedPowerCappingSupport:supportedByDefault
        managed object property"
    ::= { cucsBiosVfEnhancedPowerCappingSupportEntry 5 }

cucsBiosVfEnhancedPowerCappingSupportVpEnhancedPowerCapping OBJECT-TYPE
    SYNTAX       CucsBiosVfEnhancedPowerCappingSupportVpEnhancedPowerCapping
    MAX-ACCESS   read-only
    STATUS       current
    DESCRIPTION
        "Cisco UCS bios:VfEnhancedPowerCappingSupport:vpEnhancedPowerCappi
        ng managed object property"
    ::= { cucsBiosVfEnhancedPowerCappingSupportEntry 6 }

cucsBiosVfExecuteDisableBitTable OBJECT-TYPE
    SYNTAX           SEQUENCE OF CucsBiosVfExecuteDisableBitEntry
    MAX-ACCESS       not-accessible
    STATUS           current
    DESCRIPTION
        "Cisco UCS bios:VfExecuteDisableBit managed object table"
    ::= { cucsBiosObjects 36 }

cucsBiosVfExecuteDisableBitEntry OBJECT-TYPE
    SYNTAX           CucsBiosVfExecuteDisableBitEntry
    MAX-ACCESS       not-accessible
    STATUS           current
    DESCRIPTION
        "Entry for the cucsBiosVfExecuteDisableBitTable table."
    INDEX { cucsBiosVfExecuteDisableBitInstanceId }
    ::= { cucsBiosVfExecuteDisableBitTable 1 }

CucsBiosVfExecuteDisableBitEntry ::= SEQUENCE {
    cucsBiosVfExecuteDisableBitInstanceId                            CucsManagedObjectId,
    cucsBiosVfExecuteDisableBitDn                                    CucsManagedObjectDn,
    cucsBiosVfExecuteDisableBitRn                                    SnmpAdminString,
    cucsBiosVfExecuteDisableBitVpExecuteDisableBit                   CucsBiosVfExecuteDisableBitVpExecuteDisableBit,
    cucsBiosVfExecuteDisableBitPropAcl                               Unsigned64,
    cucsBiosVfExecuteDisableBitSupportedByDefault                    CucsBiosSupportedAction
}

cucsBiosVfExecuteDisableBitInstanceId OBJECT-TYPE
    SYNTAX       CucsManagedObjectId
    MAX-ACCESS   not-accessible
    STATUS       current
    DESCRIPTION
        "Instance identifier of the managed object."
    ::= { cucsBiosVfExecuteDisableBitEntry 1 }

cucsBiosVfExecuteDisableBitDn OBJECT-TYPE
    SYNTAX       CucsManagedObjectDn
    MAX-ACCESS   read-only
    STATUS       current
    DESCRIPTION
        "Cisco UCS bios:VfExecuteDisableBit:dn managed object property"
    ::= { cucsBiosVfExecuteDisableBitEntry 2 }

cucsBiosVfExecuteDisableBitRn OBJECT-TYPE
    SYNTAX       SnmpAdminString
    MAX-ACCESS   read-only
    STATUS       current
    DESCRIPTION
        "Cisco UCS bios:VfExecuteDisableBit:rn managed object property"
    ::= { cucsBiosVfExecuteDisableBitEntry 3 }

cucsBiosVfExecuteDisableBitVpExecuteDisableBit OBJECT-TYPE
    SYNTAX       CucsBiosVfExecuteDisableBitVpExecuteDisableBit
    MAX-ACCESS   read-only
    STATUS       current
    DESCRIPTION
        "Cisco UCS bios:VfExecuteDisableBit:vpExecuteDisableBit
        managed object property"
    ::= { cucsBiosVfExecuteDisableBitEntry 4 }

cucsBiosVfExecuteDisableBitPropAcl OBJECT-TYPE
    SYNTAX       Unsigned64
    MAX-ACCESS   read-only
    STATUS       current
    DESCRIPTION
        "Cisco UCS bios:VfExecuteDisableBit:propAcl managed
        object property"
    ::= { cucsBiosVfExecuteDisableBitEntry 5 }

cucsBiosVfExecuteDisableBitSupportedByDefault OBJECT-TYPE
    SYNTAX       CucsBiosSupportedAction
    MAX-ACCESS   read-only
    STATUS       current
    DESCRIPTION
        "Cisco UCS bios:VfExecuteDisableBit:supportedByDefault
        managed object property"
    ::= { cucsBiosVfExecuteDisableBitEntry 6 }

cucsBiosVfFRB2TimerTable OBJECT-TYPE
    SYNTAX           SEQUENCE OF CucsBiosVfFRB2TimerEntry
    MAX-ACCESS       not-accessible
    STATUS           current
    DESCRIPTION
        "Cisco UCS bios:VfFRB2Timer managed object table"
    ::= { cucsBiosObjects 66 }

cucsBiosVfFRB2TimerEntry OBJECT-TYPE
    SYNTAX           CucsBiosVfFRB2TimerEntry
    MAX-ACCESS       not-accessible
    STATUS           current
    DESCRIPTION
        "Entry for the cucsBiosVfFRB2TimerTable table."
    INDEX { cucsBiosVfFRB2TimerInstanceId }
    ::= { cucsBiosVfFRB2TimerTable 1 }

CucsBiosVfFRB2TimerEntry ::= SEQUENCE {
    cucsBiosVfFRB2TimerInstanceId                                    CucsManagedObjectId,
    cucsBiosVfFRB2TimerDn                                            CucsManagedObjectDn,
    cucsBiosVfFRB2TimerRn                                            SnmpAdminString,
    cucsBiosVfFRB2TimerVpFRB2Timer                                   CucsBiosVfFRB2TimerVpFRB2Timer,
    cucsBiosVfFRB2TimerPropAcl                                       Unsigned64,
    cucsBiosVfFRB2TimerSupportedByDefault                            CucsBiosSupportedAction
}

cucsBiosVfFRB2TimerInstanceId OBJECT-TYPE
    SYNTAX       CucsManagedObjectId
    MAX-ACCESS   not-accessible
    STATUS       current
    DESCRIPTION
        "Instance identifier of the managed object."
    ::= { cucsBiosVfFRB2TimerEntry 1 }

cucsBiosVfFRB2TimerDn OBJECT-TYPE
    SYNTAX       CucsManagedObjectDn
    MAX-ACCESS   read-only
    STATUS       current
    DESCRIPTION
        "Cisco UCS bios:VfFRB2Timer:dn managed object property"
    ::= { cucsBiosVfFRB2TimerEntry 2 }

cucsBiosVfFRB2TimerRn OBJECT-TYPE
    SYNTAX       SnmpAdminString
    MAX-ACCESS   read-only
    STATUS       current
    DESCRIPTION
        "Cisco UCS bios:VfFRB2Timer:rn managed object property"
    ::= { cucsBiosVfFRB2TimerEntry 3 }

cucsBiosVfFRB2TimerVpFRB2Timer OBJECT-TYPE
    SYNTAX       CucsBiosVfFRB2TimerVpFRB2Timer
    MAX-ACCESS   read-only
    STATUS       current
    DESCRIPTION
        "Cisco UCS bios:VfFRB2Timer:vpFRB2Timer managed object property"
    ::= { cucsBiosVfFRB2TimerEntry 4 }

cucsBiosVfFRB2TimerPropAcl OBJECT-TYPE
    SYNTAX       Unsigned64
    MAX-ACCESS   read-only
    STATUS       current
    DESCRIPTION
        "Cisco UCS bios:VfFRB2Timer:propAcl managed object property"
    ::= { cucsBiosVfFRB2TimerEntry 5 }

cucsBiosVfFRB2TimerSupportedByDefault OBJECT-TYPE
    SYNTAX       CucsBiosSupportedAction
    MAX-ACCESS   read-only
    STATUS       current
    DESCRIPTION
        "Cisco UCS bios:VfFRB2Timer:supportedByDefault
        managed object property"
    ::= { cucsBiosVfFRB2TimerEntry 6 }

cucsBiosVfFrequencyFloorOverrideTable OBJECT-TYPE
    SYNTAX           SEQUENCE OF CucsBiosVfFrequencyFloorOverrideEntry
    MAX-ACCESS       not-accessible
    STATUS           current
    DESCRIPTION
        "Cisco UCS bios:VfFrequencyFloorOverride managed object table"
    ::= { cucsBiosObjects 67 }

cucsBiosVfFrequencyFloorOverrideEntry OBJECT-TYPE
    SYNTAX           CucsBiosVfFrequencyFloorOverrideEntry
    MAX-ACCESS       not-accessible
    STATUS           current
    DESCRIPTION
        "Entry for the cucsBiosVfFrequencyFloorOverrideTable table."
    INDEX { cucsBiosVfFrequencyFloorOverrideInstanceId }
    ::= { cucsBiosVfFrequencyFloorOverrideTable 1 }

CucsBiosVfFrequencyFloorOverrideEntry ::= SEQUENCE {
    cucsBiosVfFrequencyFloorOverrideInstanceId                       CucsManagedObjectId,
    cucsBiosVfFrequencyFloorOverrideDn                               CucsManagedObjectDn,
    cucsBiosVfFrequencyFloorOverrideRn                               SnmpAdminString,
    cucsBiosVfFrequencyFloorOverrideVpFrequencyFloorOverride         CucsBiosVfFrequencyFloorOverrideVpFrequencyFloorOverride,
    cucsBiosVfFrequencyFloorOverridePropAcl                          Unsigned64,
    cucsBiosVfFrequencyFloorOverrideSupportedByDefault               CucsBiosSupportedAction
}

cucsBiosVfFrequencyFloorOverrideInstanceId OBJECT-TYPE
    SYNTAX       CucsManagedObjectId
    MAX-ACCESS   not-accessible
    STATUS       current
    DESCRIPTION
        "Instance identifier of the managed object."
    ::= { cucsBiosVfFrequencyFloorOverrideEntry 1 }

cucsBiosVfFrequencyFloorOverrideDn OBJECT-TYPE
    SYNTAX       CucsManagedObjectDn
    MAX-ACCESS   read-only
    STATUS       current
    DESCRIPTION
        "Cisco UCS bios:VfFrequencyFloorOverride:dn managed
        object property"
    ::= { cucsBiosVfFrequencyFloorOverrideEntry 2 }

cucsBiosVfFrequencyFloorOverrideRn OBJECT-TYPE
    SYNTAX       SnmpAdminString
    MAX-ACCESS   read-only
    STATUS       current
    DESCRIPTION
        "Cisco UCS bios:VfFrequencyFloorOverride:rn managed
        object property"
    ::= { cucsBiosVfFrequencyFloorOverrideEntry 3 }

cucsBiosVfFrequencyFloorOverrideVpFrequencyFloorOverride OBJECT-TYPE
    SYNTAX       CucsBiosVfFrequencyFloorOverrideVpFrequencyFloorOverride
    MAX-ACCESS   read-only
    STATUS       current
    DESCRIPTION
        "Cisco UCS bios:VfFrequencyFloorOverride:vpFrequencyFloorOverride
        managed object property"
    ::= { cucsBiosVfFrequencyFloorOverrideEntry 4 }

cucsBiosVfFrequencyFloorOverridePropAcl OBJECT-TYPE
    SYNTAX       Unsigned64
    MAX-ACCESS   read-only
    STATUS       current
    DESCRIPTION
        "Cisco UCS bios:VfFrequencyFloorOverride:propAcl
        managed object property"
    ::= { cucsBiosVfFrequencyFloorOverrideEntry 5 }

cucsBiosVfFrequencyFloorOverrideSupportedByDefault OBJECT-TYPE
    SYNTAX       CucsBiosSupportedAction
    MAX-ACCESS   read-only
    STATUS       current
    DESCRIPTION
        "Cisco UCS bios:VfFrequencyFloorOverride:supportedByDefault
        managed object property"
    ::= { cucsBiosVfFrequencyFloorOverrideEntry 6 }

cucsBiosVfFrontPanelLockoutTable OBJECT-TYPE
    SYNTAX           SEQUENCE OF CucsBiosVfFrontPanelLockoutEntry
    MAX-ACCESS       not-accessible
    STATUS           current
    DESCRIPTION
        "Cisco UCS bios:VfFrontPanelLockout managed object table"
    ::= { cucsBiosObjects 14 }

cucsBiosVfFrontPanelLockoutEntry OBJECT-TYPE
    SYNTAX           CucsBiosVfFrontPanelLockoutEntry
    MAX-ACCESS       not-accessible
    STATUS           current
    DESCRIPTION
        "Entry for the cucsBiosVfFrontPanelLockoutTable table."
    INDEX { cucsBiosVfFrontPanelLockoutInstanceId }
    ::= { cucsBiosVfFrontPanelLockoutTable 1 }

CucsBiosVfFrontPanelLockoutEntry ::= SEQUENCE {
    cucsBiosVfFrontPanelLockoutInstanceId                            CucsManagedObjectId,
    cucsBiosVfFrontPanelLockoutDn                                    CucsManagedObjectDn,
    cucsBiosVfFrontPanelLockoutRn                                    SnmpAdminString,
    cucsBiosVfFrontPanelLockoutVpFrontPanelLockout                   CucsBiosVfFrontPanelLockoutVpFrontPanelLockout,
    cucsBiosVfFrontPanelLockoutPropAcl                               Unsigned64,
    cucsBiosVfFrontPanelLockoutSupportedByDefault                    CucsBiosSupportedAction
}

cucsBiosVfFrontPanelLockoutInstanceId OBJECT-TYPE
    SYNTAX       CucsManagedObjectId
    MAX-ACCESS   not-accessible
    STATUS       current
    DESCRIPTION
        "Instance identifier of the managed object."
    ::= { cucsBiosVfFrontPanelLockoutEntry 1 }

cucsBiosVfFrontPanelLockoutDn OBJECT-TYPE
    SYNTAX       CucsManagedObjectDn
    MAX-ACCESS   read-only
    STATUS       current
    DESCRIPTION
        "Cisco UCS bios:VfFrontPanelLockout:dn managed object property"
    ::= { cucsBiosVfFrontPanelLockoutEntry 2 }

cucsBiosVfFrontPanelLockoutRn OBJECT-TYPE
    SYNTAX       SnmpAdminString
    MAX-ACCESS   read-only
    STATUS       current
    DESCRIPTION
        "Cisco UCS bios:VfFrontPanelLockout:rn managed object property"
    ::= { cucsBiosVfFrontPanelLockoutEntry 3 }

cucsBiosVfFrontPanelLockoutVpFrontPanelLockout OBJECT-TYPE
    SYNTAX       CucsBiosVfFrontPanelLockoutVpFrontPanelLockout
    MAX-ACCESS   read-only
    STATUS       current
    DESCRIPTION
        "Cisco UCS bios:VfFrontPanelLockout:vpFrontPanelLockout
        managed object property"
    ::= { cucsBiosVfFrontPanelLockoutEntry 4 }

cucsBiosVfFrontPanelLockoutPropAcl OBJECT-TYPE
    SYNTAX       Unsigned64
    MAX-ACCESS   read-only
    STATUS       current
    DESCRIPTION
        "Cisco UCS bios:VfFrontPanelLockout:propAcl managed
        object property"
    ::= { cucsBiosVfFrontPanelLockoutEntry 5 }

cucsBiosVfFrontPanelLockoutSupportedByDefault OBJECT-TYPE
    SYNTAX       CucsBiosSupportedAction
    MAX-ACCESS   read-only
    STATUS       current
    DESCRIPTION
        "Cisco UCS bios:VfFrontPanelLockout:supportedByDefault
        managed object property"
    ::= { cucsBiosVfFrontPanelLockoutEntry 6 }

cucsBiosVfIOEMezz1OptionROMTable OBJECT-TYPE
    SYNTAX           SEQUENCE OF CucsBiosVfIOEMezz1OptionROMEntry
    MAX-ACCESS       not-accessible
    STATUS           current
    DESCRIPTION
        "Cisco UCS bios:VfIOEMezz1OptionROM managed object table"
    ::= { cucsBiosObjects 98 }

cucsBiosVfIOEMezz1OptionROMEntry OBJECT-TYPE
    SYNTAX           CucsBiosVfIOEMezz1OptionROMEntry
    MAX-ACCESS       not-accessible
    STATUS           current
    DESCRIPTION
        "Entry for the cucsBiosVfIOEMezz1OptionROMTable table."
    INDEX { cucsBiosVfIOEMezz1OptionROMInstanceId }
    ::= { cucsBiosVfIOEMezz1OptionROMTable 1 }

CucsBiosVfIOEMezz1OptionROMEntry ::= SEQUENCE {
    cucsBiosVfIOEMezz1OptionROMInstanceId                            CucsManagedObjectId,
    cucsBiosVfIOEMezz1OptionROMDn                                    CucsManagedObjectDn,
    cucsBiosVfIOEMezz1OptionROMRn                                    SnmpAdminString,
    cucsBiosVfIOEMezz1OptionROMPropAcl                               Unsigned64,
    cucsBiosVfIOEMezz1OptionROMSupportedByDefault                    CucsBiosSupportedAction,
    cucsBiosVfIOEMezz1OptionROMVpIOEMezz1OptionROM                   CucsBiosVfIOEMezz1OptionROMVpIOEMezz1OptionROM
}

cucsBiosVfIOEMezz1OptionROMInstanceId OBJECT-TYPE
    SYNTAX       CucsManagedObjectId
    MAX-ACCESS   not-accessible
    STATUS       current
    DESCRIPTION
        "Instance identifier of the managed object."
    ::= { cucsBiosVfIOEMezz1OptionROMEntry 1 }

cucsBiosVfIOEMezz1OptionROMDn OBJECT-TYPE
    SYNTAX       CucsManagedObjectDn
    MAX-ACCESS   read-only
    STATUS       current
    DESCRIPTION
        "Cisco UCS bios:VfIOEMezz1OptionROM:dn managed object property"
    ::= { cucsBiosVfIOEMezz1OptionROMEntry 2 }

cucsBiosVfIOEMezz1OptionROMRn OBJECT-TYPE
    SYNTAX       SnmpAdminString
    MAX-ACCESS   read-only
    STATUS       current
    DESCRIPTION
        "Cisco UCS bios:VfIOEMezz1OptionROM:rn managed object property"
    ::= { cucsBiosVfIOEMezz1OptionROMEntry 3 }

cucsBiosVfIOEMezz1OptionROMPropAcl OBJECT-TYPE
    SYNTAX       Unsigned64
    MAX-ACCESS   read-only
    STATUS       current
    DESCRIPTION
        "Cisco UCS bios:VfIOEMezz1OptionROM:propAcl managed
        object property"
    ::= { cucsBiosVfIOEMezz1OptionROMEntry 4 }

cucsBiosVfIOEMezz1OptionROMSupportedByDefault OBJECT-TYPE
    SYNTAX       CucsBiosSupportedAction
    MAX-ACCESS   read-only
    STATUS       current
    DESCRIPTION
        "Cisco UCS bios:VfIOEMezz1OptionROM:supportedByDefault
        managed object property"
    ::= { cucsBiosVfIOEMezz1OptionROMEntry 5 }

cucsBiosVfIOEMezz1OptionROMVpIOEMezz1OptionROM OBJECT-TYPE
    SYNTAX       CucsBiosVfIOEMezz1OptionROMVpIOEMezz1OptionROM
    MAX-ACCESS   read-only
    STATUS       current
    DESCRIPTION
        "Cisco UCS bios:VfIOEMezz1OptionROM:vpIOEMezz1OptionROM
        managed object property"
    ::= { cucsBiosVfIOEMezz1OptionROMEntry 6 }

cucsBiosVfIOENVMe1OptionROMTable OBJECT-TYPE
    SYNTAX           SEQUENCE OF CucsBiosVfIOENVMe1OptionROMEntry
    MAX-ACCESS       not-accessible
    STATUS           current
    DESCRIPTION
        "Cisco UCS bios:VfIOENVMe1OptionROM managed object table"
    ::= { cucsBiosObjects 99 }

cucsBiosVfIOENVMe1OptionROMEntry OBJECT-TYPE
    SYNTAX           CucsBiosVfIOENVMe1OptionROMEntry
    MAX-ACCESS       not-accessible
    STATUS           current
    DESCRIPTION
        "Entry for the cucsBiosVfIOENVMe1OptionROMTable table."
    INDEX { cucsBiosVfIOENVMe1OptionROMInstanceId }
    ::= { cucsBiosVfIOENVMe1OptionROMTable 1 }

CucsBiosVfIOENVMe1OptionROMEntry ::= SEQUENCE {
    cucsBiosVfIOENVMe1OptionROMInstanceId                            CucsManagedObjectId,
    cucsBiosVfIOENVMe1OptionROMDn                                    CucsManagedObjectDn,
    cucsBiosVfIOENVMe1OptionROMRn                                    SnmpAdminString,
    cucsBiosVfIOENVMe1OptionROMPropAcl                               Unsigned64,
    cucsBiosVfIOENVMe1OptionROMSupportedByDefault                    CucsBiosSupportedAction,
    cucsBiosVfIOENVMe1OptionROMVpIOENVMe1OptionROM                   CucsBiosVfIOENVMe1OptionROMVpIOENVMe1OptionROM
}

cucsBiosVfIOENVMe1OptionROMInstanceId OBJECT-TYPE
    SYNTAX       CucsManagedObjectId
    MAX-ACCESS   not-accessible
    STATUS       current
    DESCRIPTION
        "Instance identifier of the managed object."
    ::= { cucsBiosVfIOENVMe1OptionROMEntry 1 }

cucsBiosVfIOENVMe1OptionROMDn OBJECT-TYPE
    SYNTAX       CucsManagedObjectDn
    MAX-ACCESS   read-only
    STATUS       current
    DESCRIPTION
        "Cisco UCS bios:VfIOENVMe1OptionROM:dn managed object property"
    ::= { cucsBiosVfIOENVMe1OptionROMEntry 2 }

cucsBiosVfIOENVMe1OptionROMRn OBJECT-TYPE
    SYNTAX       SnmpAdminString
    MAX-ACCESS   read-only
    STATUS       current
    DESCRIPTION
        "Cisco UCS bios:VfIOENVMe1OptionROM:rn managed object property"
    ::= { cucsBiosVfIOENVMe1OptionROMEntry 3 }

cucsBiosVfIOENVMe1OptionROMPropAcl OBJECT-TYPE
    SYNTAX       Unsigned64
    MAX-ACCESS   read-only
    STATUS       current
    DESCRIPTION
        "Cisco UCS bios:VfIOENVMe1OptionROM:propAcl managed
        object property"
    ::= { cucsBiosVfIOENVMe1OptionROMEntry 4 }

cucsBiosVfIOENVMe1OptionROMSupportedByDefault OBJECT-TYPE
    SYNTAX       CucsBiosSupportedAction
    MAX-ACCESS   read-only
    STATUS       current
    DESCRIPTION
        "Cisco UCS bios:VfIOENVMe1OptionROM:supportedByDefault
        managed object property"
    ::= { cucsBiosVfIOENVMe1OptionROMEntry 5 }

cucsBiosVfIOENVMe1OptionROMVpIOENVMe1OptionROM OBJECT-TYPE
    SYNTAX       CucsBiosVfIOENVMe1OptionROMVpIOENVMe1OptionROM
    MAX-ACCESS   read-only
    STATUS       current
    DESCRIPTION
        "Cisco UCS bios:VfIOENVMe1OptionROM:vpIOENVMe1OptionROM
        managed object property"
    ::= { cucsBiosVfIOENVMe1OptionROMEntry 6 }

cucsBiosVfIOENVMe2OptionROMTable OBJECT-TYPE
    SYNTAX           SEQUENCE OF CucsBiosVfIOENVMe2OptionROMEntry
    MAX-ACCESS       not-accessible
    STATUS           current
    DESCRIPTION
        "Cisco UCS bios:VfIOENVMe2OptionROM managed object table"
    ::= { cucsBiosObjects 100 }

cucsBiosVfIOENVMe2OptionROMEntry OBJECT-TYPE
    SYNTAX           CucsBiosVfIOENVMe2OptionROMEntry
    MAX-ACCESS       not-accessible
    STATUS           current
    DESCRIPTION
        "Entry for the cucsBiosVfIOENVMe2OptionROMTable table."
    INDEX { cucsBiosVfIOENVMe2OptionROMInstanceId }
    ::= { cucsBiosVfIOENVMe2OptionROMTable 1 }

CucsBiosVfIOENVMe2OptionROMEntry ::= SEQUENCE {
    cucsBiosVfIOENVMe2OptionROMInstanceId                            CucsManagedObjectId,
    cucsBiosVfIOENVMe2OptionROMDn                                    CucsManagedObjectDn,
    cucsBiosVfIOENVMe2OptionROMRn                                    SnmpAdminString,
    cucsBiosVfIOENVMe2OptionROMPropAcl                               Unsigned64,
    cucsBiosVfIOENVMe2OptionROMSupportedByDefault                    CucsBiosSupportedAction,
    cucsBiosVfIOENVMe2OptionROMVpIOENVMe2OptionROM                   CucsBiosVfIOENVMe2OptionROMVpIOENVMe2OptionROM
}

cucsBiosVfIOENVMe2OptionROMInstanceId OBJECT-TYPE
    SYNTAX       CucsManagedObjectId
    MAX-ACCESS   not-accessible
    STATUS       current
    DESCRIPTION
        "Instance identifier of the managed object."
    ::= { cucsBiosVfIOENVMe2OptionROMEntry 1 }

cucsBiosVfIOENVMe2OptionROMDn OBJECT-TYPE
    SYNTAX       CucsManagedObjectDn
    MAX-ACCESS   read-only
    STATUS       current
    DESCRIPTION
        "Cisco UCS bios:VfIOENVMe2OptionROM:dn managed object property"
    ::= { cucsBiosVfIOENVMe2OptionROMEntry 2 }

cucsBiosVfIOENVMe2OptionROMRn OBJECT-TYPE
    SYNTAX       SnmpAdminString
    MAX-ACCESS   read-only
    STATUS       current
    DESCRIPTION
        "Cisco UCS bios:VfIOENVMe2OptionROM:rn managed object property"
    ::= { cucsBiosVfIOENVMe2OptionROMEntry 3 }

cucsBiosVfIOENVMe2OptionROMPropAcl OBJECT-TYPE
    SYNTAX       Unsigned64
    MAX-ACCESS   read-only
    STATUS       current
    DESCRIPTION
        "Cisco UCS bios:VfIOENVMe2OptionROM:propAcl managed
        object property"
    ::= { cucsBiosVfIOENVMe2OptionROMEntry 4 }

cucsBiosVfIOENVMe2OptionROMSupportedByDefault OBJECT-TYPE
    SYNTAX       CucsBiosSupportedAction
    MAX-ACCESS   read-only
    STATUS       current
    DESCRIPTION
        "Cisco UCS bios:VfIOENVMe2OptionROM:supportedByDefault
        managed object property"
    ::= { cucsBiosVfIOENVMe2OptionROMEntry 5 }

cucsBiosVfIOENVMe2OptionROMVpIOENVMe2OptionROM OBJECT-TYPE
    SYNTAX       CucsBiosVfIOENVMe2OptionROMVpIOENVMe2OptionROM
    MAX-ACCESS   read-only
    STATUS       current
    DESCRIPTION
        "Cisco UCS bios:VfIOENVMe2OptionROM:vpIOENVMe2OptionROM
        managed object property"
    ::= { cucsBiosVfIOENVMe2OptionROMEntry 6 }

cucsBiosVfIOESlot1OptionROMTable OBJECT-TYPE
    SYNTAX           SEQUENCE OF CucsBiosVfIOESlot1OptionROMEntry
    MAX-ACCESS       not-accessible
    STATUS           current
    DESCRIPTION
        "Cisco UCS bios:VfIOESlot1OptionROM managed object table"
    ::= { cucsBiosObjects 101 }

cucsBiosVfIOESlot1OptionROMEntry OBJECT-TYPE
    SYNTAX           CucsBiosVfIOESlot1OptionROMEntry
    MAX-ACCESS       not-accessible
    STATUS           current
    DESCRIPTION
        "Entry for the cucsBiosVfIOESlot1OptionROMTable table."
    INDEX { cucsBiosVfIOESlot1OptionROMInstanceId }
    ::= { cucsBiosVfIOESlot1OptionROMTable 1 }

CucsBiosVfIOESlot1OptionROMEntry ::= SEQUENCE {
    cucsBiosVfIOESlot1OptionROMInstanceId                            CucsManagedObjectId,
    cucsBiosVfIOESlot1OptionROMDn                                    CucsManagedObjectDn,
    cucsBiosVfIOESlot1OptionROMRn                                    SnmpAdminString,
    cucsBiosVfIOESlot1OptionROMPropAcl                               Unsigned64,
    cucsBiosVfIOESlot1OptionROMSupportedByDefault                    CucsBiosSupportedAction,
    cucsBiosVfIOESlot1OptionROMVpIOESlot1OptionROM                   CucsBiosVfIOESlot1OptionROMVpIOESlot1OptionROM
}

cucsBiosVfIOESlot1OptionROMInstanceId OBJECT-TYPE
    SYNTAX       CucsManagedObjectId
    MAX-ACCESS   not-accessible
    STATUS       current
    DESCRIPTION
        "Instance identifier of the managed object."
    ::= { cucsBiosVfIOESlot1OptionROMEntry 1 }

cucsBiosVfIOESlot1OptionROMDn OBJECT-TYPE
    SYNTAX       CucsManagedObjectDn
    MAX-ACCESS   read-only
    STATUS       current
    DESCRIPTION
        "Cisco UCS bios:VfIOESlot1OptionROM:dn managed object property"
    ::= { cucsBiosVfIOESlot1OptionROMEntry 2 }

cucsBiosVfIOESlot1OptionROMRn OBJECT-TYPE
    SYNTAX       SnmpAdminString
    MAX-ACCESS   read-only
    STATUS       current
    DESCRIPTION
        "Cisco UCS bios:VfIOESlot1OptionROM:rn managed object property"
    ::= { cucsBiosVfIOESlot1OptionROMEntry 3 }

cucsBiosVfIOESlot1OptionROMPropAcl OBJECT-TYPE
    SYNTAX       Unsigned64
    MAX-ACCESS   read-only
    STATUS       current
    DESCRIPTION
        "Cisco UCS bios:VfIOESlot1OptionROM:propAcl managed
        object property"
    ::= { cucsBiosVfIOESlot1OptionROMEntry 4 }

cucsBiosVfIOESlot1OptionROMSupportedByDefault OBJECT-TYPE
    SYNTAX       CucsBiosSupportedAction
    MAX-ACCESS   read-only
    STATUS       current
    DESCRIPTION
        "Cisco UCS bios:VfIOESlot1OptionROM:supportedByDefault
        managed object property"
    ::= { cucsBiosVfIOESlot1OptionROMEntry 5 }

cucsBiosVfIOESlot1OptionROMVpIOESlot1OptionROM OBJECT-TYPE
    SYNTAX       CucsBiosVfIOESlot1OptionROMVpIOESlot1OptionROM
    MAX-ACCESS   read-only
    STATUS       current
    DESCRIPTION
        "Cisco UCS bios:VfIOESlot1OptionROM:vpIOESlot1OptionROM
        managed object property"
    ::= { cucsBiosVfIOESlot1OptionROMEntry 6 }

cucsBiosVfIOESlot2OptionROMTable OBJECT-TYPE
    SYNTAX           SEQUENCE OF CucsBiosVfIOESlot2OptionROMEntry
    MAX-ACCESS       not-accessible
    STATUS           current
    DESCRIPTION
        "Cisco UCS bios:VfIOESlot2OptionROM managed object table"
    ::= { cucsBiosObjects 102 }

cucsBiosVfIOESlot2OptionROMEntry OBJECT-TYPE
    SYNTAX           CucsBiosVfIOESlot2OptionROMEntry
    MAX-ACCESS       not-accessible
    STATUS           current
    DESCRIPTION
        "Entry for the cucsBiosVfIOESlot2OptionROMTable table."
    INDEX { cucsBiosVfIOESlot2OptionROMInstanceId }
    ::= { cucsBiosVfIOESlot2OptionROMTable 1 }

CucsBiosVfIOESlot2OptionROMEntry ::= SEQUENCE {
    cucsBiosVfIOESlot2OptionROMInstanceId                            CucsManagedObjectId,
    cucsBiosVfIOESlot2OptionROMDn                                    CucsManagedObjectDn,
    cucsBiosVfIOESlot2OptionROMRn                                    SnmpAdminString,
    cucsBiosVfIOESlot2OptionROMPropAcl                               Unsigned64,
    cucsBiosVfIOESlot2OptionROMSupportedByDefault                    CucsBiosSupportedAction,
    cucsBiosVfIOESlot2OptionROMVpIOESlot2OptionROM                   CucsBiosVfIOESlot2OptionROMVpIOESlot2OptionROM
}

cucsBiosVfIOESlot2OptionROMInstanceId OBJECT-TYPE
    SYNTAX       CucsManagedObjectId
    MAX-ACCESS   not-accessible
    STATUS       current
    DESCRIPTION
        "Instance identifier of the managed object."
    ::= { cucsBiosVfIOESlot2OptionROMEntry 1 }

cucsBiosVfIOESlot2OptionROMDn OBJECT-TYPE
    SYNTAX       CucsManagedObjectDn
    MAX-ACCESS   read-only
    STATUS       current
    DESCRIPTION
        "Cisco UCS bios:VfIOESlot2OptionROM:dn managed object property"
    ::= { cucsBiosVfIOESlot2OptionROMEntry 2 }

cucsBiosVfIOESlot2OptionROMRn OBJECT-TYPE
    SYNTAX       SnmpAdminString
    MAX-ACCESS   read-only
    STATUS       current
    DESCRIPTION
        "Cisco UCS bios:VfIOESlot2OptionROM:rn managed object property"
    ::= { cucsBiosVfIOESlot2OptionROMEntry 3 }

cucsBiosVfIOESlot2OptionROMPropAcl OBJECT-TYPE
    SYNTAX       Unsigned64
    MAX-ACCESS   read-only
    STATUS       current
    DESCRIPTION
        "Cisco UCS bios:VfIOESlot2OptionROM:propAcl managed
        object property"
    ::= { cucsBiosVfIOESlot2OptionROMEntry 4 }

cucsBiosVfIOESlot2OptionROMSupportedByDefault OBJECT-TYPE
    SYNTAX       CucsBiosSupportedAction
    MAX-ACCESS   read-only
    STATUS       current
    DESCRIPTION
        "Cisco UCS bios:VfIOESlot2OptionROM:supportedByDefault
        managed object property"
    ::= { cucsBiosVfIOESlot2OptionROMEntry 5 }

cucsBiosVfIOESlot2OptionROMVpIOESlot2OptionROM OBJECT-TYPE
    SYNTAX       CucsBiosVfIOESlot2OptionROMVpIOESlot2OptionROM
    MAX-ACCESS   read-only
    STATUS       current
    DESCRIPTION
        "Cisco UCS bios:VfIOESlot2OptionROM:vpIOESlot2OptionROM
        managed object property"
    ::= { cucsBiosVfIOESlot2OptionROMEntry 6 }

cucsBiosVfIntegratedGraphicsTable OBJECT-TYPE
    SYNTAX           SEQUENCE OF CucsBiosVfIntegratedGraphicsEntry
    MAX-ACCESS       not-accessible
    STATUS           current
    DESCRIPTION
        "Cisco UCS bios:VfIntegratedGraphics managed object table"
    ::= { cucsBiosObjects 93 }

cucsBiosVfIntegratedGraphicsEntry OBJECT-TYPE
    SYNTAX           CucsBiosVfIntegratedGraphicsEntry
    MAX-ACCESS       not-accessible
    STATUS           current
    DESCRIPTION
        "Entry for the cucsBiosVfIntegratedGraphicsTable table."
    INDEX { cucsBiosVfIntegratedGraphicsInstanceId }
    ::= { cucsBiosVfIntegratedGraphicsTable 1 }

CucsBiosVfIntegratedGraphicsEntry ::= SEQUENCE {
    cucsBiosVfIntegratedGraphicsInstanceId                           CucsManagedObjectId,
    cucsBiosVfIntegratedGraphicsDn                                   CucsManagedObjectDn,
    cucsBiosVfIntegratedGraphicsRn                                   SnmpAdminString,
    cucsBiosVfIntegratedGraphicsSupportedByDefault                   CucsBiosSupportedAction,
    cucsBiosVfIntegratedGraphicsVpIntegratedGraphics                 CucsBiosVfIntegratedGraphicsVpIntegratedGraphics,
    cucsBiosVfIntegratedGraphicsPropAcl                              Unsigned64
}

cucsBiosVfIntegratedGraphicsInstanceId OBJECT-TYPE
    SYNTAX       CucsManagedObjectId
    MAX-ACCESS   not-accessible
    STATUS       current
    DESCRIPTION
        "Instance identifier of the managed object."
    ::= { cucsBiosVfIntegratedGraphicsEntry 1 }

cucsBiosVfIntegratedGraphicsDn OBJECT-TYPE
    SYNTAX       CucsManagedObjectDn
    MAX-ACCESS   read-only
    STATUS       current
    DESCRIPTION
        "Cisco UCS bios:VfIntegratedGraphics:dn managed object property"
    ::= { cucsBiosVfIntegratedGraphicsEntry 2 }

cucsBiosVfIntegratedGraphicsRn OBJECT-TYPE
    SYNTAX       SnmpAdminString
    MAX-ACCESS   read-only
    STATUS       current
    DESCRIPTION
        "Cisco UCS bios:VfIntegratedGraphics:rn managed object property"
    ::= { cucsBiosVfIntegratedGraphicsEntry 3 }

cucsBiosVfIntegratedGraphicsSupportedByDefault OBJECT-TYPE
    SYNTAX       CucsBiosSupportedAction
    MAX-ACCESS   read-only
    STATUS       current
    DESCRIPTION
        "Cisco UCS bios:VfIntegratedGraphics:supportedByDefault
        managed object property"
    ::= { cucsBiosVfIntegratedGraphicsEntry 4 }

cucsBiosVfIntegratedGraphicsVpIntegratedGraphics OBJECT-TYPE
    SYNTAX       CucsBiosVfIntegratedGraphicsVpIntegratedGraphics
    MAX-ACCESS   read-only
    STATUS       current
    DESCRIPTION
        "Cisco UCS bios:VfIntegratedGraphics:vpIntegratedGraphics
        managed object property"
    ::= { cucsBiosVfIntegratedGraphicsEntry 5 }

cucsBiosVfIntegratedGraphicsPropAcl OBJECT-TYPE
    SYNTAX       Unsigned64
    MAX-ACCESS   read-only
    STATUS       current
    DESCRIPTION
        "Cisco UCS bios:VfIntegratedGraphics:propAcl managed
        object property"
    ::= { cucsBiosVfIntegratedGraphicsEntry 6 }

cucsBiosVfIntegratedGraphicsApertureSizeTable OBJECT-TYPE
    SYNTAX           SEQUENCE OF CucsBiosVfIntegratedGraphicsApertureSizeEntry
    MAX-ACCESS       not-accessible
    STATUS           current
    DESCRIPTION
        "Cisco UCS bios:VfIntegratedGraphicsApertureSize
        managed object table"
    ::= { cucsBiosObjects 94 }

cucsBiosVfIntegratedGraphicsApertureSizeEntry OBJECT-TYPE
    SYNTAX           CucsBiosVfIntegratedGraphicsApertureSizeEntry
    MAX-ACCESS       not-accessible
    STATUS           current
    DESCRIPTION
        "Entry for the cucsBiosVfIntegratedGraphicsApertureSizeTable table."
    INDEX { cucsBiosVfIntegratedGraphicsApertureSizeInstanceId }
    ::= { cucsBiosVfIntegratedGraphicsApertureSizeTable 1 }

CucsBiosVfIntegratedGraphicsApertureSizeEntry ::= SEQUENCE {
    cucsBiosVfIntegratedGraphicsApertureSizeInstanceId               CucsManagedObjectId,
    cucsBiosVfIntegratedGraphicsApertureSizeDn                       CucsManagedObjectDn,
    cucsBiosVfIntegratedGraphicsApertureSizeRn                       SnmpAdminString,
    cucsBiosVfIntegratedGraphicsApertureSizeSupportedByDefault       CucsBiosSupportedAction,
    cucsBiosVfIntegratedGraphicsApertureSizeVpIntgtGraphApertureSize CucsBiosVfIntegratedGraphicsApertureSizeVpIntgtGraphApertureSize,
    cucsBiosVfIntegratedGraphicsApertureSizePropAcl                  Unsigned64
}

cucsBiosVfIntegratedGraphicsApertureSizeInstanceId OBJECT-TYPE
    SYNTAX       CucsManagedObjectId
    MAX-ACCESS   not-accessible
    STATUS       current
    DESCRIPTION
        "Instance identifier of the managed object."
    ::= { cucsBiosVfIntegratedGraphicsApertureSizeEntry 1 }

cucsBiosVfIntegratedGraphicsApertureSizeDn OBJECT-TYPE
    SYNTAX       CucsManagedObjectDn
    MAX-ACCESS   read-only
    STATUS       current
    DESCRIPTION
        "Cisco UCS bios:VfIntegratedGraphicsApertureSize:dn
        managed object property"
    ::= { cucsBiosVfIntegratedGraphicsApertureSizeEntry 2 }

cucsBiosVfIntegratedGraphicsApertureSizeRn OBJECT-TYPE
    SYNTAX       SnmpAdminString
    MAX-ACCESS   read-only
    STATUS       current
    DESCRIPTION
        "Cisco UCS bios:VfIntegratedGraphicsApertureSize:rn
        managed object property"
    ::= { cucsBiosVfIntegratedGraphicsApertureSizeEntry 3 }

cucsBiosVfIntegratedGraphicsApertureSizeSupportedByDefault OBJECT-TYPE
    SYNTAX       CucsBiosSupportedAction
    MAX-ACCESS   read-only
    STATUS       current
    DESCRIPTION
        "Cisco UCS bios:VfIntegratedGraphicsApertureSize:supportedByDefaul
        t managed object property"
    ::= { cucsBiosVfIntegratedGraphicsApertureSizeEntry 4 }

cucsBiosVfIntegratedGraphicsApertureSizeVpIntgtGraphApertureSize OBJECT-TYPE
    SYNTAX       CucsBiosVfIntegratedGraphicsApertureSizeVpIntgtGraphApertureSize
    MAX-ACCESS   read-only
    STATUS       current
    DESCRIPTION
        "Cisco UCS bios:VfIntegratedGraphicsApertureSize:vpIntegratedGraph
        icsApertureSize managed object property"
    ::= { cucsBiosVfIntegratedGraphicsApertureSizeEntry 5 }

cucsBiosVfIntegratedGraphicsApertureSizePropAcl OBJECT-TYPE
    SYNTAX       Unsigned64
    MAX-ACCESS   read-only
    STATUS       current
    DESCRIPTION
        "Cisco UCS bios:VfIntegratedGraphicsApertureSize:propAcl
        managed object property"
    ::= { cucsBiosVfIntegratedGraphicsApertureSizeEntry 6 }

cucsBiosVfIntelEntrySASRAIDModuleTable OBJECT-TYPE
    SYNTAX           SEQUENCE OF CucsBiosVfIntelEntrySASRAIDModuleEntry
    MAX-ACCESS       not-accessible
    STATUS           current
    DESCRIPTION
        "Cisco UCS bios:VfIntelEntrySASRAIDModule managed object table"
    ::= { cucsBiosObjects 39 }

cucsBiosVfIntelEntrySASRAIDModuleEntry OBJECT-TYPE
    SYNTAX           CucsBiosVfIntelEntrySASRAIDModuleEntry
    MAX-ACCESS       not-accessible
    STATUS           current
    DESCRIPTION
        "Entry for the cucsBiosVfIntelEntrySASRAIDModuleTable table."
    INDEX { cucsBiosVfIntelEntrySASRAIDModuleInstanceId }
    ::= { cucsBiosVfIntelEntrySASRAIDModuleTable 1 }

CucsBiosVfIntelEntrySASRAIDModuleEntry ::= SEQUENCE {
    cucsBiosVfIntelEntrySASRAIDModuleInstanceId                      CucsManagedObjectId,
    cucsBiosVfIntelEntrySASRAIDModuleDn                              CucsManagedObjectDn,
    cucsBiosVfIntelEntrySASRAIDModuleRn                              SnmpAdminString,
    cucsBiosVfIntelEntrySASRAIDModuleVpSASRAID                       CucsBiosVfIntelEntrySASRAIDModuleVpSASRAID,
    cucsBiosVfIntelEntrySASRAIDModuleVpSASRAIDModule                 CucsBiosVfIntelEntrySASRAIDModuleVpSASRAIDModule,
    cucsBiosVfIntelEntrySASRAIDModulePropAcl                         Unsigned64,
    cucsBiosVfIntelEntrySASRAIDModuleSupportedByDefault              CucsBiosSupportedAction
}

cucsBiosVfIntelEntrySASRAIDModuleInstanceId OBJECT-TYPE
    SYNTAX       CucsManagedObjectId
    MAX-ACCESS   not-accessible
    STATUS       current
    DESCRIPTION
        "Instance identifier of the managed object."
    ::= { cucsBiosVfIntelEntrySASRAIDModuleEntry 1 }

cucsBiosVfIntelEntrySASRAIDModuleDn OBJECT-TYPE
    SYNTAX       CucsManagedObjectDn
    MAX-ACCESS   read-only
    STATUS       current
    DESCRIPTION
        "Cisco UCS bios:VfIntelEntrySASRAIDModule:dn managed
        object property"
    ::= { cucsBiosVfIntelEntrySASRAIDModuleEntry 2 }

cucsBiosVfIntelEntrySASRAIDModuleRn OBJECT-TYPE
    SYNTAX       SnmpAdminString
    MAX-ACCESS   read-only
    STATUS       current
    DESCRIPTION
        "Cisco UCS bios:VfIntelEntrySASRAIDModule:rn managed
        object property"
    ::= { cucsBiosVfIntelEntrySASRAIDModuleEntry 3 }

cucsBiosVfIntelEntrySASRAIDModuleVpSASRAID OBJECT-TYPE
    SYNTAX       CucsBiosVfIntelEntrySASRAIDModuleVpSASRAID
    MAX-ACCESS   read-only
    STATUS       current
    DESCRIPTION
        "Cisco UCS bios:VfIntelEntrySASRAIDModule:vpSASRAID
        managed object property"
    ::= { cucsBiosVfIntelEntrySASRAIDModuleEntry 4 }

cucsBiosVfIntelEntrySASRAIDModuleVpSASRAIDModule OBJECT-TYPE
    SYNTAX       CucsBiosVfIntelEntrySASRAIDModuleVpSASRAIDModule
    MAX-ACCESS   read-only
    STATUS       current
    DESCRIPTION
        "Cisco UCS bios:VfIntelEntrySASRAIDModule:vpSASRAIDModule
        managed object property"
    ::= { cucsBiosVfIntelEntrySASRAIDModuleEntry 5 }

cucsBiosVfIntelEntrySASRAIDModulePropAcl OBJECT-TYPE
    SYNTAX       Unsigned64
    MAX-ACCESS   read-only
    STATUS       current
    DESCRIPTION
        "Cisco UCS bios:VfIntelEntrySASRAIDModule:propAcl
        managed object property"
    ::= { cucsBiosVfIntelEntrySASRAIDModuleEntry 6 }

cucsBiosVfIntelEntrySASRAIDModuleSupportedByDefault OBJECT-TYPE
    SYNTAX       CucsBiosSupportedAction
    MAX-ACCESS   read-only
    STATUS       current
    DESCRIPTION
        "Cisco UCS bios:VfIntelEntrySASRAIDModule:supportedByDefault
        managed object property"
    ::= { cucsBiosVfIntelEntrySASRAIDModuleEntry 7 }

cucsBiosVfIntelHyperThreadingTechTable OBJECT-TYPE
    SYNTAX           SEQUENCE OF CucsBiosVfIntelHyperThreadingTechEntry
    MAX-ACCESS       not-accessible
    STATUS           current
    DESCRIPTION
        "Cisco UCS bios:VfIntelHyperThreadingTech managed object table"
    ::= { cucsBiosObjects 15 }

cucsBiosVfIntelHyperThreadingTechEntry OBJECT-TYPE
    SYNTAX           CucsBiosVfIntelHyperThreadingTechEntry
    MAX-ACCESS       not-accessible
    STATUS           current
    DESCRIPTION
        "Entry for the cucsBiosVfIntelHyperThreadingTechTable table."
    INDEX { cucsBiosVfIntelHyperThreadingTechInstanceId }
    ::= { cucsBiosVfIntelHyperThreadingTechTable 1 }

CucsBiosVfIntelHyperThreadingTechEntry ::= SEQUENCE {
    cucsBiosVfIntelHyperThreadingTechInstanceId                      CucsManagedObjectId,
    cucsBiosVfIntelHyperThreadingTechDn                              CucsManagedObjectDn,
    cucsBiosVfIntelHyperThreadingTechRn                              SnmpAdminString,
    cucsBiosVfIntelHyperThreadingTechVpIntelHyperThreadingTech       CucsBiosVfIntelHyperThreadingTechVpIntelHyperThreadingTech,
    cucsBiosVfIntelHyperThreadingTechPropAcl                         Unsigned64,
    cucsBiosVfIntelHyperThreadingTechSupportedByDefault              CucsBiosSupportedAction
}

cucsBiosVfIntelHyperThreadingTechInstanceId OBJECT-TYPE
    SYNTAX       CucsManagedObjectId
    MAX-ACCESS   not-accessible
    STATUS       current
    DESCRIPTION
        "Instance identifier of the managed object."
    ::= { cucsBiosVfIntelHyperThreadingTechEntry 1 }

cucsBiosVfIntelHyperThreadingTechDn OBJECT-TYPE
    SYNTAX       CucsManagedObjectDn
    MAX-ACCESS   read-only
    STATUS       current
    DESCRIPTION
        "Cisco UCS bios:VfIntelHyperThreadingTech:dn managed
        object property"
    ::= { cucsBiosVfIntelHyperThreadingTechEntry 2 }

cucsBiosVfIntelHyperThreadingTechRn OBJECT-TYPE
    SYNTAX       SnmpAdminString
    MAX-ACCESS   read-only
    STATUS       current
    DESCRIPTION
        "Cisco UCS bios:VfIntelHyperThreadingTech:rn managed
        object property"
    ::= { cucsBiosVfIntelHyperThreadingTechEntry 3 }

cucsBiosVfIntelHyperThreadingTechVpIntelHyperThreadingTech OBJECT-TYPE
    SYNTAX       CucsBiosVfIntelHyperThreadingTechVpIntelHyperThreadingTech
    MAX-ACCESS   read-only
    STATUS       current
    DESCRIPTION
        "Cisco UCS bios:VfIntelHyperThreadingTech:vpIntelHyperThreadingTec
        h managed object property"
    ::= { cucsBiosVfIntelHyperThreadingTechEntry 4 }

cucsBiosVfIntelHyperThreadingTechPropAcl OBJECT-TYPE
    SYNTAX       Unsigned64
    MAX-ACCESS   read-only
    STATUS       current
    DESCRIPTION
        "Cisco UCS bios:VfIntelHyperThreadingTech:propAcl
        managed object property"
    ::= { cucsBiosVfIntelHyperThreadingTechEntry 5 }

cucsBiosVfIntelHyperThreadingTechSupportedByDefault OBJECT-TYPE
    SYNTAX       CucsBiosSupportedAction
    MAX-ACCESS   read-only
    STATUS       current
    DESCRIPTION
        "Cisco UCS bios:VfIntelHyperThreadingTech:supportedByDefault
        managed object property"
    ::= { cucsBiosVfIntelHyperThreadingTechEntry 6 }

cucsBiosVfIntelTrustedExecutionTechnologyTable OBJECT-TYPE
    SYNTAX           SEQUENCE OF CucsBiosVfIntelTrustedExecutionTechnologyEntry
    MAX-ACCESS       not-accessible
    STATUS           current
    DESCRIPTION
        "Cisco UCS bios:VfIntelTrustedExecutionTechnology
        managed object table"
    ::= { cucsBiosObjects 88 }

cucsBiosVfIntelTrustedExecutionTechnologyEntry OBJECT-TYPE
    SYNTAX           CucsBiosVfIntelTrustedExecutionTechnologyEntry
    MAX-ACCESS       not-accessible
    STATUS           current
    DESCRIPTION
        "Entry for the cucsBiosVfIntelTrustedExecutionTechnologyTable table."
    INDEX { cucsBiosVfIntelTrustedExecutionTechnologyInstanceId }
    ::= { cucsBiosVfIntelTrustedExecutionTechnologyTable 1 }

CucsBiosVfIntelTrustedExecutionTechnologyEntry ::= SEQUENCE {
    cucsBiosVfIntelTrustedExecutionTechnologyInstanceId              CucsManagedObjectId,
    cucsBiosVfIntelTrustedExecutionTechnologyDn                      CucsManagedObjectDn,
    cucsBiosVfIntelTrustedExecutionTechnologyRn                      SnmpAdminString,
    cucsBiosVfIntelTrustedExecutionTechnologyVpIntelTstdExecTechSup  CucsBiosVfIntelTrustedExecutionTechnologyVpIntelTstdExecTechSup,
    cucsBiosVfIntelTrustedExecutionTechnologySupportedByDefault      CucsBiosSupportedAction,
    cucsBiosVfIntelTrustedExecutionTechnologyPropAcl                 Unsigned64
}

cucsBiosVfIntelTrustedExecutionTechnologyInstanceId OBJECT-TYPE
    SYNTAX       CucsManagedObjectId
    MAX-ACCESS   not-accessible
    STATUS       current
    DESCRIPTION
        "Instance identifier of the managed object."
    ::= { cucsBiosVfIntelTrustedExecutionTechnologyEntry 1 }

cucsBiosVfIntelTrustedExecutionTechnologyDn OBJECT-TYPE
    SYNTAX       CucsManagedObjectDn
    MAX-ACCESS   read-only
    STATUS       current
    DESCRIPTION
        "Cisco UCS bios:VfIntelTrustedExecutionTechnology:dn
        managed object property"
    ::= { cucsBiosVfIntelTrustedExecutionTechnologyEntry 2 }

cucsBiosVfIntelTrustedExecutionTechnologyRn OBJECT-TYPE
    SYNTAX       SnmpAdminString
    MAX-ACCESS   read-only
    STATUS       current
    DESCRIPTION
        "Cisco UCS bios:VfIntelTrustedExecutionTechnology:rn
        managed object property"
    ::= { cucsBiosVfIntelTrustedExecutionTechnologyEntry 3 }

cucsBiosVfIntelTrustedExecutionTechnologyVpIntelTstdExecTechSup OBJECT-TYPE
    SYNTAX       CucsBiosVfIntelTrustedExecutionTechnologyVpIntelTstdExecTechSup
    MAX-ACCESS   read-only
    STATUS       current
    DESCRIPTION
        "Cisco UCS bios:VfIntelTrustedExecutionTechnology:vpIntelTrustedEx
        ecutionTechnologySupport managed object property"
    ::= { cucsBiosVfIntelTrustedExecutionTechnologyEntry 4 }

cucsBiosVfIntelTrustedExecutionTechnologySupportedByDefault OBJECT-TYPE
    SYNTAX       CucsBiosSupportedAction
    MAX-ACCESS   read-only
    STATUS       current
    DESCRIPTION
        "Cisco UCS bios:VfIntelTrustedExecutionTechnology:supportedByDefau
        lt managed object property"
    ::= { cucsBiosVfIntelTrustedExecutionTechnologyEntry 5 }

cucsBiosVfIntelTrustedExecutionTechnologyPropAcl OBJECT-TYPE
    SYNTAX       Unsigned64
    MAX-ACCESS   read-only
    STATUS       current
    DESCRIPTION
        "Cisco UCS bios:VfIntelTrustedExecutionTechnology:propAcl
        managed object property"
    ::= { cucsBiosVfIntelTrustedExecutionTechnologyEntry 6 }

cucsBiosVfIntelTurboBoostTechTable OBJECT-TYPE
    SYNTAX           SEQUENCE OF CucsBiosVfIntelTurboBoostTechEntry
    MAX-ACCESS       not-accessible
    STATUS           current
    DESCRIPTION
        "Cisco UCS bios:VfIntelTurboBoostTech managed object table"
    ::= { cucsBiosObjects 16 }

cucsBiosVfIntelTurboBoostTechEntry OBJECT-TYPE
    SYNTAX           CucsBiosVfIntelTurboBoostTechEntry
    MAX-ACCESS       not-accessible
    STATUS           current
    DESCRIPTION
        "Entry for the cucsBiosVfIntelTurboBoostTechTable table."
    INDEX { cucsBiosVfIntelTurboBoostTechInstanceId }
    ::= { cucsBiosVfIntelTurboBoostTechTable 1 }

CucsBiosVfIntelTurboBoostTechEntry ::= SEQUENCE {
    cucsBiosVfIntelTurboBoostTechInstanceId                          CucsManagedObjectId,
    cucsBiosVfIntelTurboBoostTechDn                                  CucsManagedObjectDn,
    cucsBiosVfIntelTurboBoostTechRn                                  SnmpAdminString,
    cucsBiosVfIntelTurboBoostTechVpIntelTurboBoostTech               CucsBiosVfIntelTurboBoostTechVpIntelTurboBoostTech,
    cucsBiosVfIntelTurboBoostTechPropAcl                             Unsigned64,
    cucsBiosVfIntelTurboBoostTechSupportedByDefault                  CucsBiosSupportedAction
}

cucsBiosVfIntelTurboBoostTechInstanceId OBJECT-TYPE
    SYNTAX       CucsManagedObjectId
    MAX-ACCESS   not-accessible
    STATUS       current
    DESCRIPTION
        "Instance identifier of the managed object."
    ::= { cucsBiosVfIntelTurboBoostTechEntry 1 }

cucsBiosVfIntelTurboBoostTechDn OBJECT-TYPE
    SYNTAX       CucsManagedObjectDn
    MAX-ACCESS   read-only
    STATUS       current
    DESCRIPTION
        "Cisco UCS bios:VfIntelTurboBoostTech:dn managed object property"
    ::= { cucsBiosVfIntelTurboBoostTechEntry 2 }

cucsBiosVfIntelTurboBoostTechRn OBJECT-TYPE
    SYNTAX       SnmpAdminString
    MAX-ACCESS   read-only
    STATUS       current
    DESCRIPTION
        "Cisco UCS bios:VfIntelTurboBoostTech:rn managed object property"
    ::= { cucsBiosVfIntelTurboBoostTechEntry 3 }

cucsBiosVfIntelTurboBoostTechVpIntelTurboBoostTech OBJECT-TYPE
    SYNTAX       CucsBiosVfIntelTurboBoostTechVpIntelTurboBoostTech
    MAX-ACCESS   read-only
    STATUS       current
    DESCRIPTION
        "Cisco UCS bios:VfIntelTurboBoostTech:vpIntelTurboBoostTech
        managed object property"
    ::= { cucsBiosVfIntelTurboBoostTechEntry 4 }

cucsBiosVfIntelTurboBoostTechPropAcl OBJECT-TYPE
    SYNTAX       Unsigned64
    MAX-ACCESS   read-only
    STATUS       current
    DESCRIPTION
        "Cisco UCS bios:VfIntelTurboBoostTech:propAcl managed
        object property"
    ::= { cucsBiosVfIntelTurboBoostTechEntry 5 }

cucsBiosVfIntelTurboBoostTechSupportedByDefault OBJECT-TYPE
    SYNTAX       CucsBiosSupportedAction
    MAX-ACCESS   read-only
    STATUS       current
    DESCRIPTION
        "Cisco UCS bios:VfIntelTurboBoostTech:supportedByDefault
        managed object property"
    ::= { cucsBiosVfIntelTurboBoostTechEntry 6 }

cucsBiosVfIntelVTForDirectedIOTable OBJECT-TYPE
    SYNTAX           SEQUENCE OF CucsBiosVfIntelVTForDirectedIOEntry
    MAX-ACCESS       not-accessible
    STATUS           current
    DESCRIPTION
        "Cisco UCS bios:VfIntelVTForDirectedIO managed object table"
    ::= { cucsBiosObjects 17 }

cucsBiosVfIntelVTForDirectedIOEntry OBJECT-TYPE
    SYNTAX           CucsBiosVfIntelVTForDirectedIOEntry
    MAX-ACCESS       not-accessible
    STATUS           current
    DESCRIPTION
        "Entry for the cucsBiosVfIntelVTForDirectedIOTable table."
    INDEX { cucsBiosVfIntelVTForDirectedIOInstanceId }
    ::= { cucsBiosVfIntelVTForDirectedIOTable 1 }

CucsBiosVfIntelVTForDirectedIOEntry ::= SEQUENCE {
    cucsBiosVfIntelVTForDirectedIOInstanceId                         CucsManagedObjectId,
    cucsBiosVfIntelVTForDirectedIODn                                 CucsManagedObjectDn,
    cucsBiosVfIntelVTForDirectedIORn                                 SnmpAdminString,
    cucsBiosVfIntelVTForDirectedIOVpIntelVTDATSSupport               CucsBiosVfIntelVTForDirectedIOVpIntelVTDATSSupport,
    cucsBiosVfIntelVTForDirectedIOVpIntelVTDCoherencySupport         CucsBiosVfIntelVTForDirectedIOVpIntelVTDCoherencySupport,
    cucsBiosVfIntelVTForDirectedIOVpIntelVTDInterruptRemapping       CucsBiosVfIntelVTForDirectedIOVpIntelVTDInterruptRemapping,
    cucsBiosVfIntelVTForDirectedIOVpIntelVTDPassThroughDMASupport    CucsBiosVfIntelVTForDirectedIOVpIntelVTDPassThroughDMASupport,
    cucsBiosVfIntelVTForDirectedIOVpIntelVTForDirectedIO             CucsBiosVfIntelVTForDirectedIOVpIntelVTForDirectedIO,
    cucsBiosVfIntelVTForDirectedIOPropAcl                            Unsigned64,
    cucsBiosVfIntelVTForDirectedIOSupportedByDefault                 CucsBiosSupportedAction
}

cucsBiosVfIntelVTForDirectedIOInstanceId OBJECT-TYPE
    SYNTAX       CucsManagedObjectId
    MAX-ACCESS   not-accessible
    STATUS       current
    DESCRIPTION
        "Instance identifier of the managed object."
    ::= { cucsBiosVfIntelVTForDirectedIOEntry 1 }

cucsBiosVfIntelVTForDirectedIODn OBJECT-TYPE
    SYNTAX       CucsManagedObjectDn
    MAX-ACCESS   read-only
    STATUS       current
    DESCRIPTION
        "Cisco UCS bios:VfIntelVTForDirectedIO:dn managed object property"
    ::= { cucsBiosVfIntelVTForDirectedIOEntry 2 }

cucsBiosVfIntelVTForDirectedIORn OBJECT-TYPE
    SYNTAX       SnmpAdminString
    MAX-ACCESS   read-only
    STATUS       current
    DESCRIPTION
        "Cisco UCS bios:VfIntelVTForDirectedIO:rn managed object property"
    ::= { cucsBiosVfIntelVTForDirectedIOEntry 3 }

cucsBiosVfIntelVTForDirectedIOVpIntelVTDATSSupport OBJECT-TYPE
    SYNTAX       CucsBiosVfIntelVTForDirectedIOVpIntelVTDATSSupport
    MAX-ACCESS   read-only
    STATUS       current
    DESCRIPTION
        "Cisco UCS bios:VfIntelVTForDirectedIO:vpIntelVTDATSSupport
        managed object property"
    ::= { cucsBiosVfIntelVTForDirectedIOEntry 4 }

cucsBiosVfIntelVTForDirectedIOVpIntelVTDCoherencySupport OBJECT-TYPE
    SYNTAX       CucsBiosVfIntelVTForDirectedIOVpIntelVTDCoherencySupport
    MAX-ACCESS   read-only
    STATUS       current
    DESCRIPTION
        "Cisco UCS bios:VfIntelVTForDirectedIO:vpIntelVTDCoherencySupport
        managed object property"
    ::= { cucsBiosVfIntelVTForDirectedIOEntry 5 }

cucsBiosVfIntelVTForDirectedIOVpIntelVTDInterruptRemapping OBJECT-TYPE
    SYNTAX       CucsBiosVfIntelVTForDirectedIOVpIntelVTDInterruptRemapping
    MAX-ACCESS   read-only
    STATUS       current
    DESCRIPTION
        "Cisco UCS bios:VfIntelVTForDirectedIO:vpIntelVTDInterruptRemappin
        g managed object property"
    ::= { cucsBiosVfIntelVTForDirectedIOEntry 6 }

cucsBiosVfIntelVTForDirectedIOVpIntelVTDPassThroughDMASupport OBJECT-TYPE
    SYNTAX       CucsBiosVfIntelVTForDirectedIOVpIntelVTDPassThroughDMASupport
    MAX-ACCESS   read-only
    STATUS       current
    DESCRIPTION
        "Cisco UCS bios:VfIntelVTForDirectedIO:vpIntelVTDPassThroughDMASup
        port managed object property"
    ::= { cucsBiosVfIntelVTForDirectedIOEntry 7 }

cucsBiosVfIntelVTForDirectedIOVpIntelVTForDirectedIO OBJECT-TYPE
    SYNTAX       CucsBiosVfIntelVTForDirectedIOVpIntelVTForDirectedIO
    MAX-ACCESS   read-only
    STATUS       current
    DESCRIPTION
        "Cisco UCS bios:VfIntelVTForDirectedIO:vpIntelVTForDirectedIO
        managed object property"
    ::= { cucsBiosVfIntelVTForDirectedIOEntry 8 }

cucsBiosVfIntelVTForDirectedIOPropAcl OBJECT-TYPE
    SYNTAX       Unsigned64
    MAX-ACCESS   read-only
    STATUS       current
    DESCRIPTION
        "Cisco UCS bios:VfIntelVTForDirectedIO:propAcl
        managed object property"
    ::= { cucsBiosVfIntelVTForDirectedIOEntry 9 }

cucsBiosVfIntelVTForDirectedIOSupportedByDefault OBJECT-TYPE
    SYNTAX       CucsBiosSupportedAction
    MAX-ACCESS   read-only
    STATUS       current
    DESCRIPTION
        "Cisco UCS bios:VfIntelVTForDirectedIO:supportedByDefault
        managed object property"
    ::= { cucsBiosVfIntelVTForDirectedIOEntry 10 }

cucsBiosVfIntelVirtualizationTechnologyTable OBJECT-TYPE
    SYNTAX           SEQUENCE OF CucsBiosVfIntelVirtualizationTechnologyEntry
    MAX-ACCESS       not-accessible
    STATUS           current
    DESCRIPTION
        "Cisco UCS bios:VfIntelVirtualizationTechnology
        managed object table"
    ::= { cucsBiosObjects 18 }

cucsBiosVfIntelVirtualizationTechnologyEntry OBJECT-TYPE
    SYNTAX           CucsBiosVfIntelVirtualizationTechnologyEntry
    MAX-ACCESS       not-accessible
    STATUS           current
    DESCRIPTION
        "Entry for the cucsBiosVfIntelVirtualizationTechnologyTable table."
    INDEX { cucsBiosVfIntelVirtualizationTechnologyInstanceId }
    ::= { cucsBiosVfIntelVirtualizationTechnologyTable 1 }

CucsBiosVfIntelVirtualizationTechnologyEntry ::= SEQUENCE {
    cucsBiosVfIntelVirtualizationTechnologyInstanceId                CucsManagedObjectId,
    cucsBiosVfIntelVirtualizationTechnologyDn                        CucsManagedObjectDn,
    cucsBiosVfIntelVirtualizationTechnologyRn                        SnmpAdminString,
    cucsBiosVpIntelVirtualizationTechnology                          CucsBiosVpIntelVirtualizationTechnology,
    cucsBiosVfIntelVirtualizationTechnologyPropAcl                   Unsigned64,
    cucsBiosVfIntelVirtualizationTechnologySupportedByDefault        CucsBiosSupportedAction
}

cucsBiosVfIntelVirtualizationTechnologyInstanceId OBJECT-TYPE
    SYNTAX       CucsManagedObjectId
    MAX-ACCESS   not-accessible
    STATUS       current
    DESCRIPTION
        "Instance identifier of the managed object."
    ::= { cucsBiosVfIntelVirtualizationTechnologyEntry 1 }

cucsBiosVfIntelVirtualizationTechnologyDn OBJECT-TYPE
    SYNTAX       CucsManagedObjectDn
    MAX-ACCESS   read-only
    STATUS       current
    DESCRIPTION
        "Cisco UCS bios:VfIntelVirtualizationTechnology:dn
        managed object property"
    ::= { cucsBiosVfIntelVirtualizationTechnologyEntry 2 }

cucsBiosVfIntelVirtualizationTechnologyRn OBJECT-TYPE
    SYNTAX       SnmpAdminString
    MAX-ACCESS   read-only
    STATUS       current
    DESCRIPTION
        "Cisco UCS bios:VfIntelVirtualizationTechnology:rn
        managed object property"
    ::= { cucsBiosVfIntelVirtualizationTechnologyEntry 3 }

cucsBiosVpIntelVirtualizationTechnology OBJECT-TYPE
    SYNTAX       CucsBiosVpIntelVirtualizationTechnology
    MAX-ACCESS   read-only
    STATUS       current
    DESCRIPTION
        "Cisco UCS bios:VfIntelVirtualizationTechnology:vpIntelVirtualizat
        ionTechnology managed object property"
    ::= { cucsBiosVfIntelVirtualizationTechnologyEntry 4 }

cucsBiosVfIntelVirtualizationTechnologyPropAcl OBJECT-TYPE
    SYNTAX       Unsigned64
    MAX-ACCESS   read-only
    STATUS       current
    DESCRIPTION
        "Cisco UCS bios:VfIntelVirtualizationTechnology:propAcl
        managed object property"
    ::= { cucsBiosVfIntelVirtualizationTechnologyEntry 5 }

cucsBiosVfIntelVirtualizationTechnologySupportedByDefault OBJECT-TYPE
    SYNTAX       CucsBiosSupportedAction
    MAX-ACCESS   read-only
    STATUS       current
    DESCRIPTION
        "Cisco UCS bios:VfIntelVirtualizationTechnology:supportedByDefault
         managed object property"
    ::= { cucsBiosVfIntelVirtualizationTechnologyEntry 6 }

cucsBiosVfInterleaveConfigurationTable OBJECT-TYPE
    SYNTAX           SEQUENCE OF CucsBiosVfInterleaveConfigurationEntry
    MAX-ACCESS       not-accessible
    STATUS           current
    DESCRIPTION
        "Cisco UCS bios:VfInterleaveConfiguration managed object table"
    ::= { cucsBiosObjects 68 }

cucsBiosVfInterleaveConfigurationEntry OBJECT-TYPE
    SYNTAX           CucsBiosVfInterleaveConfigurationEntry
    MAX-ACCESS       not-accessible
    STATUS           current
    DESCRIPTION
        "Entry for the cucsBiosVfInterleaveConfigurationTable table."
    INDEX { cucsBiosVfInterleaveConfigurationInstanceId }
    ::= { cucsBiosVfInterleaveConfigurationTable 1 }

CucsBiosVfInterleaveConfigurationEntry ::= SEQUENCE {
    cucsBiosVfInterleaveConfigurationInstanceId                      CucsManagedObjectId,
    cucsBiosVfInterleaveConfigurationDn                              CucsManagedObjectDn,
    cucsBiosVfInterleaveConfigurationRn                              SnmpAdminString,
    cucsBiosVfInterleaveConfigurationVpChannelInterleaving           CucsBiosVfInterleaveConfigurationVpChannelInterleaving,
    cucsBiosVfInterleaveConfigurationVpMemoryInterleaving            CucsBiosVfInterleaveConfigurationVpMemoryInterleaving,
    cucsBiosVfInterleaveConfigurationVpRankInterleaving              CucsBiosVfInterleaveConfigurationVpRankInterleaving,
    cucsBiosVfInterleaveConfigurationPropAcl                         Unsigned64,
    cucsBiosVfInterleaveConfigurationSupportedByDefault              CucsBiosSupportedAction
}

cucsBiosVfInterleaveConfigurationInstanceId OBJECT-TYPE
    SYNTAX       CucsManagedObjectId
    MAX-ACCESS   not-accessible
    STATUS       current
    DESCRIPTION
        "Instance identifier of the managed object."
    ::= { cucsBiosVfInterleaveConfigurationEntry 1 }

cucsBiosVfInterleaveConfigurationDn OBJECT-TYPE
    SYNTAX       CucsManagedObjectDn
    MAX-ACCESS   read-only
    STATUS       current
    DESCRIPTION
        "Cisco UCS bios:VfInterleaveConfiguration:dn managed
        object property"
    ::= { cucsBiosVfInterleaveConfigurationEntry 2 }

cucsBiosVfInterleaveConfigurationRn OBJECT-TYPE
    SYNTAX       SnmpAdminString
    MAX-ACCESS   read-only
    STATUS       current
    DESCRIPTION
        "Cisco UCS bios:VfInterleaveConfiguration:rn managed
        object property"
    ::= { cucsBiosVfInterleaveConfigurationEntry 3 }

cucsBiosVfInterleaveConfigurationVpChannelInterleaving OBJECT-TYPE
    SYNTAX       CucsBiosVfInterleaveConfigurationVpChannelInterleaving
    MAX-ACCESS   read-only
    STATUS       current
    DESCRIPTION
        "Cisco UCS bios:VfInterleaveConfiguration:vpChannelInterleaving
        managed object property"
    ::= { cucsBiosVfInterleaveConfigurationEntry 4 }

cucsBiosVfInterleaveConfigurationVpMemoryInterleaving OBJECT-TYPE
    SYNTAX       CucsBiosVfInterleaveConfigurationVpMemoryInterleaving
    MAX-ACCESS   read-only
    STATUS       current
    DESCRIPTION
        "Cisco UCS bios:VfInterleaveConfiguration:vpMemoryInterleaving
        managed object property"
    ::= { cucsBiosVfInterleaveConfigurationEntry 5 }

cucsBiosVfInterleaveConfigurationVpRankInterleaving OBJECT-TYPE
    SYNTAX       CucsBiosVfInterleaveConfigurationVpRankInterleaving
    MAX-ACCESS   read-only
    STATUS       current
    DESCRIPTION
        "Cisco UCS bios:VfInterleaveConfiguration:vpRankInterleaving
        managed object property"
    ::= { cucsBiosVfInterleaveConfigurationEntry 6 }

cucsBiosVfInterleaveConfigurationPropAcl OBJECT-TYPE
    SYNTAX       Unsigned64
    MAX-ACCESS   read-only
    STATUS       current
    DESCRIPTION
        "Cisco UCS bios:VfInterleaveConfiguration:propAcl
        managed object property"
    ::= { cucsBiosVfInterleaveConfigurationEntry 7 }

cucsBiosVfInterleaveConfigurationSupportedByDefault OBJECT-TYPE
    SYNTAX       CucsBiosSupportedAction
    MAX-ACCESS   read-only
    STATUS       current
    DESCRIPTION
        "Cisco UCS bios:VfInterleaveConfiguration:supportedByDefault
        managed object property"
    ::= { cucsBiosVfInterleaveConfigurationEntry 8 }

cucsBiosVfLocalX2ApicTable OBJECT-TYPE
    SYNTAX           SEQUENCE OF CucsBiosVfLocalX2ApicEntry
    MAX-ACCESS       not-accessible
    STATUS           current
    DESCRIPTION
        "Cisco UCS bios:VfLocalX2Apic managed object table"
    ::= { cucsBiosObjects 62 }

cucsBiosVfLocalX2ApicEntry OBJECT-TYPE
    SYNTAX           CucsBiosVfLocalX2ApicEntry
    MAX-ACCESS       not-accessible
    STATUS           current
    DESCRIPTION
        "Entry for the cucsBiosVfLocalX2ApicTable table."
    INDEX { cucsBiosVfLocalX2ApicInstanceId }
    ::= { cucsBiosVfLocalX2ApicTable 1 }

CucsBiosVfLocalX2ApicEntry ::= SEQUENCE {
    cucsBiosVfLocalX2ApicInstanceId                                  CucsManagedObjectId,
    cucsBiosVfLocalX2ApicDn                                          CucsManagedObjectDn,
    cucsBiosVfLocalX2ApicRn                                          SnmpAdminString,
    cucsBiosVfLocalX2ApicVpLocalX2Apic                               CucsBiosVfLocalX2ApicVpLocalX2Apic,
    cucsBiosVfLocalX2ApicPropAcl                                     Unsigned64,
    cucsBiosVfLocalX2ApicSupportedByDefault                          CucsBiosSupportedAction
}

cucsBiosVfLocalX2ApicInstanceId OBJECT-TYPE
    SYNTAX       CucsManagedObjectId
    MAX-ACCESS   not-accessible
    STATUS       current
    DESCRIPTION
        "Instance identifier of the managed object."
    ::= { cucsBiosVfLocalX2ApicEntry 1 }

cucsBiosVfLocalX2ApicDn OBJECT-TYPE
    SYNTAX       CucsManagedObjectDn
    MAX-ACCESS   read-only
    STATUS       current
    DESCRIPTION
        "Cisco UCS bios:VfLocalX2Apic:dn managed object property"
    ::= { cucsBiosVfLocalX2ApicEntry 2 }

cucsBiosVfLocalX2ApicRn OBJECT-TYPE
    SYNTAX       SnmpAdminString
    MAX-ACCESS   read-only
    STATUS       current
    DESCRIPTION
        "Cisco UCS bios:VfLocalX2Apic:rn managed object property"
    ::= { cucsBiosVfLocalX2ApicEntry 3 }

cucsBiosVfLocalX2ApicVpLocalX2Apic OBJECT-TYPE
    SYNTAX       CucsBiosVfLocalX2ApicVpLocalX2Apic
    MAX-ACCESS   read-only
    STATUS       current
    DESCRIPTION
        "Cisco UCS bios:VfLocalX2Apic:vpLocalX2Apic managed
        object property"
    ::= { cucsBiosVfLocalX2ApicEntry 4 }

cucsBiosVfLocalX2ApicPropAcl OBJECT-TYPE
    SYNTAX       Unsigned64
    MAX-ACCESS   read-only
    STATUS       current
    DESCRIPTION
        "Cisco UCS bios:VfLocalX2Apic:propAcl managed object property"
    ::= { cucsBiosVfLocalX2ApicEntry 5 }

cucsBiosVfLocalX2ApicSupportedByDefault OBJECT-TYPE
    SYNTAX       CucsBiosSupportedAction
    MAX-ACCESS   read-only
    STATUS       current
    DESCRIPTION
        "Cisco UCS bios:VfLocalX2Apic:supportedByDefault
        managed object property"
    ::= { cucsBiosVfLocalX2ApicEntry 6 }

cucsBiosVfLvDIMMSupportTable OBJECT-TYPE
    SYNTAX           SEQUENCE OF CucsBiosVfLvDIMMSupportEntry
    MAX-ACCESS       not-accessible
    STATUS           current
    DESCRIPTION
        "Cisco UCS bios:VfLvDIMMSupport managed object table"
    ::= { cucsBiosObjects 19 }

cucsBiosVfLvDIMMSupportEntry OBJECT-TYPE
    SYNTAX           CucsBiosVfLvDIMMSupportEntry
    MAX-ACCESS       not-accessible
    STATUS           current
    DESCRIPTION
        "Entry for the cucsBiosVfLvDIMMSupportTable table."
    INDEX { cucsBiosVfLvDIMMSupportInstanceId }
    ::= { cucsBiosVfLvDIMMSupportTable 1 }

CucsBiosVfLvDIMMSupportEntry ::= SEQUENCE {
    cucsBiosVfLvDIMMSupportInstanceId                                CucsManagedObjectId,
    cucsBiosVfLvDIMMSupportDn                                        CucsManagedObjectDn,
    cucsBiosVfLvDIMMSupportRn                                        SnmpAdminString,
    cucsBiosVfLvDIMMSupportVpLvDDRMode                               CucsBiosVfLvDIMMSupportVpLvDDRMode,
    cucsBiosVfLvDIMMSupportPropAcl                                   Unsigned64,
    cucsBiosVfLvDIMMSupportSupportedByDefault                        CucsBiosSupportedAction
}

cucsBiosVfLvDIMMSupportInstanceId OBJECT-TYPE
    SYNTAX       CucsManagedObjectId
    MAX-ACCESS   not-accessible
    STATUS       current
    DESCRIPTION
        "Instance identifier of the managed object."
    ::= { cucsBiosVfLvDIMMSupportEntry 1 }

cucsBiosVfLvDIMMSupportDn OBJECT-TYPE
    SYNTAX       CucsManagedObjectDn
    MAX-ACCESS   read-only
    STATUS       current
    DESCRIPTION
        "Cisco UCS bios:VfLvDIMMSupport:dn managed object property"
    ::= { cucsBiosVfLvDIMMSupportEntry 2 }

cucsBiosVfLvDIMMSupportRn OBJECT-TYPE
    SYNTAX       SnmpAdminString
    MAX-ACCESS   read-only
    STATUS       current
    DESCRIPTION
        "Cisco UCS bios:VfLvDIMMSupport:rn managed object property"
    ::= { cucsBiosVfLvDIMMSupportEntry 3 }

cucsBiosVfLvDIMMSupportVpLvDDRMode OBJECT-TYPE
    SYNTAX       CucsBiosVfLvDIMMSupportVpLvDDRMode
    MAX-ACCESS   read-only
    STATUS       current
    DESCRIPTION
        "Cisco UCS bios:VfLvDIMMSupport:vpLvDDRMode managed
        object property"
    ::= { cucsBiosVfLvDIMMSupportEntry 4 }

cucsBiosVfLvDIMMSupportPropAcl OBJECT-TYPE
    SYNTAX       Unsigned64
    MAX-ACCESS   read-only
    STATUS       current
    DESCRIPTION
        "Cisco UCS bios:VfLvDIMMSupport:propAcl managed object property"
    ::= { cucsBiosVfLvDIMMSupportEntry 5 }

cucsBiosVfLvDIMMSupportSupportedByDefault OBJECT-TYPE
    SYNTAX       CucsBiosSupportedAction
    MAX-ACCESS   read-only
    STATUS       current
    DESCRIPTION
        "Cisco UCS bios:VfLvDIMMSupport:supportedByDefault
        managed object property"
    ::= { cucsBiosVfLvDIMMSupportEntry 6 }

cucsBiosVfMaxVariableMTRRSettingTable OBJECT-TYPE
    SYNTAX           SEQUENCE OF CucsBiosVfMaxVariableMTRRSettingEntry
    MAX-ACCESS       not-accessible
    STATUS           current
    DESCRIPTION
        "Cisco UCS bios:VfMaxVariableMTRRSetting managed object table"
    ::= { cucsBiosObjects 47 }

cucsBiosVfMaxVariableMTRRSettingEntry OBJECT-TYPE
    SYNTAX           CucsBiosVfMaxVariableMTRRSettingEntry
    MAX-ACCESS       not-accessible
    STATUS           current
    DESCRIPTION
        "Entry for the cucsBiosVfMaxVariableMTRRSettingTable table."
    INDEX { cucsBiosVfMaxVariableMTRRSettingInstanceId }
    ::= { cucsBiosVfMaxVariableMTRRSettingTable 1 }

CucsBiosVfMaxVariableMTRRSettingEntry ::= SEQUENCE {
    cucsBiosVfMaxVariableMTRRSettingInstanceId                       CucsManagedObjectId,
    cucsBiosVfMaxVariableMTRRSettingDn                               CucsManagedObjectDn,
    cucsBiosVfMaxVariableMTRRSettingRn                               SnmpAdminString,
    cucsBiosVfMaxVariableMTRRSettingVpProcessorMtrr                  CucsBiosVfMaxVariableMTRRSettingVpProcessorMtrr,
    cucsBiosVfMaxVariableMTRRSettingPropAcl                          Unsigned64,
    cucsBiosVfMaxVariableMTRRSettingSupportedByDefault               CucsBiosSupportedAction
}

cucsBiosVfMaxVariableMTRRSettingInstanceId OBJECT-TYPE
    SYNTAX       CucsManagedObjectId
    MAX-ACCESS   not-accessible
    STATUS       current
    DESCRIPTION
        "Instance identifier of the managed object."
    ::= { cucsBiosVfMaxVariableMTRRSettingEntry 1 }

cucsBiosVfMaxVariableMTRRSettingDn OBJECT-TYPE
    SYNTAX       CucsManagedObjectDn
    MAX-ACCESS   read-only
    STATUS       current
    DESCRIPTION
        "Cisco UCS bios:VfMaxVariableMTRRSetting:dn managed
        object property"
    ::= { cucsBiosVfMaxVariableMTRRSettingEntry 2 }

cucsBiosVfMaxVariableMTRRSettingRn OBJECT-TYPE
    SYNTAX       SnmpAdminString
    MAX-ACCESS   read-only
    STATUS       current
    DESCRIPTION
        "Cisco UCS bios:VfMaxVariableMTRRSetting:rn managed
        object property"
    ::= { cucsBiosVfMaxVariableMTRRSettingEntry 3 }

cucsBiosVfMaxVariableMTRRSettingVpProcessorMtrr OBJECT-TYPE
    SYNTAX       CucsBiosVfMaxVariableMTRRSettingVpProcessorMtrr
    MAX-ACCESS   read-only
    STATUS       current
    DESCRIPTION
        "Cisco UCS bios:VfMaxVariableMTRRSetting:vpProcessorMtrr
        managed object property"
    ::= { cucsBiosVfMaxVariableMTRRSettingEntry 4 }

cucsBiosVfMaxVariableMTRRSettingPropAcl OBJECT-TYPE
    SYNTAX       Unsigned64
    MAX-ACCESS   read-only
    STATUS       current
    DESCRIPTION
        "Cisco UCS bios:VfMaxVariableMTRRSetting:propAcl
        managed object property"
    ::= { cucsBiosVfMaxVariableMTRRSettingEntry 5 }

cucsBiosVfMaxVariableMTRRSettingSupportedByDefault OBJECT-TYPE
    SYNTAX       CucsBiosSupportedAction
    MAX-ACCESS   read-only
    STATUS       current
    DESCRIPTION
        "Cisco UCS bios:VfMaxVariableMTRRSetting:supportedByDefault
        managed object property"
    ::= { cucsBiosVfMaxVariableMTRRSettingEntry 6 }

cucsBiosVfMaximumMemoryBelow4GBTable OBJECT-TYPE
    SYNTAX           SEQUENCE OF CucsBiosVfMaximumMemoryBelow4GBEntry
    MAX-ACCESS       not-accessible
    STATUS           current
    DESCRIPTION
        "Cisco UCS bios:VfMaximumMemoryBelow4GB managed object table"
    ::= { cucsBiosObjects 41 }

cucsBiosVfMaximumMemoryBelow4GBEntry OBJECT-TYPE
    SYNTAX           CucsBiosVfMaximumMemoryBelow4GBEntry
    MAX-ACCESS       not-accessible
    STATUS           current
    DESCRIPTION
        "Entry for the cucsBiosVfMaximumMemoryBelow4GBTable table."
    INDEX { cucsBiosVfMaximumMemoryBelow4GBInstanceId }
    ::= { cucsBiosVfMaximumMemoryBelow4GBTable 1 }

CucsBiosVfMaximumMemoryBelow4GBEntry ::= SEQUENCE {
    cucsBiosVfMaximumMemoryBelow4GBInstanceId                        CucsManagedObjectId,
    cucsBiosVfMaximumMemoryBelow4GBDn                                CucsManagedObjectDn,
    cucsBiosVfMaximumMemoryBelow4GBRn                                SnmpAdminString,
    cucsBiosVfMaximumMemoryBelow4GBVpMaximumMemoryBelow4GB           CucsBiosVfMaximumMemoryBelow4GBVpMaximumMemoryBelow4GB,
    cucsBiosVfMaximumMemoryBelow4GBPropAcl                           Unsigned64,
    cucsBiosVfMaximumMemoryBelow4GBSupportedByDefault                CucsBiosSupportedAction
}

cucsBiosVfMaximumMemoryBelow4GBInstanceId OBJECT-TYPE
    SYNTAX       CucsManagedObjectId
    MAX-ACCESS   not-accessible
    STATUS       current
    DESCRIPTION
        "Instance identifier of the managed object."
    ::= { cucsBiosVfMaximumMemoryBelow4GBEntry 1 }

cucsBiosVfMaximumMemoryBelow4GBDn OBJECT-TYPE
    SYNTAX       CucsManagedObjectDn
    MAX-ACCESS   read-only
    STATUS       current
    DESCRIPTION
        "Cisco UCS bios:VfMaximumMemoryBelow4GB:dn managed
        object property"
    ::= { cucsBiosVfMaximumMemoryBelow4GBEntry 2 }

cucsBiosVfMaximumMemoryBelow4GBRn OBJECT-TYPE
    SYNTAX       SnmpAdminString
    MAX-ACCESS   read-only
    STATUS       current
    DESCRIPTION
        "Cisco UCS bios:VfMaximumMemoryBelow4GB:rn managed
        object property"
    ::= { cucsBiosVfMaximumMemoryBelow4GBEntry 3 }

cucsBiosVfMaximumMemoryBelow4GBVpMaximumMemoryBelow4GB OBJECT-TYPE
    SYNTAX       CucsBiosVfMaximumMemoryBelow4GBVpMaximumMemoryBelow4GB
    MAX-ACCESS   read-only
    STATUS       current
    DESCRIPTION
        "Cisco UCS bios:VfMaximumMemoryBelow4GB:vpMaximumMemoryBelow4GB
        managed object property"
    ::= { cucsBiosVfMaximumMemoryBelow4GBEntry 4 }

cucsBiosVfMaximumMemoryBelow4GBPropAcl OBJECT-TYPE
    SYNTAX       Unsigned64
    MAX-ACCESS   read-only
    STATUS       current
    DESCRIPTION
        "Cisco UCS bios:VfMaximumMemoryBelow4GB:propAcl
        managed object property"
    ::= { cucsBiosVfMaximumMemoryBelow4GBEntry 5 }

cucsBiosVfMaximumMemoryBelow4GBSupportedByDefault OBJECT-TYPE
    SYNTAX       CucsBiosSupportedAction
    MAX-ACCESS   read-only
    STATUS       current
    DESCRIPTION
        "Cisco UCS bios:VfMaximumMemoryBelow4GB:supportedByDefault
        managed object property"
    ::= { cucsBiosVfMaximumMemoryBelow4GBEntry 6 }

cucsBiosVfMemoryMappedIOAbove4GBTable OBJECT-TYPE
    SYNTAX           SEQUENCE OF CucsBiosVfMemoryMappedIOAbove4GBEntry
    MAX-ACCESS       not-accessible
    STATUS           current
    DESCRIPTION
        "Cisco UCS bios:VfMemoryMappedIOAbove4GB managed object table"
    ::= { cucsBiosObjects 42 }

cucsBiosVfMemoryMappedIOAbove4GBEntry OBJECT-TYPE
    SYNTAX           CucsBiosVfMemoryMappedIOAbove4GBEntry
    MAX-ACCESS       not-accessible
    STATUS           current
    DESCRIPTION
        "Entry for the cucsBiosVfMemoryMappedIOAbove4GBTable table."
    INDEX { cucsBiosVfMemoryMappedIOAbove4GBInstanceId }
    ::= { cucsBiosVfMemoryMappedIOAbove4GBTable 1 }

CucsBiosVfMemoryMappedIOAbove4GBEntry ::= SEQUENCE {
    cucsBiosVfMemoryMappedIOAbove4GBInstanceId                       CucsManagedObjectId,
    cucsBiosVfMemoryMappedIOAbove4GBDn                               CucsManagedObjectDn,
    cucsBiosVfMemoryMappedIOAbove4GBRn                               SnmpAdminString,
    cucsBiosVfMemoryMappedIOAbove4GBVpMemoryMappedIOAbove4GB         CucsBiosVfMemoryMappedIOAbove4GBVpMemoryMappedIOAbove4GB,
    cucsBiosVfMemoryMappedIOAbove4GBPropAcl                          Unsigned64,
    cucsBiosVfMemoryMappedIOAbove4GBSupportedByDefault               CucsBiosSupportedAction
}

cucsBiosVfMemoryMappedIOAbove4GBInstanceId OBJECT-TYPE
    SYNTAX       CucsManagedObjectId
    MAX-ACCESS   not-accessible
    STATUS       current
    DESCRIPTION
        "Instance identifier of the managed object."
    ::= { cucsBiosVfMemoryMappedIOAbove4GBEntry 1 }

cucsBiosVfMemoryMappedIOAbove4GBDn OBJECT-TYPE
    SYNTAX       CucsManagedObjectDn
    MAX-ACCESS   read-only
    STATUS       current
    DESCRIPTION
        "Cisco UCS bios:VfMemoryMappedIOAbove4GB:dn managed
        object property"
    ::= { cucsBiosVfMemoryMappedIOAbove4GBEntry 2 }

cucsBiosVfMemoryMappedIOAbove4GBRn OBJECT-TYPE
    SYNTAX       SnmpAdminString
    MAX-ACCESS   read-only
    STATUS       current
    DESCRIPTION
        "Cisco UCS bios:VfMemoryMappedIOAbove4GB:rn managed
        object property"
    ::= { cucsBiosVfMemoryMappedIOAbove4GBEntry 3 }

cucsBiosVfMemoryMappedIOAbove4GBVpMemoryMappedIOAbove4GB OBJECT-TYPE
    SYNTAX       CucsBiosVfMemoryMappedIOAbove4GBVpMemoryMappedIOAbove4GB
    MAX-ACCESS   read-only
    STATUS       current
    DESCRIPTION
        "Cisco UCS bios:VfMemoryMappedIOAbove4GB:vpMemoryMappedIOAbove4GB
        managed object property"
    ::= { cucsBiosVfMemoryMappedIOAbove4GBEntry 4 }

cucsBiosVfMemoryMappedIOAbove4GBPropAcl OBJECT-TYPE
    SYNTAX       Unsigned64
    MAX-ACCESS   read-only
    STATUS       current
    DESCRIPTION
        "Cisco UCS bios:VfMemoryMappedIOAbove4GB:propAcl
        managed object property"
    ::= { cucsBiosVfMemoryMappedIOAbove4GBEntry 5 }

cucsBiosVfMemoryMappedIOAbove4GBSupportedByDefault OBJECT-TYPE
    SYNTAX       CucsBiosSupportedAction
    MAX-ACCESS   read-only
    STATUS       current
    DESCRIPTION
        "Cisco UCS bios:VfMemoryMappedIOAbove4GB:supportedByDefault
        managed object property"
    ::= { cucsBiosVfMemoryMappedIOAbove4GBEntry 6 }

cucsBiosVfMirroringModeTable OBJECT-TYPE
    SYNTAX           SEQUENCE OF CucsBiosVfMirroringModeEntry
    MAX-ACCESS       not-accessible
    STATUS           current
    DESCRIPTION
        "Cisco UCS bios:VfMirroringMode managed object table"
    ::= { cucsBiosObjects 20 }

cucsBiosVfMirroringModeEntry OBJECT-TYPE
    SYNTAX           CucsBiosVfMirroringModeEntry
    MAX-ACCESS       not-accessible
    STATUS           current
    DESCRIPTION
        "Entry for the cucsBiosVfMirroringModeTable table."
    INDEX { cucsBiosVfMirroringModeInstanceId }
    ::= { cucsBiosVfMirroringModeTable 1 }

CucsBiosVfMirroringModeEntry ::= SEQUENCE {
    cucsBiosVfMirroringModeInstanceId                                CucsManagedObjectId,
    cucsBiosVfMirroringModeDn                                        CucsManagedObjectDn,
    cucsBiosVfMirroringModeRn                                        SnmpAdminString,
    cucsBiosVfMirroringModeVpMirroringMode                           CucsBiosVfMirroringModeVpMirroringMode,
    cucsBiosVfMirroringModePropAcl                                   Unsigned64,
    cucsBiosVfMirroringModeSupportedByDefault                        CucsBiosSupportedAction
}

cucsBiosVfMirroringModeInstanceId OBJECT-TYPE
    SYNTAX       CucsManagedObjectId
    MAX-ACCESS   not-accessible
    STATUS       current
    DESCRIPTION
        "Instance identifier of the managed object."
    ::= { cucsBiosVfMirroringModeEntry 1 }

cucsBiosVfMirroringModeDn OBJECT-TYPE
    SYNTAX       CucsManagedObjectDn
    MAX-ACCESS   read-only
    STATUS       current
    DESCRIPTION
        "Cisco UCS bios:VfMirroringMode:dn managed object property"
    ::= { cucsBiosVfMirroringModeEntry 2 }

cucsBiosVfMirroringModeRn OBJECT-TYPE
    SYNTAX       SnmpAdminString
    MAX-ACCESS   read-only
    STATUS       current
    DESCRIPTION
        "Cisco UCS bios:VfMirroringMode:rn managed object property"
    ::= { cucsBiosVfMirroringModeEntry 3 }

cucsBiosVfMirroringModeVpMirroringMode OBJECT-TYPE
    SYNTAX       CucsBiosVfMirroringModeVpMirroringMode
    MAX-ACCESS   read-only
    STATUS       current
    DESCRIPTION
        "Cisco UCS bios:VfMirroringMode:vpMirroringMode
        managed object property"
    ::= { cucsBiosVfMirroringModeEntry 4 }

cucsBiosVfMirroringModePropAcl OBJECT-TYPE
    SYNTAX       Unsigned64
    MAX-ACCESS   read-only
    STATUS       current
    DESCRIPTION
        "Cisco UCS bios:VfMirroringMode:propAcl managed object property"
    ::= { cucsBiosVfMirroringModeEntry 5 }

cucsBiosVfMirroringModeSupportedByDefault OBJECT-TYPE
    SYNTAX       CucsBiosSupportedAction
    MAX-ACCESS   read-only
    STATUS       current
    DESCRIPTION
        "Cisco UCS bios:VfMirroringMode:supportedByDefault
        managed object property"
    ::= { cucsBiosVfMirroringModeEntry 6 }

cucsBiosVfNUMAOptimizedTable OBJECT-TYPE
    SYNTAX           SEQUENCE OF CucsBiosVfNUMAOptimizedEntry
    MAX-ACCESS       not-accessible
    STATUS           current
    DESCRIPTION
        "Cisco UCS bios:VfNUMAOptimized managed object table"
    ::= { cucsBiosObjects 21 }

cucsBiosVfNUMAOptimizedEntry OBJECT-TYPE
    SYNTAX           CucsBiosVfNUMAOptimizedEntry
    MAX-ACCESS       not-accessible
    STATUS           current
    DESCRIPTION
        "Entry for the cucsBiosVfNUMAOptimizedTable table."
    INDEX { cucsBiosVfNUMAOptimizedInstanceId }
    ::= { cucsBiosVfNUMAOptimizedTable 1 }

CucsBiosVfNUMAOptimizedEntry ::= SEQUENCE {
    cucsBiosVfNUMAOptimizedInstanceId                                CucsManagedObjectId,
    cucsBiosVfNUMAOptimizedDn                                        CucsManagedObjectDn,
    cucsBiosVfNUMAOptimizedRn                                        SnmpAdminString,
    cucsBiosVfNUMAOptimizedVpNUMAOptimized                           CucsBiosVfNUMAOptimizedVpNUMAOptimized,
    cucsBiosVfNUMAOptimizedPropAcl                                   Unsigned64,
    cucsBiosVfNUMAOptimizedSupportedByDefault                        CucsBiosSupportedAction
}

cucsBiosVfNUMAOptimizedInstanceId OBJECT-TYPE
    SYNTAX       CucsManagedObjectId
    MAX-ACCESS   not-accessible
    STATUS       current
    DESCRIPTION
        "Instance identifier of the managed object."
    ::= { cucsBiosVfNUMAOptimizedEntry 1 }

cucsBiosVfNUMAOptimizedDn OBJECT-TYPE
    SYNTAX       CucsManagedObjectDn
    MAX-ACCESS   read-only
    STATUS       current
    DESCRIPTION
        "Cisco UCS bios:VfNUMAOptimized:dn managed object property"
    ::= { cucsBiosVfNUMAOptimizedEntry 2 }

cucsBiosVfNUMAOptimizedRn OBJECT-TYPE
    SYNTAX       SnmpAdminString
    MAX-ACCESS   read-only
    STATUS       current
    DESCRIPTION
        "Cisco UCS bios:VfNUMAOptimized:rn managed object property"
    ::= { cucsBiosVfNUMAOptimizedEntry 3 }

cucsBiosVfNUMAOptimizedVpNUMAOptimized OBJECT-TYPE
    SYNTAX       CucsBiosVfNUMAOptimizedVpNUMAOptimized
    MAX-ACCESS   read-only
    STATUS       current
    DESCRIPTION
        "Cisco UCS bios:VfNUMAOptimized:vpNUMAOptimized
        managed object property"
    ::= { cucsBiosVfNUMAOptimizedEntry 4 }

cucsBiosVfNUMAOptimizedPropAcl OBJECT-TYPE
    SYNTAX       Unsigned64
    MAX-ACCESS   read-only
    STATUS       current
    DESCRIPTION
        "Cisco UCS bios:VfNUMAOptimized:propAcl managed object property"
    ::= { cucsBiosVfNUMAOptimizedEntry 5 }

cucsBiosVfNUMAOptimizedSupportedByDefault OBJECT-TYPE
    SYNTAX       CucsBiosSupportedAction
    MAX-ACCESS   read-only
    STATUS       current
    DESCRIPTION
        "Cisco UCS bios:VfNUMAOptimized:supportedByDefault
        managed object property"
    ::= { cucsBiosVfNUMAOptimizedEntry 6 }

cucsBiosVfOSBootWatchdogTimerTable OBJECT-TYPE
    SYNTAX           SEQUENCE OF CucsBiosVfOSBootWatchdogTimerEntry
    MAX-ACCESS       not-accessible
    STATUS           current
    DESCRIPTION
        "Cisco UCS bios:VfOSBootWatchdogTimer managed object table"
    ::= { cucsBiosObjects 43 }

cucsBiosVfOSBootWatchdogTimerEntry OBJECT-TYPE
    SYNTAX           CucsBiosVfOSBootWatchdogTimerEntry
    MAX-ACCESS       not-accessible
    STATUS           current
    DESCRIPTION
        "Entry for the cucsBiosVfOSBootWatchdogTimerTable table."
    INDEX { cucsBiosVfOSBootWatchdogTimerInstanceId }
    ::= { cucsBiosVfOSBootWatchdogTimerTable 1 }

CucsBiosVfOSBootWatchdogTimerEntry ::= SEQUENCE {
    cucsBiosVfOSBootWatchdogTimerInstanceId                          CucsManagedObjectId,
    cucsBiosVfOSBootWatchdogTimerDn                                  CucsManagedObjectDn,
    cucsBiosVfOSBootWatchdogTimerRn                                  SnmpAdminString,
    cucsBiosVfOSBootWatchdogTimerVpOSBootWatchdogTimer               CucsBiosVfOSBootWatchdogTimerVpOSBootWatchdogTimer,
    cucsBiosVfOSBootWatchdogTimerPropAcl                             Unsigned64,
    cucsBiosVfOSBootWatchdogTimerSupportedByDefault                  CucsBiosSupportedAction
}

cucsBiosVfOSBootWatchdogTimerInstanceId OBJECT-TYPE
    SYNTAX       CucsManagedObjectId
    MAX-ACCESS   not-accessible
    STATUS       current
    DESCRIPTION
        "Instance identifier of the managed object."
    ::= { cucsBiosVfOSBootWatchdogTimerEntry 1 }

cucsBiosVfOSBootWatchdogTimerDn OBJECT-TYPE
    SYNTAX       CucsManagedObjectDn
    MAX-ACCESS   read-only
    STATUS       current
    DESCRIPTION
        "Cisco UCS bios:VfOSBootWatchdogTimer:dn managed object property"
    ::= { cucsBiosVfOSBootWatchdogTimerEntry 2 }

cucsBiosVfOSBootWatchdogTimerRn OBJECT-TYPE
    SYNTAX       SnmpAdminString
    MAX-ACCESS   read-only
    STATUS       current
    DESCRIPTION
        "Cisco UCS bios:VfOSBootWatchdogTimer:rn managed object property"
    ::= { cucsBiosVfOSBootWatchdogTimerEntry 3 }

cucsBiosVfOSBootWatchdogTimerVpOSBootWatchdogTimer OBJECT-TYPE
    SYNTAX       CucsBiosVfOSBootWatchdogTimerVpOSBootWatchdogTimer
    MAX-ACCESS   read-only
    STATUS       current
    DESCRIPTION
        "Cisco UCS bios:VfOSBootWatchdogTimer:vpOSBootWatchdogTimer
        managed object property"
    ::= { cucsBiosVfOSBootWatchdogTimerEntry 4 }

cucsBiosVfOSBootWatchdogTimerPropAcl OBJECT-TYPE
    SYNTAX       Unsigned64
    MAX-ACCESS   read-only
    STATUS       current
    DESCRIPTION
        "Cisco UCS bios:VfOSBootWatchdogTimer:propAcl managed
        object property"
    ::= { cucsBiosVfOSBootWatchdogTimerEntry 5 }

cucsBiosVfOSBootWatchdogTimerSupportedByDefault OBJECT-TYPE
    SYNTAX       CucsBiosSupportedAction
    MAX-ACCESS   read-only
    STATUS       current
    DESCRIPTION
        "Cisco UCS bios:VfOSBootWatchdogTimer:supportedByDefault
        managed object property"
    ::= { cucsBiosVfOSBootWatchdogTimerEntry 6 }

cucsBiosVfOSBootWatchdogTimerPolicyTable OBJECT-TYPE
    SYNTAX           SEQUENCE OF CucsBiosVfOSBootWatchdogTimerPolicyEntry
    MAX-ACCESS       not-accessible
    STATUS           current
    DESCRIPTION
        "Cisco UCS bios:VfOSBootWatchdogTimerPolicy managed object table"
    ::= { cucsBiosObjects 44 }

cucsBiosVfOSBootWatchdogTimerPolicyEntry OBJECT-TYPE
    SYNTAX           CucsBiosVfOSBootWatchdogTimerPolicyEntry
    MAX-ACCESS       not-accessible
    STATUS           current
    DESCRIPTION
        "Entry for the cucsBiosVfOSBootWatchdogTimerPolicyTable table."
    INDEX { cucsBiosVfOSBootWatchdogTimerPolicyInstanceId }
    ::= { cucsBiosVfOSBootWatchdogTimerPolicyTable 1 }

CucsBiosVfOSBootWatchdogTimerPolicyEntry ::= SEQUENCE {
    cucsBiosVfOSBootWatchdogTimerPolicyInstanceId                    CucsManagedObjectId,
    cucsBiosVfOSBootWatchdogTimerPolicyDn                            CucsManagedObjectDn,
    cucsBiosVfOSBootWatchdogTimerPolicyRn                            SnmpAdminString,
    cucsBiosVfOSBootWatchdogTimerPolicyVpOSBootWatchdogTimerPolicy   CucsBiosVfOSBootWatchdogTimerPolicyVpOSBootWatchdogTimerPolicy,
    cucsBiosVfOSBootWatchdogTimerPolicyPropAcl                       Unsigned64,
    cucsBiosVfOSBootWatchdogTimerPolicySupportedByDefault            CucsBiosSupportedAction
}

cucsBiosVfOSBootWatchdogTimerPolicyInstanceId OBJECT-TYPE
    SYNTAX       CucsManagedObjectId
    MAX-ACCESS   not-accessible
    STATUS       current
    DESCRIPTION
        "Instance identifier of the managed object."
    ::= { cucsBiosVfOSBootWatchdogTimerPolicyEntry 1 }

cucsBiosVfOSBootWatchdogTimerPolicyDn OBJECT-TYPE
    SYNTAX       CucsManagedObjectDn
    MAX-ACCESS   read-only
    STATUS       current
    DESCRIPTION
        "Cisco UCS bios:VfOSBootWatchdogTimerPolicy:dn
        managed object property"
    ::= { cucsBiosVfOSBootWatchdogTimerPolicyEntry 2 }

cucsBiosVfOSBootWatchdogTimerPolicyRn OBJECT-TYPE
    SYNTAX       SnmpAdminString
    MAX-ACCESS   read-only
    STATUS       current
    DESCRIPTION
        "Cisco UCS bios:VfOSBootWatchdogTimerPolicy:rn
        managed object property"
    ::= { cucsBiosVfOSBootWatchdogTimerPolicyEntry 3 }

cucsBiosVfOSBootWatchdogTimerPolicyVpOSBootWatchdogTimerPolicy OBJECT-TYPE
    SYNTAX       CucsBiosVfOSBootWatchdogTimerPolicyVpOSBootWatchdogTimerPolicy
    MAX-ACCESS   read-only
    STATUS       current
    DESCRIPTION
        "Cisco UCS bios:VfOSBootWatchdogTimerPolicy:vpOSBootWatchdogTimerP
        olicy managed object property"
    ::= { cucsBiosVfOSBootWatchdogTimerPolicyEntry 4 }

cucsBiosVfOSBootWatchdogTimerPolicyPropAcl OBJECT-TYPE
    SYNTAX       Unsigned64
    MAX-ACCESS   read-only
    STATUS       current
    DESCRIPTION
        "Cisco UCS bios:VfOSBootWatchdogTimerPolicy:propAcl
        managed object property"
    ::= { cucsBiosVfOSBootWatchdogTimerPolicyEntry 5 }

cucsBiosVfOSBootWatchdogTimerPolicySupportedByDefault OBJECT-TYPE
    SYNTAX       CucsBiosSupportedAction
    MAX-ACCESS   read-only
    STATUS       current
    DESCRIPTION
        "Cisco UCS bios:VfOSBootWatchdogTimerPolicy:supportedByDefault
        managed object property"
    ::= { cucsBiosVfOSBootWatchdogTimerPolicyEntry 6 }

cucsBiosVfOSBootWatchdogTimerTimeoutTable OBJECT-TYPE
    SYNTAX           SEQUENCE OF CucsBiosVfOSBootWatchdogTimerTimeoutEntry
    MAX-ACCESS       not-accessible
    STATUS           current
    DESCRIPTION
        "Cisco UCS bios:VfOSBootWatchdogTimerTimeout managed object table"
    ::= { cucsBiosObjects 52 }

cucsBiosVfOSBootWatchdogTimerTimeoutEntry OBJECT-TYPE
    SYNTAX           CucsBiosVfOSBootWatchdogTimerTimeoutEntry
    MAX-ACCESS       not-accessible
    STATUS           current
    DESCRIPTION
        "Entry for the cucsBiosVfOSBootWatchdogTimerTimeoutTable table."
    INDEX { cucsBiosVfOSBootWatchdogTimerTimeoutInstanceId }
    ::= { cucsBiosVfOSBootWatchdogTimerTimeoutTable 1 }

CucsBiosVfOSBootWatchdogTimerTimeoutEntry ::= SEQUENCE {
    cucsBiosVfOSBootWatchdogTimerTimeoutInstanceId                   CucsManagedObjectId,
    cucsBiosVfOSBootWatchdogTimerTimeoutDn                           CucsManagedObjectDn,
    cucsBiosVfOSBootWatchdogTimerTimeoutRn                           SnmpAdminString,
    cucsBiosVfOSBootWatchdogTimerTimeoutVpOSBootWatchdogTimerTimeout CucsBiosVfOSBootWatchdogTimerTimeoutVpOSBootWatchdogTimerTimeout,
    cucsBiosVfOSBootWatchdogTimerTimeoutPropAcl                      Unsigned64,
    cucsBiosVfOSBootWatchdogTimerTimeoutSupportedByDefault           CucsBiosSupportedAction
}

cucsBiosVfOSBootWatchdogTimerTimeoutInstanceId OBJECT-TYPE
    SYNTAX       CucsManagedObjectId
    MAX-ACCESS   not-accessible
    STATUS       current
    DESCRIPTION
        "Instance identifier of the managed object."
    ::= { cucsBiosVfOSBootWatchdogTimerTimeoutEntry 1 }

cucsBiosVfOSBootWatchdogTimerTimeoutDn OBJECT-TYPE
    SYNTAX       CucsManagedObjectDn
    MAX-ACCESS   read-only
    STATUS       current
    DESCRIPTION
        "Cisco UCS bios:VfOSBootWatchdogTimerTimeout:dn
        managed object property"
    ::= { cucsBiosVfOSBootWatchdogTimerTimeoutEntry 2 }

cucsBiosVfOSBootWatchdogTimerTimeoutRn OBJECT-TYPE
    SYNTAX       SnmpAdminString
    MAX-ACCESS   read-only
    STATUS       current
    DESCRIPTION
        "Cisco UCS bios:VfOSBootWatchdogTimerTimeout:rn
        managed object property"
    ::= { cucsBiosVfOSBootWatchdogTimerTimeoutEntry 3 }

cucsBiosVfOSBootWatchdogTimerTimeoutVpOSBootWatchdogTimerTimeout OBJECT-TYPE
    SYNTAX       CucsBiosVfOSBootWatchdogTimerTimeoutVpOSBootWatchdogTimerTimeout
    MAX-ACCESS   read-only
    STATUS       current
    DESCRIPTION
        "Cisco UCS bios:VfOSBootWatchdogTimerTimeout:vpOSBootWatchdogTimer
        Timeout managed object property"
    ::= { cucsBiosVfOSBootWatchdogTimerTimeoutEntry 4 }

cucsBiosVfOSBootWatchdogTimerTimeoutPropAcl OBJECT-TYPE
    SYNTAX       Unsigned64
    MAX-ACCESS   read-only
    STATUS       current
    DESCRIPTION
        "Cisco UCS bios:VfOSBootWatchdogTimerTimeout:propAcl
        managed object property"
    ::= { cucsBiosVfOSBootWatchdogTimerTimeoutEntry 5 }

cucsBiosVfOSBootWatchdogTimerTimeoutSupportedByDefault OBJECT-TYPE
    SYNTAX       CucsBiosSupportedAction
    MAX-ACCESS   read-only
    STATUS       current
    DESCRIPTION
        "Cisco UCS bios:VfOSBootWatchdogTimerTimeout:supportedByDefault
        managed object property"
    ::= { cucsBiosVfOSBootWatchdogTimerTimeoutEntry 6 }

cucsBiosVfOnboardGraphicsTable OBJECT-TYPE
    SYNTAX           SEQUENCE OF CucsBiosVfOnboardGraphicsEntry
    MAX-ACCESS       not-accessible
    STATUS           current
    DESCRIPTION
        "Cisco UCS bios:VfOnboardGraphics managed object table"
    ::= { cucsBiosObjects 95 }

cucsBiosVfOnboardGraphicsEntry OBJECT-TYPE
    SYNTAX           CucsBiosVfOnboardGraphicsEntry
    MAX-ACCESS       not-accessible
    STATUS           current
    DESCRIPTION
        "Entry for the cucsBiosVfOnboardGraphicsTable table."
    INDEX { cucsBiosVfOnboardGraphicsInstanceId }
    ::= { cucsBiosVfOnboardGraphicsTable 1 }

CucsBiosVfOnboardGraphicsEntry ::= SEQUENCE {
    cucsBiosVfOnboardGraphicsInstanceId                              CucsManagedObjectId,
    cucsBiosVfOnboardGraphicsDn                                      CucsManagedObjectDn,
    cucsBiosVfOnboardGraphicsRn                                      SnmpAdminString,
    cucsBiosVfOnboardGraphicsSupportedByDefault                      CucsBiosSupportedAction,
    cucsBiosVfOnboardGraphicsVpOnboardGraphics                       CucsBiosVfOnboardGraphicsVpOnboardGraphics,
    cucsBiosVfOnboardGraphicsPropAcl                                 Unsigned64
}

cucsBiosVfOnboardGraphicsInstanceId OBJECT-TYPE
    SYNTAX       CucsManagedObjectId
    MAX-ACCESS   not-accessible
    STATUS       current
    DESCRIPTION
        "Instance identifier of the managed object."
    ::= { cucsBiosVfOnboardGraphicsEntry 1 }

cucsBiosVfOnboardGraphicsDn OBJECT-TYPE
    SYNTAX       CucsManagedObjectDn
    MAX-ACCESS   read-only
    STATUS       current
    DESCRIPTION
        "Cisco UCS bios:VfOnboardGraphics:dn managed object property"
    ::= { cucsBiosVfOnboardGraphicsEntry 2 }

cucsBiosVfOnboardGraphicsRn OBJECT-TYPE
    SYNTAX       SnmpAdminString
    MAX-ACCESS   read-only
    STATUS       current
    DESCRIPTION
        "Cisco UCS bios:VfOnboardGraphics:rn managed object property"
    ::= { cucsBiosVfOnboardGraphicsEntry 3 }

cucsBiosVfOnboardGraphicsSupportedByDefault OBJECT-TYPE
    SYNTAX       CucsBiosSupportedAction
    MAX-ACCESS   read-only
    STATUS       current
    DESCRIPTION
        "Cisco UCS bios:VfOnboardGraphics:supportedByDefault
        managed object property"
    ::= { cucsBiosVfOnboardGraphicsEntry 4 }

cucsBiosVfOnboardGraphicsVpOnboardGraphics OBJECT-TYPE
    SYNTAX       CucsBiosVfOnboardGraphicsVpOnboardGraphics
    MAX-ACCESS   read-only
    STATUS       current
    DESCRIPTION
        "Cisco UCS bios:VfOnboardGraphics:vpOnboardGraphics
        managed object property"
    ::= { cucsBiosVfOnboardGraphicsEntry 5 }

cucsBiosVfOnboardGraphicsPropAcl OBJECT-TYPE
    SYNTAX       Unsigned64
    MAX-ACCESS   read-only
    STATUS       current
    DESCRIPTION
        "Cisco UCS bios:VfOnboardGraphics:propAcl managed object property"
    ::= { cucsBiosVfOnboardGraphicsEntry 6 }

cucsBiosVfOnboardSATAControllerTable OBJECT-TYPE
    SYNTAX           SEQUENCE OF CucsBiosVfOnboardSATAControllerEntry
    MAX-ACCESS       not-accessible
    STATUS           current
    DESCRIPTION
        "Cisco UCS bios:VfOnboardSATAController managed object table"
    ::= { cucsBiosObjects 46 }

cucsBiosVfOnboardSATAControllerEntry OBJECT-TYPE
    SYNTAX           CucsBiosVfOnboardSATAControllerEntry
    MAX-ACCESS       not-accessible
    STATUS           current
    DESCRIPTION
        "Entry for the cucsBiosVfOnboardSATAControllerTable table."
    INDEX { cucsBiosVfOnboardSATAControllerInstanceId }
    ::= { cucsBiosVfOnboardSATAControllerTable 1 }

CucsBiosVfOnboardSATAControllerEntry ::= SEQUENCE {
    cucsBiosVfOnboardSATAControllerInstanceId                        CucsManagedObjectId,
    cucsBiosVfOnboardSATAControllerDn                                CucsManagedObjectDn,
    cucsBiosVfOnboardSATAControllerRn                                SnmpAdminString,
    cucsBiosVfOnboardSATAControllerVpOnboardSATAController           CucsBiosVfOnboardSATAControllerVpOnboardSATAController,
    cucsBiosVfOnboardSATAControllerVpSATAMode                        CucsBiosVfOnboardSATAControllerVpSATAMode,
    cucsBiosVfOnboardSATAControllerPropAcl                           Unsigned64,
    cucsBiosVfOnboardSATAControllerSupportedByDefault                CucsBiosSupportedAction
}

cucsBiosVfOnboardSATAControllerInstanceId OBJECT-TYPE
    SYNTAX       CucsManagedObjectId
    MAX-ACCESS   not-accessible
    STATUS       current
    DESCRIPTION
        "Instance identifier of the managed object."
    ::= { cucsBiosVfOnboardSATAControllerEntry 1 }

cucsBiosVfOnboardSATAControllerDn OBJECT-TYPE
    SYNTAX       CucsManagedObjectDn
    MAX-ACCESS   read-only
    STATUS       current
    DESCRIPTION
        "Cisco UCS bios:VfOnboardSATAController:dn managed
        object property"
    ::= { cucsBiosVfOnboardSATAControllerEntry 2 }

cucsBiosVfOnboardSATAControllerRn OBJECT-TYPE
    SYNTAX       SnmpAdminString
    MAX-ACCESS   read-only
    STATUS       current
    DESCRIPTION
        "Cisco UCS bios:VfOnboardSATAController:rn managed
        object property"
    ::= { cucsBiosVfOnboardSATAControllerEntry 3 }

cucsBiosVfOnboardSATAControllerVpOnboardSATAController OBJECT-TYPE
    SYNTAX       CucsBiosVfOnboardSATAControllerVpOnboardSATAController
    MAX-ACCESS   read-only
    STATUS       current
    DESCRIPTION
        "Cisco UCS bios:VfOnboardSATAController:vpOnboardSATAController
        managed object property"
    ::= { cucsBiosVfOnboardSATAControllerEntry 4 }

cucsBiosVfOnboardSATAControllerVpSATAMode OBJECT-TYPE
    SYNTAX       CucsBiosVfOnboardSATAControllerVpSATAMode
    MAX-ACCESS   read-only
    STATUS       current
    DESCRIPTION
        "Cisco UCS bios:VfOnboardSATAController:vpSATAMode
        managed object property"
    ::= { cucsBiosVfOnboardSATAControllerEntry 5 }

cucsBiosVfOnboardSATAControllerPropAcl OBJECT-TYPE
    SYNTAX       Unsigned64
    MAX-ACCESS   read-only
    STATUS       current
    DESCRIPTION
        "Cisco UCS bios:VfOnboardSATAController:propAcl
        managed object property"
    ::= { cucsBiosVfOnboardSATAControllerEntry 6 }

cucsBiosVfOnboardSATAControllerSupportedByDefault OBJECT-TYPE
    SYNTAX       CucsBiosSupportedAction
    MAX-ACCESS   read-only
    STATUS       current
    DESCRIPTION
        "Cisco UCS bios:VfOnboardSATAController:supportedByDefault
        managed object property"
    ::= { cucsBiosVfOnboardSATAControllerEntry 7 }

cucsBiosVfOnboardStorageTable OBJECT-TYPE
    SYNTAX           SEQUENCE OF CucsBiosVfOnboardStorageEntry
    MAX-ACCESS       not-accessible
    STATUS           current
    DESCRIPTION
        "Cisco UCS bios:VfOnboardStorage managed object table"
    ::= { cucsBiosObjects 53 }

cucsBiosVfOnboardStorageEntry OBJECT-TYPE
    SYNTAX           CucsBiosVfOnboardStorageEntry
    MAX-ACCESS       not-accessible
    STATUS           current
    DESCRIPTION
        "Entry for the cucsBiosVfOnboardStorageTable table."
    INDEX { cucsBiosVfOnboardStorageInstanceId }
    ::= { cucsBiosVfOnboardStorageTable 1 }

CucsBiosVfOnboardStorageEntry ::= SEQUENCE {
    cucsBiosVfOnboardStorageInstanceId                               CucsManagedObjectId,
    cucsBiosVfOnboardStorageDn                                       CucsManagedObjectDn,
    cucsBiosVfOnboardStorageRn                                       SnmpAdminString,
    cucsBiosVfOnboardStorageVpOnboardSCUStorageSupport               CucsBiosVfOnboardStorageVpOnboardSCUStorageSupport,
    cucsBiosVfOnboardStoragePropAcl                                  Unsigned64,
    cucsBiosVfOnboardStorageSupportedByDefault                       CucsBiosSupportedAction
}

cucsBiosVfOnboardStorageInstanceId OBJECT-TYPE
    SYNTAX       CucsManagedObjectId
    MAX-ACCESS   not-accessible
    STATUS       current
    DESCRIPTION
        "Instance identifier of the managed object."
    ::= { cucsBiosVfOnboardStorageEntry 1 }

cucsBiosVfOnboardStorageDn OBJECT-TYPE
    SYNTAX       CucsManagedObjectDn
    MAX-ACCESS   read-only
    STATUS       current
    DESCRIPTION
        "Cisco UCS bios:VfOnboardStorage:dn managed object property"
    ::= { cucsBiosVfOnboardStorageEntry 2 }

cucsBiosVfOnboardStorageRn OBJECT-TYPE
    SYNTAX       SnmpAdminString
    MAX-ACCESS   read-only
    STATUS       current
    DESCRIPTION
        "Cisco UCS bios:VfOnboardStorage:rn managed object property"
    ::= { cucsBiosVfOnboardStorageEntry 3 }

cucsBiosVfOnboardStorageVpOnboardSCUStorageSupport OBJECT-TYPE
    SYNTAX       CucsBiosVfOnboardStorageVpOnboardSCUStorageSupport
    MAX-ACCESS   read-only
    STATUS       current
    DESCRIPTION
        "Cisco UCS bios:VfOnboardStorage:vpOnboardSCUStorageSupport
        managed object property"
    ::= { cucsBiosVfOnboardStorageEntry 4 }

cucsBiosVfOnboardStoragePropAcl OBJECT-TYPE
    SYNTAX       Unsigned64
    MAX-ACCESS   read-only
    STATUS       current
    DESCRIPTION
        "Cisco UCS bios:VfOnboardStorage:propAcl managed object property"
    ::= { cucsBiosVfOnboardStorageEntry 5 }

cucsBiosVfOnboardStorageSupportedByDefault OBJECT-TYPE
    SYNTAX       CucsBiosSupportedAction
    MAX-ACCESS   read-only
    STATUS       current
    DESCRIPTION
        "Cisco UCS bios:VfOnboardStorage:supportedByDefault
        managed object property"
    ::= { cucsBiosVfOnboardStorageEntry 6 }

cucsBiosVfOptionROMEnableTable OBJECT-TYPE
    SYNTAX           SEQUENCE OF CucsBiosVfOptionROMEnableEntry
    MAX-ACCESS       not-accessible
    STATUS           current
    DESCRIPTION
        "Cisco UCS bios:VfOptionROMEnable managed object table"
    ::= { cucsBiosObjects 54 }

cucsBiosVfOptionROMEnableEntry OBJECT-TYPE
    SYNTAX           CucsBiosVfOptionROMEnableEntry
    MAX-ACCESS       not-accessible
    STATUS           current
    DESCRIPTION
        "Entry for the cucsBiosVfOptionROMEnableTable table."
    INDEX { cucsBiosVfOptionROMEnableInstanceId }
    ::= { cucsBiosVfOptionROMEnableTable 1 }

CucsBiosVfOptionROMEnableEntry ::= SEQUENCE {
    cucsBiosVfOptionROMEnableInstanceId                              CucsManagedObjectId,
    cucsBiosVfOptionROMEnableDn                                      CucsManagedObjectDn,
    cucsBiosVfOptionROMEnableRn                                      SnmpAdminString,
    cucsBiosVfOptionROMEnableVpState                                 CucsBiosVfOptionROMEnableVpState,
    cucsBiosVfOptionROMEnablePropAcl                                 Unsigned64,
    cucsBiosVfOptionROMEnableSupportedByDefault                      CucsBiosSupportedAction
}

cucsBiosVfOptionROMEnableInstanceId OBJECT-TYPE
    SYNTAX       CucsManagedObjectId
    MAX-ACCESS   not-accessible
    STATUS       current
    DESCRIPTION
        "Instance identifier of the managed object."
    ::= { cucsBiosVfOptionROMEnableEntry 1 }

cucsBiosVfOptionROMEnableDn OBJECT-TYPE
    SYNTAX       CucsManagedObjectDn
    MAX-ACCESS   read-only
    STATUS       current
    DESCRIPTION
        "Cisco UCS bios:VfOptionROMEnable:dn managed object property"
    ::= { cucsBiosVfOptionROMEnableEntry 2 }

cucsBiosVfOptionROMEnableRn OBJECT-TYPE
    SYNTAX       SnmpAdminString
    MAX-ACCESS   read-only
    STATUS       current
    DESCRIPTION
        "Cisco UCS bios:VfOptionROMEnable:rn managed object property"
    ::= { cucsBiosVfOptionROMEnableEntry 3 }

cucsBiosVfOptionROMEnableVpState OBJECT-TYPE
    SYNTAX       CucsBiosVfOptionROMEnableVpState
    MAX-ACCESS   read-only
    STATUS       current
    DESCRIPTION
        "Cisco UCS bios:VfOptionROMEnable:vpState managed object property"
    ::= { cucsBiosVfOptionROMEnableEntry 4 }

cucsBiosVfOptionROMEnablePropAcl OBJECT-TYPE
    SYNTAX       Unsigned64
    MAX-ACCESS   read-only
    STATUS       current
    DESCRIPTION
        "Cisco UCS bios:VfOptionROMEnable:propAcl managed object property"
    ::= { cucsBiosVfOptionROMEnableEntry 5 }

cucsBiosVfOptionROMEnableSupportedByDefault OBJECT-TYPE
    SYNTAX       CucsBiosSupportedAction
    MAX-ACCESS   read-only
    STATUS       current
    DESCRIPTION
        "Cisco UCS bios:VfOptionROMEnable:supportedByDefault
        managed object property"
    ::= { cucsBiosVfOptionROMEnableEntry 6 }

cucsBiosVfOptionROMLoadTable OBJECT-TYPE
    SYNTAX           SEQUENCE OF CucsBiosVfOptionROMLoadEntry
    MAX-ACCESS       not-accessible
    STATUS           current
    DESCRIPTION
        "Cisco UCS bios:VfOptionROMLoad managed object table"
    ::= { cucsBiosObjects 12 }

cucsBiosVfOptionROMLoadEntry OBJECT-TYPE
    SYNTAX           CucsBiosVfOptionROMLoadEntry
    MAX-ACCESS       not-accessible
    STATUS           current
    DESCRIPTION
        "Entry for the cucsBiosVfOptionROMLoadTable table."
    INDEX { cucsBiosVfOptionROMLoadInstanceId }
    ::= { cucsBiosVfOptionROMLoadTable 1 }

CucsBiosVfOptionROMLoadEntry ::= SEQUENCE {
    cucsBiosVfOptionROMLoadInstanceId                                CucsManagedObjectId,
    cucsBiosVfOptionROMLoadDn                                        CucsManagedObjectDn,
    cucsBiosVfOptionROMLoadRn                                        SnmpAdminString,
    cucsBiosVfOptionROMLoadVpLoad                                    CucsBiosVfOptionROMLoadVpLoad,
    cucsBiosVfOptionROMLoadPropAcl                                   Unsigned64,
    cucsBiosVfOptionROMLoadSupportedByDefault                        CucsBiosSupportedAction
}

cucsBiosVfOptionROMLoadInstanceId OBJECT-TYPE
    SYNTAX       CucsManagedObjectId
    MAX-ACCESS   not-accessible
    STATUS       current
    DESCRIPTION
        "Instance identifier of the managed object."
    ::= { cucsBiosVfOptionROMLoadEntry 1 }

cucsBiosVfOptionROMLoadDn OBJECT-TYPE
    SYNTAX       CucsManagedObjectDn
    MAX-ACCESS   read-only
    STATUS       current
    DESCRIPTION
        "Cisco UCS bios:VfOptionROMLoad:dn managed object property"
    ::= { cucsBiosVfOptionROMLoadEntry 2 }

cucsBiosVfOptionROMLoadRn OBJECT-TYPE
    SYNTAX       SnmpAdminString
    MAX-ACCESS   read-only
    STATUS       current
    DESCRIPTION
        "Cisco UCS bios:VfOptionROMLoad:rn managed object property"
    ::= { cucsBiosVfOptionROMLoadEntry 3 }

cucsBiosVfOptionROMLoadVpLoad OBJECT-TYPE
    SYNTAX       CucsBiosVfOptionROMLoadVpLoad
    MAX-ACCESS   read-only
    STATUS       current
    DESCRIPTION
        "Cisco UCS bios:VfOptionROMLoad:vpLoad managed object property"
    ::= { cucsBiosVfOptionROMLoadEntry 4 }

cucsBiosVfOptionROMLoadPropAcl OBJECT-TYPE
    SYNTAX       Unsigned64
    MAX-ACCESS   read-only
    STATUS       current
    DESCRIPTION
        "Cisco UCS bios:VfOptionROMLoad:propAcl managed object property"
    ::= { cucsBiosVfOptionROMLoadEntry 5 }

cucsBiosVfOptionROMLoadSupportedByDefault OBJECT-TYPE
    SYNTAX       CucsBiosSupportedAction
    MAX-ACCESS   read-only
    STATUS       current
    DESCRIPTION
        "Cisco UCS bios:VfOptionROMLoad:supportedByDefault
        managed object property"
    ::= { cucsBiosVfOptionROMLoadEntry 6 }

cucsBiosVfOutOfBandManagementTable OBJECT-TYPE
    SYNTAX           SEQUENCE OF CucsBiosVfOutOfBandManagementEntry
    MAX-ACCESS       not-accessible
    STATUS           current
    DESCRIPTION
        "Cisco UCS bios:VfOutOfBandManagement managed object table"
    ::= { cucsBiosObjects 103 }

cucsBiosVfOutOfBandManagementEntry OBJECT-TYPE
    SYNTAX           CucsBiosVfOutOfBandManagementEntry
    MAX-ACCESS       not-accessible
    STATUS           current
    DESCRIPTION
        "Entry for the cucsBiosVfOutOfBandManagementTable table."
    INDEX { cucsBiosVfOutOfBandManagementInstanceId }
    ::= { cucsBiosVfOutOfBandManagementTable 1 }

CucsBiosVfOutOfBandManagementEntry ::= SEQUENCE {
    cucsBiosVfOutOfBandManagementInstanceId                          CucsManagedObjectId,
    cucsBiosVfOutOfBandManagementDn                                  CucsManagedObjectDn,
    cucsBiosVfOutOfBandManagementRn                                  SnmpAdminString,
    cucsBiosVfOutOfBandManagementPropAcl                             Unsigned64,
    cucsBiosVfOutOfBandManagementSupportedByDefault                  CucsBiosSupportedAction,
    cucsBiosVfOutOfBandManagementVpComSpcrEnable                     CucsBiosVfOutOfBandManagementVpComSpcrEnable
}

cucsBiosVfOutOfBandManagementInstanceId OBJECT-TYPE
    SYNTAX       CucsManagedObjectId
    MAX-ACCESS   not-accessible
    STATUS       current
    DESCRIPTION
        "Instance identifier of the managed object."
    ::= { cucsBiosVfOutOfBandManagementEntry 1 }

cucsBiosVfOutOfBandManagementDn OBJECT-TYPE
    SYNTAX       CucsManagedObjectDn
    MAX-ACCESS   read-only
    STATUS       current
    DESCRIPTION
        "Cisco UCS bios:VfOutOfBandManagement:dn managed object property"
    ::= { cucsBiosVfOutOfBandManagementEntry 2 }

cucsBiosVfOutOfBandManagementRn OBJECT-TYPE
    SYNTAX       SnmpAdminString
    MAX-ACCESS   read-only
    STATUS       current
    DESCRIPTION
        "Cisco UCS bios:VfOutOfBandManagement:rn managed object property"
    ::= { cucsBiosVfOutOfBandManagementEntry 3 }

cucsBiosVfOutOfBandManagementPropAcl OBJECT-TYPE
    SYNTAX       Unsigned64
    MAX-ACCESS   read-only
    STATUS       current
    DESCRIPTION
        "Cisco UCS bios:VfOutOfBandManagement:propAcl managed
        object property"
    ::= { cucsBiosVfOutOfBandManagementEntry 4 }

cucsBiosVfOutOfBandManagementSupportedByDefault OBJECT-TYPE
    SYNTAX       CucsBiosSupportedAction
    MAX-ACCESS   read-only
    STATUS       current
    DESCRIPTION
        "Cisco UCS bios:VfOutOfBandManagement:supportedByDefault
        managed object property"
    ::= { cucsBiosVfOutOfBandManagementEntry 5 }

cucsBiosVfOutOfBandManagementVpComSpcrEnable OBJECT-TYPE
    SYNTAX       CucsBiosVfOutOfBandManagementVpComSpcrEnable
    MAX-ACCESS   read-only
    STATUS       current
    DESCRIPTION
        "Cisco UCS bios:VfOutOfBandManagement:vpComSpcrEnable
        managed object property"
    ::= { cucsBiosVfOutOfBandManagementEntry 6 }

cucsBiosVfPCHSATAModeTable OBJECT-TYPE
    SYNTAX           SEQUENCE OF CucsBiosVfPCHSATAModeEntry
    MAX-ACCESS       not-accessible
    STATUS           current
    DESCRIPTION
        "Cisco UCS bios:VfPCHSATAMode managed object table"
    ::= { cucsBiosObjects 84 }

cucsBiosVfPCHSATAModeEntry OBJECT-TYPE
    SYNTAX           CucsBiosVfPCHSATAModeEntry
    MAX-ACCESS       not-accessible
    STATUS           current
    DESCRIPTION
        "Entry for the cucsBiosVfPCHSATAModeTable table."
    INDEX { cucsBiosVfPCHSATAModeInstanceId }
    ::= { cucsBiosVfPCHSATAModeTable 1 }

CucsBiosVfPCHSATAModeEntry ::= SEQUENCE {
    cucsBiosVfPCHSATAModeInstanceId                                  CucsManagedObjectId,
    cucsBiosVfPCHSATAModeDn                                          CucsManagedObjectDn,
    cucsBiosVfPCHSATAModeRn                                          SnmpAdminString,
    cucsBiosVfPCHSATAModePropAcl                                     Unsigned64,
    cucsBiosVfPCHSATAModeSupportedByDefault                          CucsBiosSupportedAction,
    cucsBiosVfPCHSATAModeVpSATAMode                                  CucsBiosVfPCHSATAModeVpSATAMode
}

cucsBiosVfPCHSATAModeInstanceId OBJECT-TYPE
    SYNTAX       CucsManagedObjectId
    MAX-ACCESS   not-accessible
    STATUS       current
    DESCRIPTION
        "Instance identifier of the managed object."
    ::= { cucsBiosVfPCHSATAModeEntry 1 }

cucsBiosVfPCHSATAModeDn OBJECT-TYPE
    SYNTAX       CucsManagedObjectDn
    MAX-ACCESS   read-only
    STATUS       current
    DESCRIPTION
        "Cisco UCS bios:VfPCHSATAMode:dn managed object property"
    ::= { cucsBiosVfPCHSATAModeEntry 2 }

cucsBiosVfPCHSATAModeRn OBJECT-TYPE
    SYNTAX       SnmpAdminString
    MAX-ACCESS   read-only
    STATUS       current
    DESCRIPTION
        "Cisco UCS bios:VfPCHSATAMode:rn managed object property"
    ::= { cucsBiosVfPCHSATAModeEntry 3 }

cucsBiosVfPCHSATAModePropAcl OBJECT-TYPE
    SYNTAX       Unsigned64
    MAX-ACCESS   read-only
    STATUS       current
    DESCRIPTION
        "Cisco UCS bios:VfPCHSATAMode:propAcl managed object property"
    ::= { cucsBiosVfPCHSATAModeEntry 4 }

cucsBiosVfPCHSATAModeSupportedByDefault OBJECT-TYPE
    SYNTAX       CucsBiosSupportedAction
    MAX-ACCESS   read-only
    STATUS       current
    DESCRIPTION
        "Cisco UCS bios:VfPCHSATAMode:supportedByDefault
        managed object property"
    ::= { cucsBiosVfPCHSATAModeEntry 5 }

cucsBiosVfPCHSATAModeVpSATAMode OBJECT-TYPE
    SYNTAX       CucsBiosVfPCHSATAModeVpSATAMode
    MAX-ACCESS   read-only
    STATUS       current
    DESCRIPTION
        "Cisco UCS bios:VfPCHSATAMode:vpSATAMode managed object property"
    ::= { cucsBiosVfPCHSATAModeEntry 7 }

cucsBiosVfPCILOMPortsConfigurationTable OBJECT-TYPE
    SYNTAX           SEQUENCE OF CucsBiosVfPCILOMPortsConfigurationEntry
    MAX-ACCESS       not-accessible
    STATUS           current
    DESCRIPTION
        "Cisco UCS bios:VfPCILOMPortsConfiguration managed object table"
    ::= { cucsBiosObjects 89 }

cucsBiosVfPCILOMPortsConfigurationEntry OBJECT-TYPE
    SYNTAX           CucsBiosVfPCILOMPortsConfigurationEntry
    MAX-ACCESS       not-accessible
    STATUS           current
    DESCRIPTION
        "Entry for the cucsBiosVfPCILOMPortsConfigurationTable table."
    INDEX { cucsBiosVfPCILOMPortsConfigurationInstanceId }
    ::= { cucsBiosVfPCILOMPortsConfigurationTable 1 }

CucsBiosVfPCILOMPortsConfigurationEntry ::= SEQUENCE {
    cucsBiosVfPCILOMPortsConfigurationInstanceId                     CucsManagedObjectId,
    cucsBiosVfPCILOMPortsConfigurationDn                             CucsManagedObjectDn,
    cucsBiosVfPCILOMPortsConfigurationRn                             SnmpAdminString,
    cucsBiosVfPCILOMPortsConfigurationVpPCIe10GLOM2Link              CucsBiosVfPCILOMPortsConfigurationVpPCIe10GLOM2Link,
    cucsBiosVfPCILOMPortsConfigurationSupportedByDefault             CucsBiosSupportedAction,
    cucsBiosVfPCILOMPortsConfigurationPropAcl                        Unsigned64
}

cucsBiosVfPCILOMPortsConfigurationInstanceId OBJECT-TYPE
    SYNTAX       CucsManagedObjectId
    MAX-ACCESS   not-accessible
    STATUS       current
    DESCRIPTION
        "Instance identifier of the managed object."
    ::= { cucsBiosVfPCILOMPortsConfigurationEntry 1 }

cucsBiosVfPCILOMPortsConfigurationDn OBJECT-TYPE
    SYNTAX       CucsManagedObjectDn
    MAX-ACCESS   read-only
    STATUS       current
    DESCRIPTION
        "Cisco UCS bios:VfPCILOMPortsConfiguration:dn managed
        object property"
    ::= { cucsBiosVfPCILOMPortsConfigurationEntry 2 }

cucsBiosVfPCILOMPortsConfigurationRn OBJECT-TYPE
    SYNTAX       SnmpAdminString
    MAX-ACCESS   read-only
    STATUS       current
    DESCRIPTION
        "Cisco UCS bios:VfPCILOMPortsConfiguration:rn managed
        object property"
    ::= { cucsBiosVfPCILOMPortsConfigurationEntry 3 }

cucsBiosVfPCILOMPortsConfigurationVpPCIe10GLOM2Link OBJECT-TYPE
    SYNTAX       CucsBiosVfPCILOMPortsConfigurationVpPCIe10GLOM2Link
    MAX-ACCESS   read-only
    STATUS       current
    DESCRIPTION
        "Cisco UCS bios:VfPCILOMPortsConfiguration:vpPCIe10GLOM2Link
        managed object property"
    ::= { cucsBiosVfPCILOMPortsConfigurationEntry 4 }

cucsBiosVfPCILOMPortsConfigurationSupportedByDefault OBJECT-TYPE
    SYNTAX       CucsBiosSupportedAction
    MAX-ACCESS   read-only
    STATUS       current
    DESCRIPTION
        "Cisco UCS bios:VfPCILOMPortsConfiguration:supportedByDefault
        managed object property"
    ::= { cucsBiosVfPCILOMPortsConfigurationEntry 5 }

cucsBiosVfPCILOMPortsConfigurationPropAcl OBJECT-TYPE
    SYNTAX       Unsigned64
    MAX-ACCESS   read-only
    STATUS       current
    DESCRIPTION
        "Cisco UCS bios:VfPCILOMPortsConfiguration:propAcl
        managed object property"
    ::= { cucsBiosVfPCILOMPortsConfigurationEntry 6 }

cucsBiosVfPCIROMCLPTable OBJECT-TYPE
    SYNTAX           SEQUENCE OF CucsBiosVfPCIROMCLPEntry
    MAX-ACCESS       not-accessible
    STATUS           current
    DESCRIPTION
        "Cisco UCS bios:VfPCIROMCLP managed object table"
    ::= { cucsBiosObjects 104 }

cucsBiosVfPCIROMCLPEntry OBJECT-TYPE
    SYNTAX           CucsBiosVfPCIROMCLPEntry
    MAX-ACCESS       not-accessible
    STATUS           current
    DESCRIPTION
        "Entry for the cucsBiosVfPCIROMCLPTable table."
    INDEX { cucsBiosVfPCIROMCLPInstanceId }
    ::= { cucsBiosVfPCIROMCLPTable 1 }

CucsBiosVfPCIROMCLPEntry ::= SEQUENCE {
    cucsBiosVfPCIROMCLPInstanceId                                    CucsManagedObjectId,
    cucsBiosVfPCIROMCLPDn                                            CucsManagedObjectDn,
    cucsBiosVfPCIROMCLPRn                                            SnmpAdminString,
    cucsBiosVfPCIROMCLPPropAcl                                       Unsigned64,
    cucsBiosVfPCIROMCLPSupportedByDefault                            CucsBiosSupportedAction,
    cucsBiosVfPCIROMCLPVpPCIROMCLP                                   CucsBiosVfPCIROMCLPVpPCIROMCLP
}

cucsBiosVfPCIROMCLPInstanceId OBJECT-TYPE
    SYNTAX       CucsManagedObjectId
    MAX-ACCESS   not-accessible
    STATUS       current
    DESCRIPTION
        "Instance identifier of the managed object."
    ::= { cucsBiosVfPCIROMCLPEntry 1 }

cucsBiosVfPCIROMCLPDn OBJECT-TYPE
    SYNTAX       CucsManagedObjectDn
    MAX-ACCESS   read-only
    STATUS       current
    DESCRIPTION
        "Cisco UCS bios:VfPCIROMCLP:dn managed object property"
    ::= { cucsBiosVfPCIROMCLPEntry 2 }

cucsBiosVfPCIROMCLPRn OBJECT-TYPE
    SYNTAX       SnmpAdminString
    MAX-ACCESS   read-only
    STATUS       current
    DESCRIPTION
        "Cisco UCS bios:VfPCIROMCLP:rn managed object property"
    ::= { cucsBiosVfPCIROMCLPEntry 3 }

cucsBiosVfPCIROMCLPPropAcl OBJECT-TYPE
    SYNTAX       Unsigned64
    MAX-ACCESS   read-only
    STATUS       current
    DESCRIPTION
        "Cisco UCS bios:VfPCIROMCLP:propAcl managed object property"
    ::= { cucsBiosVfPCIROMCLPEntry 4 }

cucsBiosVfPCIROMCLPSupportedByDefault OBJECT-TYPE
    SYNTAX       CucsBiosSupportedAction
    MAX-ACCESS   read-only
    STATUS       current
    DESCRIPTION
        "Cisco UCS bios:VfPCIROMCLP:supportedByDefault
        managed object property"
    ::= { cucsBiosVfPCIROMCLPEntry 5 }

cucsBiosVfPCIROMCLPVpPCIROMCLP OBJECT-TYPE
    SYNTAX       CucsBiosVfPCIROMCLPVpPCIROMCLP
    MAX-ACCESS   read-only
    STATUS       current
    DESCRIPTION
        "Cisco UCS bios:VfPCIROMCLP:vpPCIROMCLP managed object property"
    ::= { cucsBiosVfPCIROMCLPEntry 6 }

cucsBiosVfPCISlotLinkSpeedTable OBJECT-TYPE
    SYNTAX           SEQUENCE OF CucsBiosVfPCISlotLinkSpeedEntry
    MAX-ACCESS       not-accessible
    STATUS           current
    DESCRIPTION
        "Cisco UCS bios:VfPCISlotLinkSpeed managed object table"
    ::= { cucsBiosObjects 70 }

cucsBiosVfPCISlotLinkSpeedEntry OBJECT-TYPE
    SYNTAX           CucsBiosVfPCISlotLinkSpeedEntry
    MAX-ACCESS       not-accessible
    STATUS           current
    DESCRIPTION
        "Entry for the cucsBiosVfPCISlotLinkSpeedTable table."
    INDEX { cucsBiosVfPCISlotLinkSpeedInstanceId }
    ::= { cucsBiosVfPCISlotLinkSpeedTable 1 }

CucsBiosVfPCISlotLinkSpeedEntry ::= SEQUENCE {
    cucsBiosVfPCISlotLinkSpeedInstanceId                             CucsManagedObjectId,
    cucsBiosVfPCISlotLinkSpeedDn                                     CucsManagedObjectDn,
    cucsBiosVfPCISlotLinkSpeedRn                                     SnmpAdminString,
    cucsBiosVfPCISlotLinkSpeedVpPCIeSlot10LinkSpeed                  CucsBiosVfPCISlotLinkSpeedVpPCIeSlot10LinkSpeed,
    cucsBiosVfPCISlotLinkSpeedVpPCIeSlot1LinkSpeed                   CucsBiosVfPCISlotLinkSpeedVpPCIeSlot1LinkSpeed,
    cucsBiosVfPCISlotLinkSpeedVpPCIeSlot2LinkSpeed                   CucsBiosVfPCISlotLinkSpeedVpPCIeSlot2LinkSpeed,
    cucsBiosVfPCISlotLinkSpeedVpPCIeSlot3LinkSpeed                   CucsBiosVfPCISlotLinkSpeedVpPCIeSlot3LinkSpeed,
    cucsBiosVfPCISlotLinkSpeedVpPCIeSlot4LinkSpeed                   CucsBiosVfPCISlotLinkSpeedVpPCIeSlot4LinkSpeed,
    cucsBiosVfPCISlotLinkSpeedVpPCIeSlot5LinkSpeed                   CucsBiosVfPCISlotLinkSpeedVpPCIeSlot5LinkSpeed,
    cucsBiosVfPCISlotLinkSpeedVpPCIeSlot6LinkSpeed                   CucsBiosVfPCISlotLinkSpeedVpPCIeSlot6LinkSpeed,
    cucsBiosVfPCISlotLinkSpeedVpPCIeSlot7LinkSpeed                   CucsBiosVfPCISlotLinkSpeedVpPCIeSlot7LinkSpeed,
    cucsBiosVfPCISlotLinkSpeedVpPCIeSlot8LinkSpeed                   CucsBiosVfPCISlotLinkSpeedVpPCIeSlot8LinkSpeed,
    cucsBiosVfPCISlotLinkSpeedVpPCIeSlot9LinkSpeed                   CucsBiosVfPCISlotLinkSpeedVpPCIeSlot9LinkSpeed,
    cucsBiosVfPCISlotLinkSpeedPropAcl                                Unsigned64,
    cucsBiosVfPCISlotLinkSpeedSupportedByDefault                     CucsBiosSupportedAction
}

cucsBiosVfPCISlotLinkSpeedInstanceId OBJECT-TYPE
    SYNTAX       CucsManagedObjectId
    MAX-ACCESS   not-accessible
    STATUS       current
    DESCRIPTION
        "Instance identifier of the managed object."
    ::= { cucsBiosVfPCISlotLinkSpeedEntry 1 }

cucsBiosVfPCISlotLinkSpeedDn OBJECT-TYPE
    SYNTAX       CucsManagedObjectDn
    MAX-ACCESS   read-only
    STATUS       current
    DESCRIPTION
        "Cisco UCS bios:VfPCISlotLinkSpeed:dn managed object property"
    ::= { cucsBiosVfPCISlotLinkSpeedEntry 2 }

cucsBiosVfPCISlotLinkSpeedRn OBJECT-TYPE
    SYNTAX       SnmpAdminString
    MAX-ACCESS   read-only
    STATUS       current
    DESCRIPTION
        "Cisco UCS bios:VfPCISlotLinkSpeed:rn managed object property"
    ::= { cucsBiosVfPCISlotLinkSpeedEntry 3 }

cucsBiosVfPCISlotLinkSpeedVpPCIeSlot10LinkSpeed OBJECT-TYPE
    SYNTAX       CucsBiosVfPCISlotLinkSpeedVpPCIeSlot10LinkSpeed
    MAX-ACCESS   read-only
    STATUS       current
    DESCRIPTION
        "Cisco UCS bios:VfPCISlotLinkSpeed:vpPCIeSlot10LinkSpeed
        managed object property"
    ::= { cucsBiosVfPCISlotLinkSpeedEntry 4 }

cucsBiosVfPCISlotLinkSpeedVpPCIeSlot1LinkSpeed OBJECT-TYPE
    SYNTAX       CucsBiosVfPCISlotLinkSpeedVpPCIeSlot1LinkSpeed
    MAX-ACCESS   read-only
    STATUS       current
    DESCRIPTION
        "Cisco UCS bios:VfPCISlotLinkSpeed:vpPCIeSlot1LinkSpeed
        managed object property"
    ::= { cucsBiosVfPCISlotLinkSpeedEntry 5 }

cucsBiosVfPCISlotLinkSpeedVpPCIeSlot2LinkSpeed OBJECT-TYPE
    SYNTAX       CucsBiosVfPCISlotLinkSpeedVpPCIeSlot2LinkSpeed
    MAX-ACCESS   read-only
    STATUS       current
    DESCRIPTION
        "Cisco UCS bios:VfPCISlotLinkSpeed:vpPCIeSlot2LinkSpeed
        managed object property"
    ::= { cucsBiosVfPCISlotLinkSpeedEntry 6 }

cucsBiosVfPCISlotLinkSpeedVpPCIeSlot3LinkSpeed OBJECT-TYPE
    SYNTAX       CucsBiosVfPCISlotLinkSpeedVpPCIeSlot3LinkSpeed
    MAX-ACCESS   read-only
    STATUS       current
    DESCRIPTION
        "Cisco UCS bios:VfPCISlotLinkSpeed:vpPCIeSlot3LinkSpeed
        managed object property"
    ::= { cucsBiosVfPCISlotLinkSpeedEntry 7 }

cucsBiosVfPCISlotLinkSpeedVpPCIeSlot4LinkSpeed OBJECT-TYPE
    SYNTAX       CucsBiosVfPCISlotLinkSpeedVpPCIeSlot4LinkSpeed
    MAX-ACCESS   read-only
    STATUS       current
    DESCRIPTION
        "Cisco UCS bios:VfPCISlotLinkSpeed:vpPCIeSlot4LinkSpeed
        managed object property"
    ::= { cucsBiosVfPCISlotLinkSpeedEntry 8 }

cucsBiosVfPCISlotLinkSpeedVpPCIeSlot5LinkSpeed OBJECT-TYPE
    SYNTAX       CucsBiosVfPCISlotLinkSpeedVpPCIeSlot5LinkSpeed
    MAX-ACCESS   read-only
    STATUS       current
    DESCRIPTION
        "Cisco UCS bios:VfPCISlotLinkSpeed:vpPCIeSlot5LinkSpeed
        managed object property"
    ::= { cucsBiosVfPCISlotLinkSpeedEntry 9 }

cucsBiosVfPCISlotLinkSpeedVpPCIeSlot6LinkSpeed OBJECT-TYPE
    SYNTAX       CucsBiosVfPCISlotLinkSpeedVpPCIeSlot6LinkSpeed
    MAX-ACCESS   read-only
    STATUS       current
    DESCRIPTION
        "Cisco UCS bios:VfPCISlotLinkSpeed:vpPCIeSlot6LinkSpeed
        managed object property"
    ::= { cucsBiosVfPCISlotLinkSpeedEntry 10 }

cucsBiosVfPCISlotLinkSpeedVpPCIeSlot7LinkSpeed OBJECT-TYPE
    SYNTAX       CucsBiosVfPCISlotLinkSpeedVpPCIeSlot7LinkSpeed
    MAX-ACCESS   read-only
    STATUS       current
    DESCRIPTION
        "Cisco UCS bios:VfPCISlotLinkSpeed:vpPCIeSlot7LinkSpeed
        managed object property"
    ::= { cucsBiosVfPCISlotLinkSpeedEntry 11 }

cucsBiosVfPCISlotLinkSpeedVpPCIeSlot8LinkSpeed OBJECT-TYPE
    SYNTAX       CucsBiosVfPCISlotLinkSpeedVpPCIeSlot8LinkSpeed
    MAX-ACCESS   read-only
    STATUS       current
    DESCRIPTION
        "Cisco UCS bios:VfPCISlotLinkSpeed:vpPCIeSlot8LinkSpeed
        managed object property"
    ::= { cucsBiosVfPCISlotLinkSpeedEntry 12 }

cucsBiosVfPCISlotLinkSpeedVpPCIeSlot9LinkSpeed OBJECT-TYPE
    SYNTAX       CucsBiosVfPCISlotLinkSpeedVpPCIeSlot9LinkSpeed
    MAX-ACCESS   read-only
    STATUS       current
    DESCRIPTION
        "Cisco UCS bios:VfPCISlotLinkSpeed:vpPCIeSlot9LinkSpeed
        managed object property"
    ::= { cucsBiosVfPCISlotLinkSpeedEntry 13 }

cucsBiosVfPCISlotLinkSpeedPropAcl OBJECT-TYPE
    SYNTAX       Unsigned64
    MAX-ACCESS   read-only
    STATUS       current
    DESCRIPTION
        "Cisco UCS bios:VfPCISlotLinkSpeed:propAcl managed
        object property"
    ::= { cucsBiosVfPCISlotLinkSpeedEntry 14 }

cucsBiosVfPCISlotLinkSpeedSupportedByDefault OBJECT-TYPE
    SYNTAX       CucsBiosSupportedAction
    MAX-ACCESS   read-only
    STATUS       current
    DESCRIPTION
        "Cisco UCS bios:VfPCISlotLinkSpeed:supportedByDefault
        managed object property"
    ::= { cucsBiosVfPCISlotLinkSpeedEntry 15 }

cucsBiosVfPCISlotOptionROMEnableTable OBJECT-TYPE
    SYNTAX           SEQUENCE OF CucsBiosVfPCISlotOptionROMEnableEntry
    MAX-ACCESS       not-accessible
    STATUS           current
    DESCRIPTION
        "Cisco UCS bios:VfPCISlotOptionROMEnable managed object table"
    ::= { cucsBiosObjects 55 }

cucsBiosVfPCISlotOptionROMEnableEntry OBJECT-TYPE
    SYNTAX           CucsBiosVfPCISlotOptionROMEnableEntry
    MAX-ACCESS       not-accessible
    STATUS           current
    DESCRIPTION
        "Entry for the cucsBiosVfPCISlotOptionROMEnableTable table."
    INDEX { cucsBiosVfPCISlotOptionROMEnableInstanceId }
    ::= { cucsBiosVfPCISlotOptionROMEnableTable 1 }

CucsBiosVfPCISlotOptionROMEnableEntry ::= SEQUENCE {
    cucsBiosVfPCISlotOptionROMEnableInstanceId                       CucsManagedObjectId,
    cucsBiosVfPCISlotOptionROMEnableDn                               CucsManagedObjectDn,
    cucsBiosVfPCISlotOptionROMEnableRn                               SnmpAdminString,
    cucsBiosVfPCISlotOptionROMEnableVpSlot1State                     CucsBiosVfPCISlotOptionROMEnableVpSlot1State,
    cucsBiosVfPCISlotOptionROMEnableVpSlot2State                     CucsBiosVfPCISlotOptionROMEnableVpSlot2State,
    cucsBiosVfPCISlotOptionROMEnableVpSlot3State                     CucsBiosVfPCISlotOptionROMEnableVpSlot3State,
    cucsBiosVfPCISlotOptionROMEnableVpSlot4State                     CucsBiosVfPCISlotOptionROMEnableVpSlot4State,
    cucsBiosVfPCISlotOptionROMEnableVpSlot5State                     CucsBiosVfPCISlotOptionROMEnableVpSlot5State,
    cucsBiosVfPCISlotOptionROMEnableVpSlotMezzState                  CucsBiosVfPCISlotOptionROMEnableVpSlotMezzState,
    cucsBiosVfPCISlotOptionROMEnableVpSlot6State                     CucsBiosVfPCISlotOptionROMEnableVpSlot6State,
    cucsBiosVfPCISlotOptionROMEnableVpSlot7State                     CucsBiosVfPCISlotOptionROMEnableVpSlot7State,
    cucsBiosVfPCISlotOptionROMEnableVpPCIeSlotSASOptionROM           CucsBiosVfPCISlotOptionROMEnableVpPCIeSlotSASOptionROM,
    cucsBiosVfPCISlotOptionROMEnableVpSlot10State                    CucsBiosVfPCISlotOptionROMEnableVpSlot10State,
    cucsBiosVfPCISlotOptionROMEnableVpSlot8State                     CucsBiosVfPCISlotOptionROMEnableVpSlot8State,
    cucsBiosVfPCISlotOptionROMEnableVpSlot9State                     CucsBiosVfPCISlotOptionROMEnableVpSlot9State,
    cucsBiosVfPCISlotOptionROMEnableVpPCIeSlotHBAOptionROM           CucsBiosVfPCISlotOptionROMEnableVpPCIeSlotHBAOptionROM,
    cucsBiosVfPCISlotOptionROMEnableVpPCIeSlotMLOMOptionROM          CucsBiosVfPCISlotOptionROMEnableVpPCIeSlotMLOMOptionROM,
    cucsBiosVfPCISlotOptionROMEnableVpPCIeSlotN1OptionROM            CucsBiosVfPCISlotOptionROMEnableVpPCIeSlotN1OptionROM,
    cucsBiosVfPCISlotOptionROMEnableVpPCIeSlotN2OptionROM            CucsBiosVfPCISlotOptionROMEnableVpPCIeSlotN2OptionROM,
    cucsBiosVfPCISlotOptionROMEnablePropAcl                          Unsigned64,
    cucsBiosVfPCISlotOptionROMEnableSupportedByDefault               CucsBiosSupportedAction
}

cucsBiosVfPCISlotOptionROMEnableInstanceId OBJECT-TYPE
    SYNTAX       CucsManagedObjectId
    MAX-ACCESS   not-accessible
    STATUS       current
    DESCRIPTION
        "Instance identifier of the managed object."
    ::= { cucsBiosVfPCISlotOptionROMEnableEntry 1 }

cucsBiosVfPCISlotOptionROMEnableDn OBJECT-TYPE
    SYNTAX       CucsManagedObjectDn
    MAX-ACCESS   read-only
    STATUS       current
    DESCRIPTION
        "Cisco UCS bios:VfPCISlotOptionROMEnable:dn managed
        object property"
    ::= { cucsBiosVfPCISlotOptionROMEnableEntry 2 }

cucsBiosVfPCISlotOptionROMEnableRn OBJECT-TYPE
    SYNTAX       SnmpAdminString
    MAX-ACCESS   read-only
    STATUS       current
    DESCRIPTION
        "Cisco UCS bios:VfPCISlotOptionROMEnable:rn managed
        object property"
    ::= { cucsBiosVfPCISlotOptionROMEnableEntry 3 }

cucsBiosVfPCISlotOptionROMEnableVpSlot1State OBJECT-TYPE
    SYNTAX       CucsBiosVfPCISlotOptionROMEnableVpSlot1State
    MAX-ACCESS   read-only
    STATUS       current
    DESCRIPTION
        "Cisco UCS bios:VfPCISlotOptionROMEnable:vpSlot1State
        managed object property"
    ::= { cucsBiosVfPCISlotOptionROMEnableEntry 4 }

cucsBiosVfPCISlotOptionROMEnableVpSlot2State OBJECT-TYPE
    SYNTAX       CucsBiosVfPCISlotOptionROMEnableVpSlot2State
    MAX-ACCESS   read-only
    STATUS       current
    DESCRIPTION
        "Cisco UCS bios:VfPCISlotOptionROMEnable:vpSlot2State
        managed object property"
    ::= { cucsBiosVfPCISlotOptionROMEnableEntry 5 }

cucsBiosVfPCISlotOptionROMEnableVpSlot3State OBJECT-TYPE
    SYNTAX       CucsBiosVfPCISlotOptionROMEnableVpSlot3State
    MAX-ACCESS   read-only
    STATUS       current
    DESCRIPTION
        "Cisco UCS bios:VfPCISlotOptionROMEnable:vpSlot3State
        managed object property"
    ::= { cucsBiosVfPCISlotOptionROMEnableEntry 6 }

cucsBiosVfPCISlotOptionROMEnableVpSlot4State OBJECT-TYPE
    SYNTAX       CucsBiosVfPCISlotOptionROMEnableVpSlot4State
    MAX-ACCESS   read-only
    STATUS       current
    DESCRIPTION
        "Cisco UCS bios:VfPCISlotOptionROMEnable:vpSlot4State
        managed object property"
    ::= { cucsBiosVfPCISlotOptionROMEnableEntry 7 }

cucsBiosVfPCISlotOptionROMEnableVpSlot5State OBJECT-TYPE
    SYNTAX       CucsBiosVfPCISlotOptionROMEnableVpSlot5State
    MAX-ACCESS   read-only
    STATUS       current
    DESCRIPTION
        "Cisco UCS bios:VfPCISlotOptionROMEnable:vpSlot5State
        managed object property"
    ::= { cucsBiosVfPCISlotOptionROMEnableEntry 8 }

cucsBiosVfPCISlotOptionROMEnableVpSlotMezzState OBJECT-TYPE
    SYNTAX       CucsBiosVfPCISlotOptionROMEnableVpSlotMezzState
    MAX-ACCESS   read-only
    STATUS       current
    DESCRIPTION
        "Cisco UCS bios:VfPCISlotOptionROMEnable:vpSlotMezzState
        managed object property"
    ::= { cucsBiosVfPCISlotOptionROMEnableEntry 9 }

cucsBiosVfPCISlotOptionROMEnableVpSlot6State OBJECT-TYPE
    SYNTAX       CucsBiosVfPCISlotOptionROMEnableVpSlot6State
    MAX-ACCESS   read-only
    STATUS       current
    DESCRIPTION
        "Cisco UCS bios:VfPCISlotOptionROMEnable:vpSlot6State
        managed object property"
    ::= { cucsBiosVfPCISlotOptionROMEnableEntry 10 }

cucsBiosVfPCISlotOptionROMEnableVpSlot7State OBJECT-TYPE
    SYNTAX       CucsBiosVfPCISlotOptionROMEnableVpSlot7State
    MAX-ACCESS   read-only
    STATUS       current
    DESCRIPTION
        "Cisco UCS bios:VfPCISlotOptionROMEnable:vpSlot7State
        managed object property"
    ::= { cucsBiosVfPCISlotOptionROMEnableEntry 11 }

cucsBiosVfPCISlotOptionROMEnableVpPCIeSlotSASOptionROM OBJECT-TYPE
    SYNTAX       CucsBiosVfPCISlotOptionROMEnableVpPCIeSlotSASOptionROM
    MAX-ACCESS   read-only
    STATUS       current
    DESCRIPTION
        "Cisco UCS bios:VfPCISlotOptionROMEnable:vpPCIeSlotSASOptionROM
        managed object property"
    ::= { cucsBiosVfPCISlotOptionROMEnableEntry 12 }

cucsBiosVfPCISlotOptionROMEnableVpSlot10State OBJECT-TYPE
    SYNTAX       CucsBiosVfPCISlotOptionROMEnableVpSlot10State
    MAX-ACCESS   read-only
    STATUS       current
    DESCRIPTION
        "Cisco UCS bios:VfPCISlotOptionROMEnable:vpSlot10State
        managed object property"
    ::= { cucsBiosVfPCISlotOptionROMEnableEntry 13 }

cucsBiosVfPCISlotOptionROMEnableVpSlot8State OBJECT-TYPE
    SYNTAX       CucsBiosVfPCISlotOptionROMEnableVpSlot8State
    MAX-ACCESS   read-only
    STATUS       current
    DESCRIPTION
        "Cisco UCS bios:VfPCISlotOptionROMEnable:vpSlot8State
        managed object property"
    ::= { cucsBiosVfPCISlotOptionROMEnableEntry 14 }

cucsBiosVfPCISlotOptionROMEnableVpSlot9State OBJECT-TYPE
    SYNTAX       CucsBiosVfPCISlotOptionROMEnableVpSlot9State
    MAX-ACCESS   read-only
    STATUS       current
    DESCRIPTION
        "Cisco UCS bios:VfPCISlotOptionROMEnable:vpSlot9State
        managed object property"
    ::= { cucsBiosVfPCISlotOptionROMEnableEntry 15 }

cucsBiosVfPCISlotOptionROMEnableVpPCIeSlotHBAOptionROM OBJECT-TYPE
    SYNTAX       CucsBiosVfPCISlotOptionROMEnableVpPCIeSlotHBAOptionROM
    MAX-ACCESS   read-only
    STATUS       current
    DESCRIPTION
        "Cisco UCS bios:VfPCISlotOptionROMEnable:vpPCIeSlotHBAOptionROM
        managed object property"
    ::= { cucsBiosVfPCISlotOptionROMEnableEntry 16 }

cucsBiosVfPCISlotOptionROMEnableVpPCIeSlotMLOMOptionROM OBJECT-TYPE
    SYNTAX       CucsBiosVfPCISlotOptionROMEnableVpPCIeSlotMLOMOptionROM
    MAX-ACCESS   read-only
    STATUS       current
    DESCRIPTION
        "Cisco UCS bios:VfPCISlotOptionROMEnable:vpPCIeSlotMLOMOptionROM
        managed object property"
    ::= { cucsBiosVfPCISlotOptionROMEnableEntry 17 }

cucsBiosVfPCISlotOptionROMEnableVpPCIeSlotN1OptionROM OBJECT-TYPE
    SYNTAX       CucsBiosVfPCISlotOptionROMEnableVpPCIeSlotN1OptionROM
    MAX-ACCESS   read-only
    STATUS       current
    DESCRIPTION
        "Cisco UCS bios:VfPCISlotOptionROMEnable:vpPCIeSlotN1OptionROM
        managed object property"
    ::= { cucsBiosVfPCISlotOptionROMEnableEntry 18 }

cucsBiosVfPCISlotOptionROMEnableVpPCIeSlotN2OptionROM OBJECT-TYPE
    SYNTAX       CucsBiosVfPCISlotOptionROMEnableVpPCIeSlotN2OptionROM
    MAX-ACCESS   read-only
    STATUS       current
    DESCRIPTION
        "Cisco UCS bios:VfPCISlotOptionROMEnable:vpPCIeSlotN2OptionROM
        managed object property"
    ::= { cucsBiosVfPCISlotOptionROMEnableEntry 19 }

cucsBiosVfPCISlotOptionROMEnablePropAcl OBJECT-TYPE
    SYNTAX       Unsigned64
    MAX-ACCESS   read-only
    STATUS       current
    DESCRIPTION
        "Cisco UCS bios:VfPCISlotOptionROMEnable:propAcl
        managed object property"
    ::= { cucsBiosVfPCISlotOptionROMEnableEntry 20 }

cucsBiosVfPCISlotOptionROMEnableSupportedByDefault OBJECT-TYPE
    SYNTAX       CucsBiosSupportedAction
    MAX-ACCESS   read-only
    STATUS       current
    DESCRIPTION
        "Cisco UCS bios:VfPCISlotOptionROMEnable:supportedByDefault
        managed object property"
    ::= { cucsBiosVfPCISlotOptionROMEnableEntry 21 }

cucsBiosVfPOSTErrorPauseTable OBJECT-TYPE
    SYNTAX           SEQUENCE OF CucsBiosVfPOSTErrorPauseEntry
    MAX-ACCESS       not-accessible
    STATUS           current
    DESCRIPTION
        "Cisco UCS bios:VfPOSTErrorPause managed object table"
    ::= { cucsBiosObjects 40 }

cucsBiosVfPOSTErrorPauseEntry OBJECT-TYPE
    SYNTAX           CucsBiosVfPOSTErrorPauseEntry
    MAX-ACCESS       not-accessible
    STATUS           current
    DESCRIPTION
        "Entry for the cucsBiosVfPOSTErrorPauseTable table."
    INDEX { cucsBiosVfPOSTErrorPauseInstanceId }
    ::= { cucsBiosVfPOSTErrorPauseTable 1 }

CucsBiosVfPOSTErrorPauseEntry ::= SEQUENCE {
    cucsBiosVfPOSTErrorPauseInstanceId                               CucsManagedObjectId,
    cucsBiosVfPOSTErrorPauseDn                                       CucsManagedObjectDn,
    cucsBiosVfPOSTErrorPauseRn                                       SnmpAdminString,
    cucsBiosVfPOSTErrorPauseVpPOSTErrorPause                         CucsBiosVfPOSTErrorPauseVpPOSTErrorPause,
    cucsBiosVfPOSTErrorPausePropAcl                                  Unsigned64,
    cucsBiosVfPOSTErrorPauseSupportedByDefault                       CucsBiosSupportedAction
}

cucsBiosVfPOSTErrorPauseInstanceId OBJECT-TYPE
    SYNTAX       CucsManagedObjectId
    MAX-ACCESS   not-accessible
    STATUS       current
    DESCRIPTION
        "Instance identifier of the managed object."
    ::= { cucsBiosVfPOSTErrorPauseEntry 1 }

cucsBiosVfPOSTErrorPauseDn OBJECT-TYPE
    SYNTAX       CucsManagedObjectDn
    MAX-ACCESS   read-only
    STATUS       current
    DESCRIPTION
        "Cisco UCS bios:VfPOSTErrorPause:dn managed object property"
    ::= { cucsBiosVfPOSTErrorPauseEntry 2 }

cucsBiosVfPOSTErrorPauseRn OBJECT-TYPE
    SYNTAX       SnmpAdminString
    MAX-ACCESS   read-only
    STATUS       current
    DESCRIPTION
        "Cisco UCS bios:VfPOSTErrorPause:rn managed object property"
    ::= { cucsBiosVfPOSTErrorPauseEntry 3 }

cucsBiosVfPOSTErrorPauseVpPOSTErrorPause OBJECT-TYPE
    SYNTAX       CucsBiosVfPOSTErrorPauseVpPOSTErrorPause
    MAX-ACCESS   read-only
    STATUS       current
    DESCRIPTION
        "Cisco UCS bios:VfPOSTErrorPause:vpPOSTErrorPause
        managed object property"
    ::= { cucsBiosVfPOSTErrorPauseEntry 4 }

cucsBiosVfPOSTErrorPausePropAcl OBJECT-TYPE
    SYNTAX       Unsigned64
    MAX-ACCESS   read-only
    STATUS       current
    DESCRIPTION
        "Cisco UCS bios:VfPOSTErrorPause:propAcl managed object property"
    ::= { cucsBiosVfPOSTErrorPauseEntry 5 }

cucsBiosVfPOSTErrorPauseSupportedByDefault OBJECT-TYPE
    SYNTAX       CucsBiosSupportedAction
    MAX-ACCESS   read-only
    STATUS       current
    DESCRIPTION
        "Cisco UCS bios:VfPOSTErrorPause:supportedByDefault
        managed object property"
    ::= { cucsBiosVfPOSTErrorPauseEntry 6 }

cucsBiosVfPSTATECoordinationTable OBJECT-TYPE
    SYNTAX           SEQUENCE OF CucsBiosVfPSTATECoordinationEntry
    MAX-ACCESS       not-accessible
    STATUS           current
    DESCRIPTION
        "Cisco UCS bios:VfPSTATECoordination managed object table"
    ::= { cucsBiosObjects 71 }

cucsBiosVfPSTATECoordinationEntry OBJECT-TYPE
    SYNTAX           CucsBiosVfPSTATECoordinationEntry
    MAX-ACCESS       not-accessible
    STATUS           current
    DESCRIPTION
        "Entry for the cucsBiosVfPSTATECoordinationTable table."
    INDEX { cucsBiosVfPSTATECoordinationInstanceId }
    ::= { cucsBiosVfPSTATECoordinationTable 1 }

CucsBiosVfPSTATECoordinationEntry ::= SEQUENCE {
    cucsBiosVfPSTATECoordinationInstanceId                           CucsManagedObjectId,
    cucsBiosVfPSTATECoordinationDn                                   CucsManagedObjectDn,
    cucsBiosVfPSTATECoordinationRn                                   SnmpAdminString,
    cucsBiosVfPSTATECoordinationVpPSTATECoordination                 CucsBiosVfPSTATECoordinationVpPSTATECoordination,
    cucsBiosVfPSTATECoordinationPropAcl                              Unsigned64,
    cucsBiosVfPSTATECoordinationSupportedByDefault                   CucsBiosSupportedAction
}

cucsBiosVfPSTATECoordinationInstanceId OBJECT-TYPE
    SYNTAX       CucsManagedObjectId
    MAX-ACCESS   not-accessible
    STATUS       current
    DESCRIPTION
        "Instance identifier of the managed object."
    ::= { cucsBiosVfPSTATECoordinationEntry 1 }

cucsBiosVfPSTATECoordinationDn OBJECT-TYPE
    SYNTAX       CucsManagedObjectDn
    MAX-ACCESS   read-only
    STATUS       current
    DESCRIPTION
        "Cisco UCS bios:VfPSTATECoordination:dn managed object property"
    ::= { cucsBiosVfPSTATECoordinationEntry 2 }

cucsBiosVfPSTATECoordinationRn OBJECT-TYPE
    SYNTAX       SnmpAdminString
    MAX-ACCESS   read-only
    STATUS       current
    DESCRIPTION
        "Cisco UCS bios:VfPSTATECoordination:rn managed object property"
    ::= { cucsBiosVfPSTATECoordinationEntry 3 }

cucsBiosVfPSTATECoordinationVpPSTATECoordination OBJECT-TYPE
    SYNTAX       CucsBiosVfPSTATECoordinationVpPSTATECoordination
    MAX-ACCESS   read-only
    STATUS       current
    DESCRIPTION
        "Cisco UCS bios:VfPSTATECoordination:vpPSTATECoordination
        managed object property"
    ::= { cucsBiosVfPSTATECoordinationEntry 4 }

cucsBiosVfPSTATECoordinationPropAcl OBJECT-TYPE
    SYNTAX       Unsigned64
    MAX-ACCESS   read-only
    STATUS       current
    DESCRIPTION
        "Cisco UCS bios:VfPSTATECoordination:propAcl managed
        object property"
    ::= { cucsBiosVfPSTATECoordinationEntry 5 }

cucsBiosVfPSTATECoordinationSupportedByDefault OBJECT-TYPE
    SYNTAX       CucsBiosSupportedAction
    MAX-ACCESS   read-only
    STATUS       current
    DESCRIPTION
        "Cisco UCS bios:VfPSTATECoordination:supportedByDefault
        managed object property"
    ::= { cucsBiosVfPSTATECoordinationEntry 6 }

cucsBiosVfPackageCStateLimitTable OBJECT-TYPE
    SYNTAX           SEQUENCE OF CucsBiosVfPackageCStateLimitEntry
    MAX-ACCESS       not-accessible
    STATUS           current
    DESCRIPTION
        "Cisco UCS bios:VfPackageCStateLimit managed object table"
    ::= { cucsBiosObjects 56 }

cucsBiosVfPackageCStateLimitEntry OBJECT-TYPE
    SYNTAX           CucsBiosVfPackageCStateLimitEntry
    MAX-ACCESS       not-accessible
    STATUS           current
    DESCRIPTION
        "Entry for the cucsBiosVfPackageCStateLimitTable table."
    INDEX { cucsBiosVfPackageCStateLimitInstanceId }
    ::= { cucsBiosVfPackageCStateLimitTable 1 }

CucsBiosVfPackageCStateLimitEntry ::= SEQUENCE {
    cucsBiosVfPackageCStateLimitInstanceId                           CucsManagedObjectId,
    cucsBiosVfPackageCStateLimitDn                                   CucsManagedObjectDn,
    cucsBiosVfPackageCStateLimitRn                                   SnmpAdminString,
    cucsBiosVfPackageCStateLimitVpPackageCStateLimit                 CucsBiosVfPackageCStateLimitVpPackageCStateLimit,
    cucsBiosVfPackageCStateLimitPropAcl                              Unsigned64,
    cucsBiosVfPackageCStateLimitSupportedByDefault                   CucsBiosSupportedAction
}

cucsBiosVfPackageCStateLimitInstanceId OBJECT-TYPE
    SYNTAX       CucsManagedObjectId
    MAX-ACCESS   not-accessible
    STATUS       current
    DESCRIPTION
        "Instance identifier of the managed object."
    ::= { cucsBiosVfPackageCStateLimitEntry 1 }

cucsBiosVfPackageCStateLimitDn OBJECT-TYPE
    SYNTAX       CucsManagedObjectDn
    MAX-ACCESS   read-only
    STATUS       current
    DESCRIPTION
        "Cisco UCS bios:VfPackageCStateLimit:dn managed object property"
    ::= { cucsBiosVfPackageCStateLimitEntry 2 }

cucsBiosVfPackageCStateLimitRn OBJECT-TYPE
    SYNTAX       SnmpAdminString
    MAX-ACCESS   read-only
    STATUS       current
    DESCRIPTION
        "Cisco UCS bios:VfPackageCStateLimit:rn managed object property"
    ::= { cucsBiosVfPackageCStateLimitEntry 3 }

cucsBiosVfPackageCStateLimitVpPackageCStateLimit OBJECT-TYPE
    SYNTAX       CucsBiosVfPackageCStateLimitVpPackageCStateLimit
    MAX-ACCESS   read-only
    STATUS       current
    DESCRIPTION
        "Cisco UCS bios:VfPackageCStateLimit:vpPackageCStateLimit
        managed object property"
    ::= { cucsBiosVfPackageCStateLimitEntry 4 }

cucsBiosVfPackageCStateLimitPropAcl OBJECT-TYPE
    SYNTAX       Unsigned64
    MAX-ACCESS   read-only
    STATUS       current
    DESCRIPTION
        "Cisco UCS bios:VfPackageCStateLimit:propAcl managed
        object property"
    ::= { cucsBiosVfPackageCStateLimitEntry 5 }

cucsBiosVfPackageCStateLimitSupportedByDefault OBJECT-TYPE
    SYNTAX       CucsBiosSupportedAction
    MAX-ACCESS   read-only
    STATUS       current
    DESCRIPTION
        "Cisco UCS bios:VfPackageCStateLimit:supportedByDefault
        managed object property"
    ::= { cucsBiosVfPackageCStateLimitEntry 6 }

cucsBiosVfProcessorC1ETable OBJECT-TYPE
    SYNTAX           SEQUENCE OF CucsBiosVfProcessorC1EEntry
    MAX-ACCESS       not-accessible
    STATUS           current
    DESCRIPTION
        "Cisco UCS bios:VfProcessorC1E managed object table"
    ::= { cucsBiosObjects 57 }

cucsBiosVfProcessorC1EEntry OBJECT-TYPE
    SYNTAX           CucsBiosVfProcessorC1EEntry
    MAX-ACCESS       not-accessible
    STATUS           current
    DESCRIPTION
        "Entry for the cucsBiosVfProcessorC1ETable table."
    INDEX { cucsBiosVfProcessorC1EInstanceId }
    ::= { cucsBiosVfProcessorC1ETable 1 }

CucsBiosVfProcessorC1EEntry ::= SEQUENCE {
    cucsBiosVfProcessorC1EInstanceId                                 CucsManagedObjectId,
    cucsBiosVfProcessorC1EDn                                         CucsManagedObjectDn,
    cucsBiosVfProcessorC1ERn                                         SnmpAdminString,
    cucsBiosVfProcessorC1EVpProcessorC1E                             CucsBiosVfProcessorC1EVpProcessorC1E,
    cucsBiosVfProcessorC1EPropAcl                                    Unsigned64,
    cucsBiosVfProcessorC1ESupportedByDefault                         CucsBiosSupportedAction
}

cucsBiosVfProcessorC1EInstanceId OBJECT-TYPE
    SYNTAX       CucsManagedObjectId
    MAX-ACCESS   not-accessible
    STATUS       current
    DESCRIPTION
        "Instance identifier of the managed object."
    ::= { cucsBiosVfProcessorC1EEntry 1 }

cucsBiosVfProcessorC1EDn OBJECT-TYPE
    SYNTAX       CucsManagedObjectDn
    MAX-ACCESS   read-only
    STATUS       current
    DESCRIPTION
        "Cisco UCS bios:VfProcessorC1E:dn managed object property"
    ::= { cucsBiosVfProcessorC1EEntry 2 }

cucsBiosVfProcessorC1ERn OBJECT-TYPE
    SYNTAX       SnmpAdminString
    MAX-ACCESS   read-only
    STATUS       current
    DESCRIPTION
        "Cisco UCS bios:VfProcessorC1E:rn managed object property"
    ::= { cucsBiosVfProcessorC1EEntry 3 }

cucsBiosVfProcessorC1EVpProcessorC1E OBJECT-TYPE
    SYNTAX       CucsBiosVfProcessorC1EVpProcessorC1E
    MAX-ACCESS   read-only
    STATUS       current
    DESCRIPTION
        "Cisco UCS bios:VfProcessorC1E:vpProcessorC1E managed
        object property"
    ::= { cucsBiosVfProcessorC1EEntry 4 }

cucsBiosVfProcessorC1EPropAcl OBJECT-TYPE
    SYNTAX       Unsigned64
    MAX-ACCESS   read-only
    STATUS       current
    DESCRIPTION
        "Cisco UCS bios:VfProcessorC1E:propAcl managed object property"
    ::= { cucsBiosVfProcessorC1EEntry 5 }

cucsBiosVfProcessorC1ESupportedByDefault OBJECT-TYPE
    SYNTAX       CucsBiosSupportedAction
    MAX-ACCESS   read-only
    STATUS       current
    DESCRIPTION
        "Cisco UCS bios:VfProcessorC1E:supportedByDefault
        managed object property"
    ::= { cucsBiosVfProcessorC1EEntry 6 }

cucsBiosVfProcessorC3ReportTable OBJECT-TYPE
    SYNTAX           SEQUENCE OF CucsBiosVfProcessorC3ReportEntry
    MAX-ACCESS       not-accessible
    STATUS           current
    DESCRIPTION
        "Cisco UCS bios:VfProcessorC3Report managed object table"
    ::= { cucsBiosObjects 22 }

cucsBiosVfProcessorC3ReportEntry OBJECT-TYPE
    SYNTAX           CucsBiosVfProcessorC3ReportEntry
    MAX-ACCESS       not-accessible
    STATUS           current
    DESCRIPTION
        "Entry for the cucsBiosVfProcessorC3ReportTable table."
    INDEX { cucsBiosVfProcessorC3ReportInstanceId }
    ::= { cucsBiosVfProcessorC3ReportTable 1 }

CucsBiosVfProcessorC3ReportEntry ::= SEQUENCE {
    cucsBiosVfProcessorC3ReportInstanceId                            CucsManagedObjectId,
    cucsBiosVfProcessorC3ReportDn                                    CucsManagedObjectDn,
    cucsBiosVfProcessorC3ReportRn                                    SnmpAdminString,
    cucsBiosVfProcessorC3ReportVpProcessorC3Report                   CucsBiosVfProcessorC3ReportVpProcessorC3Report,
    cucsBiosVfProcessorC3ReportPropAcl                               Unsigned64,
    cucsBiosVfProcessorC3ReportSupportedByDefault                    CucsBiosSupportedAction
}

cucsBiosVfProcessorC3ReportInstanceId OBJECT-TYPE
    SYNTAX       CucsManagedObjectId
    MAX-ACCESS   not-accessible
    STATUS       current
    DESCRIPTION
        "Instance identifier of the managed object."
    ::= { cucsBiosVfProcessorC3ReportEntry 1 }

cucsBiosVfProcessorC3ReportDn OBJECT-TYPE
    SYNTAX       CucsManagedObjectDn
    MAX-ACCESS   read-only
    STATUS       current
    DESCRIPTION
        "Cisco UCS bios:VfProcessorC3Report:dn managed object property"
    ::= { cucsBiosVfProcessorC3ReportEntry 2 }

cucsBiosVfProcessorC3ReportRn OBJECT-TYPE
    SYNTAX       SnmpAdminString
    MAX-ACCESS   read-only
    STATUS       current
    DESCRIPTION
        "Cisco UCS bios:VfProcessorC3Report:rn managed object property"
    ::= { cucsBiosVfProcessorC3ReportEntry 3 }

cucsBiosVfProcessorC3ReportVpProcessorC3Report OBJECT-TYPE
    SYNTAX       CucsBiosVfProcessorC3ReportVpProcessorC3Report
    MAX-ACCESS   read-only
    STATUS       current
    DESCRIPTION
        "Cisco UCS bios:VfProcessorC3Report:vpProcessorC3Report
        managed object property"
    ::= { cucsBiosVfProcessorC3ReportEntry 4 }

cucsBiosVfProcessorC3ReportPropAcl OBJECT-TYPE
    SYNTAX       Unsigned64
    MAX-ACCESS   read-only
    STATUS       current
    DESCRIPTION
        "Cisco UCS bios:VfProcessorC3Report:propAcl managed
        object property"
    ::= { cucsBiosVfProcessorC3ReportEntry 5 }

cucsBiosVfProcessorC3ReportSupportedByDefault OBJECT-TYPE
    SYNTAX       CucsBiosSupportedAction
    MAX-ACCESS   read-only
    STATUS       current
    DESCRIPTION
        "Cisco UCS bios:VfProcessorC3Report:supportedByDefault
        managed object property"
    ::= { cucsBiosVfProcessorC3ReportEntry 6 }

cucsBiosVfProcessorC6ReportTable OBJECT-TYPE
    SYNTAX           SEQUENCE OF CucsBiosVfProcessorC6ReportEntry
    MAX-ACCESS       not-accessible
    STATUS           current
    DESCRIPTION
        "Cisco UCS bios:VfProcessorC6Report managed object table"
    ::= { cucsBiosObjects 23 }

cucsBiosVfProcessorC6ReportEntry OBJECT-TYPE
    SYNTAX           CucsBiosVfProcessorC6ReportEntry
    MAX-ACCESS       not-accessible
    STATUS           current
    DESCRIPTION
        "Entry for the cucsBiosVfProcessorC6ReportTable table."
    INDEX { cucsBiosVfProcessorC6ReportInstanceId }
    ::= { cucsBiosVfProcessorC6ReportTable 1 }

CucsBiosVfProcessorC6ReportEntry ::= SEQUENCE {
    cucsBiosVfProcessorC6ReportInstanceId                            CucsManagedObjectId,
    cucsBiosVfProcessorC6ReportDn                                    CucsManagedObjectDn,
    cucsBiosVfProcessorC6ReportRn                                    SnmpAdminString,
    cucsBiosVfProcessorC6ReportVpProcessorC6Report                   CucsBiosVfProcessorC6ReportVpProcessorC6Report,
    cucsBiosVfProcessorC6ReportPropAcl                               Unsigned64,
    cucsBiosVfProcessorC6ReportSupportedByDefault                    CucsBiosSupportedAction
}

cucsBiosVfProcessorC6ReportInstanceId OBJECT-TYPE
    SYNTAX       CucsManagedObjectId
    MAX-ACCESS   not-accessible
    STATUS       current
    DESCRIPTION
        "Instance identifier of the managed object."
    ::= { cucsBiosVfProcessorC6ReportEntry 1 }

cucsBiosVfProcessorC6ReportDn OBJECT-TYPE
    SYNTAX       CucsManagedObjectDn
    MAX-ACCESS   read-only
    STATUS       current
    DESCRIPTION
        "Cisco UCS bios:VfProcessorC6Report:dn managed object property"
    ::= { cucsBiosVfProcessorC6ReportEntry 2 }

cucsBiosVfProcessorC6ReportRn OBJECT-TYPE
    SYNTAX       SnmpAdminString
    MAX-ACCESS   read-only
    STATUS       current
    DESCRIPTION
        "Cisco UCS bios:VfProcessorC6Report:rn managed object property"
    ::= { cucsBiosVfProcessorC6ReportEntry 3 }

cucsBiosVfProcessorC6ReportVpProcessorC6Report OBJECT-TYPE
    SYNTAX       CucsBiosVfProcessorC6ReportVpProcessorC6Report
    MAX-ACCESS   read-only
    STATUS       current
    DESCRIPTION
        "Cisco UCS bios:VfProcessorC6Report:vpProcessorC6Report
        managed object property"
    ::= { cucsBiosVfProcessorC6ReportEntry 4 }

cucsBiosVfProcessorC6ReportPropAcl OBJECT-TYPE
    SYNTAX       Unsigned64
    MAX-ACCESS   read-only
    STATUS       current
    DESCRIPTION
        "Cisco UCS bios:VfProcessorC6Report:propAcl managed
        object property"
    ::= { cucsBiosVfProcessorC6ReportEntry 5 }

cucsBiosVfProcessorC6ReportSupportedByDefault OBJECT-TYPE
    SYNTAX       CucsBiosSupportedAction
    MAX-ACCESS   read-only
    STATUS       current
    DESCRIPTION
        "Cisco UCS bios:VfProcessorC6Report:supportedByDefault
        managed object property"
    ::= { cucsBiosVfProcessorC6ReportEntry 6 }

cucsBiosVfProcessorC7ReportTable OBJECT-TYPE
    SYNTAX           SEQUENCE OF CucsBiosVfProcessorC7ReportEntry
    MAX-ACCESS       not-accessible
    STATUS           current
    DESCRIPTION
        "Cisco UCS bios:VfProcessorC7Report managed object table"
    ::= { cucsBiosObjects 58 }

cucsBiosVfProcessorC7ReportEntry OBJECT-TYPE
    SYNTAX           CucsBiosVfProcessorC7ReportEntry
    MAX-ACCESS       not-accessible
    STATUS           current
    DESCRIPTION
        "Entry for the cucsBiosVfProcessorC7ReportTable table."
    INDEX { cucsBiosVfProcessorC7ReportInstanceId }
    ::= { cucsBiosVfProcessorC7ReportTable 1 }

CucsBiosVfProcessorC7ReportEntry ::= SEQUENCE {
    cucsBiosVfProcessorC7ReportInstanceId                            CucsManagedObjectId,
    cucsBiosVfProcessorC7ReportDn                                    CucsManagedObjectDn,
    cucsBiosVfProcessorC7ReportRn                                    SnmpAdminString,
    cucsBiosVfProcessorC7ReportVpProcessorC7Report                   CucsBiosVfProcessorC7ReportVpProcessorC7Report,
    cucsBiosVfProcessorC7ReportPropAcl                               Unsigned64,
    cucsBiosVfProcessorC7ReportSupportedByDefault                    CucsBiosSupportedAction
}

cucsBiosVfProcessorC7ReportInstanceId OBJECT-TYPE
    SYNTAX       CucsManagedObjectId
    MAX-ACCESS   not-accessible
    STATUS       current
    DESCRIPTION
        "Instance identifier of the managed object."
    ::= { cucsBiosVfProcessorC7ReportEntry 1 }

cucsBiosVfProcessorC7ReportDn OBJECT-TYPE
    SYNTAX       CucsManagedObjectDn
    MAX-ACCESS   read-only
    STATUS       current
    DESCRIPTION
        "Cisco UCS bios:VfProcessorC7Report:dn managed object property"
    ::= { cucsBiosVfProcessorC7ReportEntry 2 }

cucsBiosVfProcessorC7ReportRn OBJECT-TYPE
    SYNTAX       SnmpAdminString
    MAX-ACCESS   read-only
    STATUS       current
    DESCRIPTION
        "Cisco UCS bios:VfProcessorC7Report:rn managed object property"
    ::= { cucsBiosVfProcessorC7ReportEntry 3 }

cucsBiosVfProcessorC7ReportVpProcessorC7Report OBJECT-TYPE
    SYNTAX       CucsBiosVfProcessorC7ReportVpProcessorC7Report
    MAX-ACCESS   read-only
    STATUS       current
    DESCRIPTION
        "Cisco UCS bios:VfProcessorC7Report:vpProcessorC7Report
        managed object property"
    ::= { cucsBiosVfProcessorC7ReportEntry 4 }

cucsBiosVfProcessorC7ReportPropAcl OBJECT-TYPE
    SYNTAX       Unsigned64
    MAX-ACCESS   read-only
    STATUS       current
    DESCRIPTION
        "Cisco UCS bios:VfProcessorC7Report:propAcl managed
        object property"
    ::= { cucsBiosVfProcessorC7ReportEntry 5 }

cucsBiosVfProcessorC7ReportSupportedByDefault OBJECT-TYPE
    SYNTAX       CucsBiosSupportedAction
    MAX-ACCESS   read-only
    STATUS       current
    DESCRIPTION
        "Cisco UCS bios:VfProcessorC7Report:supportedByDefault
        managed object property"
    ::= { cucsBiosVfProcessorC7ReportEntry 6 }

cucsBiosVfProcessorCMCITable OBJECT-TYPE
    SYNTAX           SEQUENCE OF CucsBiosVfProcessorCMCIEntry
    MAX-ACCESS       not-accessible
    STATUS           current
    DESCRIPTION
        "Cisco UCS bios:VfProcessorCMCI managed object table"
    ::= { cucsBiosObjects 96 }

cucsBiosVfProcessorCMCIEntry OBJECT-TYPE
    SYNTAX           CucsBiosVfProcessorCMCIEntry
    MAX-ACCESS       not-accessible
    STATUS           current
    DESCRIPTION
        "Entry for the cucsBiosVfProcessorCMCITable table."
    INDEX { cucsBiosVfProcessorCMCIInstanceId }
    ::= { cucsBiosVfProcessorCMCITable 1 }

CucsBiosVfProcessorCMCIEntry ::= SEQUENCE {
    cucsBiosVfProcessorCMCIInstanceId                                CucsManagedObjectId,
    cucsBiosVfProcessorCMCIDn                                        CucsManagedObjectDn,
    cucsBiosVfProcessorCMCIRn                                        SnmpAdminString,
    cucsBiosVfProcessorCMCIVpProcessorCMCI                           CucsBiosVfProcessorCMCIVpProcessorCMCI,
    cucsBiosVfProcessorCMCIPropAcl                                   Unsigned64,
    cucsBiosVfProcessorCMCISupportedByDefault                        CucsBiosSupportedAction
}

cucsBiosVfProcessorCMCIInstanceId OBJECT-TYPE
    SYNTAX       CucsManagedObjectId
    MAX-ACCESS   not-accessible
    STATUS       current
    DESCRIPTION
        "Instance identifier of the managed object."
    ::= { cucsBiosVfProcessorCMCIEntry 1 }

cucsBiosVfProcessorCMCIDn OBJECT-TYPE
    SYNTAX       CucsManagedObjectDn
    MAX-ACCESS   read-only
    STATUS       current
    DESCRIPTION
        "Cisco UCS bios:VfProcessorCMCI:dn managed object property"
    ::= { cucsBiosVfProcessorCMCIEntry 2 }

cucsBiosVfProcessorCMCIRn OBJECT-TYPE
    SYNTAX       SnmpAdminString
    MAX-ACCESS   read-only
    STATUS       current
    DESCRIPTION
        "Cisco UCS bios:VfProcessorCMCI:rn managed object property"
    ::= { cucsBiosVfProcessorCMCIEntry 3 }

cucsBiosVfProcessorCMCIVpProcessorCMCI OBJECT-TYPE
    SYNTAX       CucsBiosVfProcessorCMCIVpProcessorCMCI
    MAX-ACCESS   read-only
    STATUS       current
    DESCRIPTION
        "Cisco UCS bios:VfProcessorCMCI:vpProcessorCMCI
        managed object property"
    ::= { cucsBiosVfProcessorCMCIEntry 4 }

cucsBiosVfProcessorCMCIPropAcl OBJECT-TYPE
    SYNTAX       Unsigned64
    MAX-ACCESS   read-only
    STATUS       current
    DESCRIPTION
        "Cisco UCS bios:VfProcessorCMCI:propAcl managed object property"
    ::= { cucsBiosVfProcessorCMCIEntry 5 }

cucsBiosVfProcessorCMCISupportedByDefault OBJECT-TYPE
    SYNTAX       CucsBiosSupportedAction
    MAX-ACCESS   read-only
    STATUS       current
    DESCRIPTION
        "Cisco UCS bios:VfProcessorCMCI:supportedByDefault
        managed object property"
    ::= { cucsBiosVfProcessorCMCIEntry 6 }

cucsBiosVfProcessorCStateTable OBJECT-TYPE
    SYNTAX           SEQUENCE OF CucsBiosVfProcessorCStateEntry
    MAX-ACCESS       not-accessible
    STATUS           current
    DESCRIPTION
        "Cisco UCS bios:VfProcessorCState managed object table"
    ::= { cucsBiosObjects 59 }

cucsBiosVfProcessorCStateEntry OBJECT-TYPE
    SYNTAX           CucsBiosVfProcessorCStateEntry
    MAX-ACCESS       not-accessible
    STATUS           current
    DESCRIPTION
        "Entry for the cucsBiosVfProcessorCStateTable table."
    INDEX { cucsBiosVfProcessorCStateInstanceId }
    ::= { cucsBiosVfProcessorCStateTable 1 }

CucsBiosVfProcessorCStateEntry ::= SEQUENCE {
    cucsBiosVfProcessorCStateInstanceId                              CucsManagedObjectId,
    cucsBiosVfProcessorCStateDn                                      CucsManagedObjectDn,
    cucsBiosVfProcessorCStateRn                                      SnmpAdminString,
    cucsBiosVfProcessorCStateVpProcessorCState                       CucsBiosVfProcessorCStateVpProcessorCState,
    cucsBiosVfProcessorCStatePropAcl                                 Unsigned64,
    cucsBiosVfProcessorCStateSupportedByDefault                      CucsBiosSupportedAction
}

cucsBiosVfProcessorCStateInstanceId OBJECT-TYPE
    SYNTAX       CucsManagedObjectId
    MAX-ACCESS   not-accessible
    STATUS       current
    DESCRIPTION
        "Instance identifier of the managed object."
    ::= { cucsBiosVfProcessorCStateEntry 1 }

cucsBiosVfProcessorCStateDn OBJECT-TYPE
    SYNTAX       CucsManagedObjectDn
    MAX-ACCESS   read-only
    STATUS       current
    DESCRIPTION
        "Cisco UCS bios:VfProcessorCState:dn managed object property"
    ::= { cucsBiosVfProcessorCStateEntry 2 }

cucsBiosVfProcessorCStateRn OBJECT-TYPE
    SYNTAX       SnmpAdminString
    MAX-ACCESS   read-only
    STATUS       current
    DESCRIPTION
        "Cisco UCS bios:VfProcessorCState:rn managed object property"
    ::= { cucsBiosVfProcessorCStateEntry 3 }

cucsBiosVfProcessorCStateVpProcessorCState OBJECT-TYPE
    SYNTAX       CucsBiosVfProcessorCStateVpProcessorCState
    MAX-ACCESS   read-only
    STATUS       current
    DESCRIPTION
        "Cisco UCS bios:VfProcessorCState:vpProcessorCState
        managed object property"
    ::= { cucsBiosVfProcessorCStateEntry 4 }

cucsBiosVfProcessorCStatePropAcl OBJECT-TYPE
    SYNTAX       Unsigned64
    MAX-ACCESS   read-only
    STATUS       current
    DESCRIPTION
        "Cisco UCS bios:VfProcessorCState:propAcl managed object property"
    ::= { cucsBiosVfProcessorCStateEntry 5 }

cucsBiosVfProcessorCStateSupportedByDefault OBJECT-TYPE
    SYNTAX       CucsBiosSupportedAction
    MAX-ACCESS   read-only
    STATUS       current
    DESCRIPTION
        "Cisco UCS bios:VfProcessorCState:supportedByDefault
        managed object property"
    ::= { cucsBiosVfProcessorCStateEntry 6 }

cucsBiosVfProcessorEnergyConfigurationTable OBJECT-TYPE
    SYNTAX           SEQUENCE OF CucsBiosVfProcessorEnergyConfigurationEntry
    MAX-ACCESS       not-accessible
    STATUS           current
    DESCRIPTION
        "Cisco UCS bios:VfProcessorEnergyConfiguration
        managed object table"
    ::= { cucsBiosObjects 72 }

cucsBiosVfProcessorEnergyConfigurationEntry OBJECT-TYPE
    SYNTAX           CucsBiosVfProcessorEnergyConfigurationEntry
    MAX-ACCESS       not-accessible
    STATUS           current
    DESCRIPTION
        "Entry for the cucsBiosVfProcessorEnergyConfigurationTable table."
    INDEX { cucsBiosVfProcessorEnergyConfigurationInstanceId }
    ::= { cucsBiosVfProcessorEnergyConfigurationTable 1 }

CucsBiosVfProcessorEnergyConfigurationEntry ::= SEQUENCE {
    cucsBiosVfProcessorEnergyConfigurationInstanceId                 CucsManagedObjectId,
    cucsBiosVfProcessorEnergyConfigurationDn                         CucsManagedObjectDn,
    cucsBiosVfProcessorEnergyConfigurationRn                         SnmpAdminString,
    cucsBiosVfProcessorEnergyConfigurationVpEnergyPerformance        CucsBiosVfProcessorEnergyConfigurationVpEnergyPerformance,
    cucsBiosVfProcessorEnergyConfigurationVpPowerTechnology          CucsBiosVfProcessorEnergyConfigurationVpPowerTechnology,
    cucsBiosVfProcessorEnergyConfigurationPropAcl                    Unsigned64,
    cucsBiosVfProcessorEnergyConfigurationSupportedByDefault         CucsBiosSupportedAction
}

cucsBiosVfProcessorEnergyConfigurationInstanceId OBJECT-TYPE
    SYNTAX       CucsManagedObjectId
    MAX-ACCESS   not-accessible
    STATUS       current
    DESCRIPTION
        "Instance identifier of the managed object."
    ::= { cucsBiosVfProcessorEnergyConfigurationEntry 1 }

cucsBiosVfProcessorEnergyConfigurationDn OBJECT-TYPE
    SYNTAX       CucsManagedObjectDn
    MAX-ACCESS   read-only
    STATUS       current
    DESCRIPTION
        "Cisco UCS bios:VfProcessorEnergyConfiguration:dn
        managed object property"
    ::= { cucsBiosVfProcessorEnergyConfigurationEntry 2 }

cucsBiosVfProcessorEnergyConfigurationRn OBJECT-TYPE
    SYNTAX       SnmpAdminString
    MAX-ACCESS   read-only
    STATUS       current
    DESCRIPTION
        "Cisco UCS bios:VfProcessorEnergyConfiguration:rn
        managed object property"
    ::= { cucsBiosVfProcessorEnergyConfigurationEntry 3 }

cucsBiosVfProcessorEnergyConfigurationVpEnergyPerformance OBJECT-TYPE
    SYNTAX       CucsBiosVfProcessorEnergyConfigurationVpEnergyPerformance
    MAX-ACCESS   read-only
    STATUS       current
    DESCRIPTION
        "Cisco UCS bios:VfProcessorEnergyConfiguration:vpEnergyPerformance
         managed object property"
    ::= { cucsBiosVfProcessorEnergyConfigurationEntry 4 }

cucsBiosVfProcessorEnergyConfigurationVpPowerTechnology OBJECT-TYPE
    SYNTAX       CucsBiosVfProcessorEnergyConfigurationVpPowerTechnology
    MAX-ACCESS   read-only
    STATUS       current
    DESCRIPTION
        "Cisco UCS bios:VfProcessorEnergyConfiguration:vpPowerTechnology
        managed object property"
    ::= { cucsBiosVfProcessorEnergyConfigurationEntry 5 }

cucsBiosVfProcessorEnergyConfigurationPropAcl OBJECT-TYPE
    SYNTAX       Unsigned64
    MAX-ACCESS   read-only
    STATUS       current
    DESCRIPTION
        "Cisco UCS bios:VfProcessorEnergyConfiguration:propAcl
        managed object property"
    ::= { cucsBiosVfProcessorEnergyConfigurationEntry 6 }

cucsBiosVfProcessorEnergyConfigurationSupportedByDefault OBJECT-TYPE
    SYNTAX       CucsBiosSupportedAction
    MAX-ACCESS   read-only
    STATUS       current
    DESCRIPTION
        "Cisco UCS bios:VfProcessorEnergyConfiguration:supportedByDefault
        managed object property"
    ::= { cucsBiosVfProcessorEnergyConfigurationEntry 7 }

cucsBiosVfProcessorPrefetchConfigTable OBJECT-TYPE
    SYNTAX           SEQUENCE OF CucsBiosVfProcessorPrefetchConfigEntry
    MAX-ACCESS       not-accessible
    STATUS           current
    DESCRIPTION
        "Cisco UCS bios:VfProcessorPrefetchConfig managed object table"
    ::= { cucsBiosObjects 73 }

cucsBiosVfProcessorPrefetchConfigEntry OBJECT-TYPE
    SYNTAX           CucsBiosVfProcessorPrefetchConfigEntry
    MAX-ACCESS       not-accessible
    STATUS           current
    DESCRIPTION
        "Entry for the cucsBiosVfProcessorPrefetchConfigTable table."
    INDEX { cucsBiosVfProcessorPrefetchConfigInstanceId }
    ::= { cucsBiosVfProcessorPrefetchConfigTable 1 }

CucsBiosVfProcessorPrefetchConfigEntry ::= SEQUENCE {
    cucsBiosVfProcessorPrefetchConfigInstanceId                      CucsManagedObjectId,
    cucsBiosVfProcessorPrefetchConfigDn                              CucsManagedObjectDn,
    cucsBiosVfProcessorPrefetchConfigRn                              SnmpAdminString,
    cucsBiosVfProcessorPrefetchConfigVpAdjacentCacheLinePrefetcher   CucsBiosVfProcessorPrefetchConfigVpAdjacentCacheLinePrefetcher,
    cucsBiosVfProcessorPrefetchConfigVpDCUIPPrefetcher               CucsBiosVfProcessorPrefetchConfigVpDCUIPPrefetcher,
    cucsBiosVfProcessorPrefetchConfigVpDCUStreamerPrefetch           CucsBiosVfProcessorPrefetchConfigVpDCUStreamerPrefetch,
    cucsBiosVfProcessorPrefetchConfigVpHardwarePrefetcher            CucsBiosVfProcessorPrefetchConfigVpHardwarePrefetcher,
    cucsBiosVfProcessorPrefetchConfigPropAcl                         Unsigned64,
    cucsBiosVfProcessorPrefetchConfigSupportedByDefault              CucsBiosSupportedAction
}

cucsBiosVfProcessorPrefetchConfigInstanceId OBJECT-TYPE
    SYNTAX       CucsManagedObjectId
    MAX-ACCESS   not-accessible
    STATUS       current
    DESCRIPTION
        "Instance identifier of the managed object."
    ::= { cucsBiosVfProcessorPrefetchConfigEntry 1 }

cucsBiosVfProcessorPrefetchConfigDn OBJECT-TYPE
    SYNTAX       CucsManagedObjectDn
    MAX-ACCESS   read-only
    STATUS       current
    DESCRIPTION
        "Cisco UCS bios:VfProcessorPrefetchConfig:dn managed
        object property"
    ::= { cucsBiosVfProcessorPrefetchConfigEntry 2 }

cucsBiosVfProcessorPrefetchConfigRn OBJECT-TYPE
    SYNTAX       SnmpAdminString
    MAX-ACCESS   read-only
    STATUS       current
    DESCRIPTION
        "Cisco UCS bios:VfProcessorPrefetchConfig:rn managed
        object property"
    ::= { cucsBiosVfProcessorPrefetchConfigEntry 3 }

cucsBiosVfProcessorPrefetchConfigVpAdjacentCacheLinePrefetcher OBJECT-TYPE
    SYNTAX       CucsBiosVfProcessorPrefetchConfigVpAdjacentCacheLinePrefetcher
    MAX-ACCESS   read-only
    STATUS       current
    DESCRIPTION
        "Cisco UCS bios:VfProcessorPrefetchConfig:vpAdjacentCacheLinePrefe
        tcher managed object property"
    ::= { cucsBiosVfProcessorPrefetchConfigEntry 4 }

cucsBiosVfProcessorPrefetchConfigVpDCUIPPrefetcher OBJECT-TYPE
    SYNTAX       CucsBiosVfProcessorPrefetchConfigVpDCUIPPrefetcher
    MAX-ACCESS   read-only
    STATUS       current
    DESCRIPTION
        "Cisco UCS bios:VfProcessorPrefetchConfig:vpDCUIPPrefetcher
        managed object property"
    ::= { cucsBiosVfProcessorPrefetchConfigEntry 5 }

cucsBiosVfProcessorPrefetchConfigVpDCUStreamerPrefetch OBJECT-TYPE
    SYNTAX       CucsBiosVfProcessorPrefetchConfigVpDCUStreamerPrefetch
    MAX-ACCESS   read-only
    STATUS       current
    DESCRIPTION
        "Cisco UCS bios:VfProcessorPrefetchConfig:vpDCUStreamerPrefetch
        managed object property"
    ::= { cucsBiosVfProcessorPrefetchConfigEntry 6 }

cucsBiosVfProcessorPrefetchConfigVpHardwarePrefetcher OBJECT-TYPE
    SYNTAX       CucsBiosVfProcessorPrefetchConfigVpHardwarePrefetcher
    MAX-ACCESS   read-only
    STATUS       current
    DESCRIPTION
        "Cisco UCS bios:VfProcessorPrefetchConfig:vpHardwarePrefetcher
        managed object property"
    ::= { cucsBiosVfProcessorPrefetchConfigEntry 7 }

cucsBiosVfProcessorPrefetchConfigPropAcl OBJECT-TYPE
    SYNTAX       Unsigned64
    MAX-ACCESS   read-only
    STATUS       current
    DESCRIPTION
        "Cisco UCS bios:VfProcessorPrefetchConfig:propAcl
        managed object property"
    ::= { cucsBiosVfProcessorPrefetchConfigEntry 8 }

cucsBiosVfProcessorPrefetchConfigSupportedByDefault OBJECT-TYPE
    SYNTAX       CucsBiosSupportedAction
    MAX-ACCESS   read-only
    STATUS       current
    DESCRIPTION
        "Cisco UCS bios:VfProcessorPrefetchConfig:supportedByDefault
        managed object property"
    ::= { cucsBiosVfProcessorPrefetchConfigEntry 9 }

cucsBiosVfQPILinkFrequencySelectTable OBJECT-TYPE
    SYNTAX           SEQUENCE OF CucsBiosVfQPILinkFrequencySelectEntry
    MAX-ACCESS       not-accessible
    STATUS           current
    DESCRIPTION
        "Cisco UCS bios:VfQPILinkFrequencySelect managed object table"
    ::= { cucsBiosObjects 74 }

cucsBiosVfQPILinkFrequencySelectEntry OBJECT-TYPE
    SYNTAX           CucsBiosVfQPILinkFrequencySelectEntry
    MAX-ACCESS       not-accessible
    STATUS           current
    DESCRIPTION
        "Entry for the cucsBiosVfQPILinkFrequencySelectTable table."
    INDEX { cucsBiosVfQPILinkFrequencySelectInstanceId }
    ::= { cucsBiosVfQPILinkFrequencySelectTable 1 }

CucsBiosVfQPILinkFrequencySelectEntry ::= SEQUENCE {
    cucsBiosVfQPILinkFrequencySelectInstanceId                       CucsManagedObjectId,
    cucsBiosVfQPILinkFrequencySelectDn                               CucsManagedObjectDn,
    cucsBiosVfQPILinkFrequencySelectRn                               SnmpAdminString,
    cucsBiosVfQPILinkFrequencySelectVpQPILinkFrequencySelect         CucsBiosVfQPILinkFrequencySelectVpQPILinkFrequencySelect,
    cucsBiosVfQPILinkFrequencySelectPropAcl                          Unsigned64,
    cucsBiosVfQPILinkFrequencySelectSupportedByDefault               CucsBiosSupportedAction
}

cucsBiosVfQPILinkFrequencySelectInstanceId OBJECT-TYPE
    SYNTAX       CucsManagedObjectId
    MAX-ACCESS   not-accessible
    STATUS       current
    DESCRIPTION
        "Instance identifier of the managed object."
    ::= { cucsBiosVfQPILinkFrequencySelectEntry 1 }

cucsBiosVfQPILinkFrequencySelectDn OBJECT-TYPE
    SYNTAX       CucsManagedObjectDn
    MAX-ACCESS   read-only
    STATUS       current
    DESCRIPTION
        "Cisco UCS bios:VfQPILinkFrequencySelect:dn managed
        object property"
    ::= { cucsBiosVfQPILinkFrequencySelectEntry 2 }

cucsBiosVfQPILinkFrequencySelectRn OBJECT-TYPE
    SYNTAX       SnmpAdminString
    MAX-ACCESS   read-only
    STATUS       current
    DESCRIPTION
        "Cisco UCS bios:VfQPILinkFrequencySelect:rn managed
        object property"
    ::= { cucsBiosVfQPILinkFrequencySelectEntry 3 }

cucsBiosVfQPILinkFrequencySelectVpQPILinkFrequencySelect OBJECT-TYPE
    SYNTAX       CucsBiosVfQPILinkFrequencySelectVpQPILinkFrequencySelect
    MAX-ACCESS   read-only
    STATUS       current
    DESCRIPTION
        "Cisco UCS bios:VfQPILinkFrequencySelect:vpQPILinkFrequencySelect
        managed object property"
    ::= { cucsBiosVfQPILinkFrequencySelectEntry 4 }

cucsBiosVfQPILinkFrequencySelectPropAcl OBJECT-TYPE
    SYNTAX       Unsigned64
    MAX-ACCESS   read-only
    STATUS       current
    DESCRIPTION
        "Cisco UCS bios:VfQPILinkFrequencySelect:propAcl
        managed object property"
    ::= { cucsBiosVfQPILinkFrequencySelectEntry 5 }

cucsBiosVfQPILinkFrequencySelectSupportedByDefault OBJECT-TYPE
    SYNTAX       CucsBiosSupportedAction
    MAX-ACCESS   read-only
    STATUS       current
    DESCRIPTION
        "Cisco UCS bios:VfQPILinkFrequencySelect:supportedByDefault
        managed object property"
    ::= { cucsBiosVfQPILinkFrequencySelectEntry 6 }

cucsBiosVfQPISnoopModeTable OBJECT-TYPE
    SYNTAX           SEQUENCE OF CucsBiosVfQPISnoopModeEntry
    MAX-ACCESS       not-accessible
    STATUS           current
    DESCRIPTION
        "Cisco UCS bios:VfQPISnoopMode managed object table"
    ::= { cucsBiosObjects 81 }

cucsBiosVfQPISnoopModeEntry OBJECT-TYPE
    SYNTAX           CucsBiosVfQPISnoopModeEntry
    MAX-ACCESS       not-accessible
    STATUS           current
    DESCRIPTION
        "Entry for the cucsBiosVfQPISnoopModeTable table."
    INDEX { cucsBiosVfQPISnoopModeInstanceId }
    ::= { cucsBiosVfQPISnoopModeTable 1 }

CucsBiosVfQPISnoopModeEntry ::= SEQUENCE {
    cucsBiosVfQPISnoopModeInstanceId                                 CucsManagedObjectId,
    cucsBiosVfQPISnoopModeDn                                         CucsManagedObjectDn,
    cucsBiosVfQPISnoopModeRn                                         SnmpAdminString,
    cucsBiosVfQPISnoopModeVpQPISnoopMode                             CucsBiosVfQPISnoopModeVpQPISnoopMode,
    cucsBiosVfQPISnoopModePropAcl                                    Unsigned64,
    cucsBiosVfQPISnoopModeSupportedByDefault                         CucsBiosSupportedAction
}

cucsBiosVfQPISnoopModeInstanceId OBJECT-TYPE
    SYNTAX       CucsManagedObjectId
    MAX-ACCESS   not-accessible
    STATUS       current
    DESCRIPTION
        "Instance identifier of the managed object."
    ::= { cucsBiosVfQPISnoopModeEntry 1 }

cucsBiosVfQPISnoopModeDn OBJECT-TYPE
    SYNTAX       CucsManagedObjectDn
    MAX-ACCESS   read-only
    STATUS       current
    DESCRIPTION
        "Cisco UCS bios:VfQPISnoopMode:dn managed object property"
    ::= { cucsBiosVfQPISnoopModeEntry 2 }

cucsBiosVfQPISnoopModeRn OBJECT-TYPE
    SYNTAX       SnmpAdminString
    MAX-ACCESS   read-only
    STATUS       current
    DESCRIPTION
        "Cisco UCS bios:VfQPISnoopMode:rn managed object property"
    ::= { cucsBiosVfQPISnoopModeEntry 3 }

cucsBiosVfQPISnoopModeVpQPISnoopMode OBJECT-TYPE
    SYNTAX       CucsBiosVfQPISnoopModeVpQPISnoopMode
    MAX-ACCESS   read-only
    STATUS       current
    DESCRIPTION
        "Cisco UCS bios:VfQPISnoopMode:vpQPISnoopMode managed
        object property"
    ::= { cucsBiosVfQPISnoopModeEntry 4 }

cucsBiosVfQPISnoopModePropAcl OBJECT-TYPE
    SYNTAX       Unsigned64
    MAX-ACCESS   read-only
    STATUS       current
    DESCRIPTION
        "Cisco UCS bios:VfQPISnoopMode:propAcl managed object property"
    ::= { cucsBiosVfQPISnoopModeEntry 5 }

cucsBiosVfQPISnoopModeSupportedByDefault OBJECT-TYPE
    SYNTAX       CucsBiosSupportedAction
    MAX-ACCESS   read-only
    STATUS       current
    DESCRIPTION
        "Cisco UCS bios:VfQPISnoopMode:supportedByDefault
        managed object property"
    ::= { cucsBiosVfQPISnoopModeEntry 6 }

cucsBiosVfQuietBootTable OBJECT-TYPE
    SYNTAX           SEQUENCE OF CucsBiosVfQuietBootEntry
    MAX-ACCESS       not-accessible
    STATUS           current
    DESCRIPTION
        "Cisco UCS bios:VfQuietBoot managed object table"
    ::= { cucsBiosObjects 24 }

cucsBiosVfQuietBootEntry OBJECT-TYPE
    SYNTAX           CucsBiosVfQuietBootEntry
    MAX-ACCESS       not-accessible
    STATUS           current
    DESCRIPTION
        "Entry for the cucsBiosVfQuietBootTable table."
    INDEX { cucsBiosVfQuietBootInstanceId }
    ::= { cucsBiosVfQuietBootTable 1 }

CucsBiosVfQuietBootEntry ::= SEQUENCE {
    cucsBiosVfQuietBootInstanceId                                    CucsManagedObjectId,
    cucsBiosVfQuietBootDn                                            CucsManagedObjectDn,
    cucsBiosVfQuietBootRn                                            SnmpAdminString,
    cucsBiosVfQuietBootVpQuietBoot                                   CucsBiosVfQuietBootVpQuietBoot,
    cucsBiosVfQuietBootPropAcl                                       Unsigned64,
    cucsBiosVfQuietBootSupportedByDefault                            CucsBiosSupportedAction
}

cucsBiosVfQuietBootInstanceId OBJECT-TYPE
    SYNTAX       CucsManagedObjectId
    MAX-ACCESS   not-accessible
    STATUS       current
    DESCRIPTION
        "Instance identifier of the managed object."
    ::= { cucsBiosVfQuietBootEntry 1 }

cucsBiosVfQuietBootDn OBJECT-TYPE
    SYNTAX       CucsManagedObjectDn
    MAX-ACCESS   read-only
    STATUS       current
    DESCRIPTION
        "Cisco UCS bios:VfQuietBoot:dn managed object property"
    ::= { cucsBiosVfQuietBootEntry 2 }

cucsBiosVfQuietBootRn OBJECT-TYPE
    SYNTAX       SnmpAdminString
    MAX-ACCESS   read-only
    STATUS       current
    DESCRIPTION
        "Cisco UCS bios:VfQuietBoot:rn managed object property"
    ::= { cucsBiosVfQuietBootEntry 3 }

cucsBiosVfQuietBootVpQuietBoot OBJECT-TYPE
    SYNTAX       CucsBiosVfQuietBootVpQuietBoot
    MAX-ACCESS   read-only
    STATUS       current
    DESCRIPTION
        "Cisco UCS bios:VfQuietBoot:vpQuietBoot managed object property"
    ::= { cucsBiosVfQuietBootEntry 4 }

cucsBiosVfQuietBootPropAcl OBJECT-TYPE
    SYNTAX       Unsigned64
    MAX-ACCESS   read-only
    STATUS       current
    DESCRIPTION
        "Cisco UCS bios:VfQuietBoot:propAcl managed object property"
    ::= { cucsBiosVfQuietBootEntry 5 }

cucsBiosVfQuietBootSupportedByDefault OBJECT-TYPE
    SYNTAX       CucsBiosSupportedAction
    MAX-ACCESS   read-only
    STATUS       current
    DESCRIPTION
        "Cisco UCS bios:VfQuietBoot:supportedByDefault
        managed object property"
    ::= { cucsBiosVfQuietBootEntry 6 }

cucsBiosVfRedirectionAfterBIOSPOSTTable OBJECT-TYPE
    SYNTAX           SEQUENCE OF CucsBiosVfRedirectionAfterBIOSPOSTEntry
    MAX-ACCESS       not-accessible
    STATUS           current
    DESCRIPTION
        "Cisco UCS bios:VfRedirectionAfterBIOSPOST managed object table"
    ::= { cucsBiosObjects 105 }

cucsBiosVfRedirectionAfterBIOSPOSTEntry OBJECT-TYPE
    SYNTAX           CucsBiosVfRedirectionAfterBIOSPOSTEntry
    MAX-ACCESS       not-accessible
    STATUS           current
    DESCRIPTION
        "Entry for the cucsBiosVfRedirectionAfterBIOSPOSTTable table."
    INDEX { cucsBiosVfRedirectionAfterBIOSPOSTInstanceId }
    ::= { cucsBiosVfRedirectionAfterBIOSPOSTTable 1 }

CucsBiosVfRedirectionAfterBIOSPOSTEntry ::= SEQUENCE {
    cucsBiosVfRedirectionAfterBIOSPOSTInstanceId                     CucsManagedObjectId,
    cucsBiosVfRedirectionAfterBIOSPOSTDn                             CucsManagedObjectDn,
    cucsBiosVfRedirectionAfterBIOSPOSTRn                             SnmpAdminString,
    cucsBiosVfRedirectionAfterBIOSPOSTPropAcl                        Unsigned64,
    cucsBiosVfRedirectionAfterBIOSPOSTSupportedByDefault             CucsBiosSupportedAction,
    cucsBiosVfRedirectionAfterBIOSPOSTVpRedirectionAfterPOST         CucsBiosVfRedirectionAfterBIOSPOSTVpRedirectionAfterPOST
}

cucsBiosVfRedirectionAfterBIOSPOSTInstanceId OBJECT-TYPE
    SYNTAX       CucsManagedObjectId
    MAX-ACCESS   not-accessible
    STATUS       current
    DESCRIPTION
        "Instance identifier of the managed object."
    ::= { cucsBiosVfRedirectionAfterBIOSPOSTEntry 1 }

cucsBiosVfRedirectionAfterBIOSPOSTDn OBJECT-TYPE
    SYNTAX       CucsManagedObjectDn
    MAX-ACCESS   read-only
    STATUS       current
    DESCRIPTION
        "Cisco UCS bios:VfRedirectionAfterBIOSPOST:dn managed
        object property"
    ::= { cucsBiosVfRedirectionAfterBIOSPOSTEntry 2 }

cucsBiosVfRedirectionAfterBIOSPOSTRn OBJECT-TYPE
    SYNTAX       SnmpAdminString
    MAX-ACCESS   read-only
    STATUS       current
    DESCRIPTION
        "Cisco UCS bios:VfRedirectionAfterBIOSPOST:rn managed
        object property"
    ::= { cucsBiosVfRedirectionAfterBIOSPOSTEntry 3 }

cucsBiosVfRedirectionAfterBIOSPOSTPropAcl OBJECT-TYPE
    SYNTAX       Unsigned64
    MAX-ACCESS   read-only
    STATUS       current
    DESCRIPTION
        "Cisco UCS bios:VfRedirectionAfterBIOSPOST:propAcl
        managed object property"
    ::= { cucsBiosVfRedirectionAfterBIOSPOSTEntry 4 }

cucsBiosVfRedirectionAfterBIOSPOSTSupportedByDefault OBJECT-TYPE
    SYNTAX       CucsBiosSupportedAction
    MAX-ACCESS   read-only
    STATUS       current
    DESCRIPTION
        "Cisco UCS bios:VfRedirectionAfterBIOSPOST:supportedByDefault
        managed object property"
    ::= { cucsBiosVfRedirectionAfterBIOSPOSTEntry 5 }

cucsBiosVfRedirectionAfterBIOSPOSTVpRedirectionAfterPOST OBJECT-TYPE
    SYNTAX       CucsBiosVfRedirectionAfterBIOSPOSTVpRedirectionAfterPOST
    MAX-ACCESS   read-only
    STATUS       current
    DESCRIPTION
        "Cisco UCS bios:VfRedirectionAfterBIOSPOST:vpRedirectionAfterPOST
        managed object property"
    ::= { cucsBiosVfRedirectionAfterBIOSPOSTEntry 6 }

cucsBiosVfResumeOnACPowerLossTable OBJECT-TYPE
    SYNTAX           SEQUENCE OF CucsBiosVfResumeOnACPowerLossEntry
    MAX-ACCESS       not-accessible
    STATUS           current
    DESCRIPTION
        "Cisco UCS bios:VfResumeOnACPowerLoss managed object table"
    ::= { cucsBiosObjects 25 }

cucsBiosVfResumeOnACPowerLossEntry OBJECT-TYPE
    SYNTAX           CucsBiosVfResumeOnACPowerLossEntry
    MAX-ACCESS       not-accessible
    STATUS           current
    DESCRIPTION
        "Entry for the cucsBiosVfResumeOnACPowerLossTable table."
    INDEX { cucsBiosVfResumeOnACPowerLossInstanceId }
    ::= { cucsBiosVfResumeOnACPowerLossTable 1 }

CucsBiosVfResumeOnACPowerLossEntry ::= SEQUENCE {
    cucsBiosVfResumeOnACPowerLossInstanceId                          CucsManagedObjectId,
    cucsBiosVfResumeOnACPowerLossDn                                  CucsManagedObjectDn,
    cucsBiosVfResumeOnACPowerLossRn                                  SnmpAdminString,
    cucsBiosVfResumeOnACPowerLossVpResumeOnACPowerLoss               CucsBiosVfResumeOnACPowerLossVpResumeOnACPowerLoss,
    cucsBiosVfResumeOnACPowerLossPropAcl                             Unsigned64,
    cucsBiosVfResumeOnACPowerLossSupportedByDefault                  CucsBiosSupportedAction
}

cucsBiosVfResumeOnACPowerLossInstanceId OBJECT-TYPE
    SYNTAX       CucsManagedObjectId
    MAX-ACCESS   not-accessible
    STATUS       current
    DESCRIPTION
        "Instance identifier of the managed object."
    ::= { cucsBiosVfResumeOnACPowerLossEntry 1 }

cucsBiosVfResumeOnACPowerLossDn OBJECT-TYPE
    SYNTAX       CucsManagedObjectDn
    MAX-ACCESS   read-only
    STATUS       current
    DESCRIPTION
        "Cisco UCS bios:VfResumeOnACPowerLoss:dn managed object property"
    ::= { cucsBiosVfResumeOnACPowerLossEntry 2 }

cucsBiosVfResumeOnACPowerLossRn OBJECT-TYPE
    SYNTAX       SnmpAdminString
    MAX-ACCESS   read-only
    STATUS       current
    DESCRIPTION
        "Cisco UCS bios:VfResumeOnACPowerLoss:rn managed object property"
    ::= { cucsBiosVfResumeOnACPowerLossEntry 3 }

cucsBiosVfResumeOnACPowerLossVpResumeOnACPowerLoss OBJECT-TYPE
    SYNTAX       CucsBiosVfResumeOnACPowerLossVpResumeOnACPowerLoss
    MAX-ACCESS   read-only
    STATUS       current
    DESCRIPTION
        "Cisco UCS bios:VfResumeOnACPowerLoss:vpResumeOnACPowerLoss
        managed object property"
    ::= { cucsBiosVfResumeOnACPowerLossEntry 4 }

cucsBiosVfResumeOnACPowerLossPropAcl OBJECT-TYPE
    SYNTAX       Unsigned64
    MAX-ACCESS   read-only
    STATUS       current
    DESCRIPTION
        "Cisco UCS bios:VfResumeOnACPowerLoss:propAcl managed
        object property"
    ::= { cucsBiosVfResumeOnACPowerLossEntry 5 }

cucsBiosVfResumeOnACPowerLossSupportedByDefault OBJECT-TYPE
    SYNTAX       CucsBiosSupportedAction
    MAX-ACCESS   read-only
    STATUS       current
    DESCRIPTION
        "Cisco UCS bios:VfResumeOnACPowerLoss:supportedByDefault
        managed object property"
    ::= { cucsBiosVfResumeOnACPowerLossEntry 6 }

cucsBiosVfSBMezz1OptionROMTable OBJECT-TYPE
    SYNTAX           SEQUENCE OF CucsBiosVfSBMezz1OptionROMEntry
    MAX-ACCESS       not-accessible
    STATUS           current
    DESCRIPTION
        "Cisco UCS bios:VfSBMezz1OptionROM managed object table"
    ::= { cucsBiosObjects 106 }

cucsBiosVfSBMezz1OptionROMEntry OBJECT-TYPE
    SYNTAX           CucsBiosVfSBMezz1OptionROMEntry
    MAX-ACCESS       not-accessible
    STATUS           current
    DESCRIPTION
        "Entry for the cucsBiosVfSBMezz1OptionROMTable table."
    INDEX { cucsBiosVfSBMezz1OptionROMInstanceId }
    ::= { cucsBiosVfSBMezz1OptionROMTable 1 }

CucsBiosVfSBMezz1OptionROMEntry ::= SEQUENCE {
    cucsBiosVfSBMezz1OptionROMInstanceId                             CucsManagedObjectId,
    cucsBiosVfSBMezz1OptionROMDn                                     CucsManagedObjectDn,
    cucsBiosVfSBMezz1OptionROMRn                                     SnmpAdminString,
    cucsBiosVfSBMezz1OptionROMPropAcl                                Unsigned64,
    cucsBiosVfSBMezz1OptionROMSupportedByDefault                     CucsBiosSupportedAction,
    cucsBiosVfSBMezz1OptionROMVpSBMezz1OptionROM                     CucsBiosVfSBMezz1OptionROMVpSBMezz1OptionROM
}

cucsBiosVfSBMezz1OptionROMInstanceId OBJECT-TYPE
    SYNTAX       CucsManagedObjectId
    MAX-ACCESS   not-accessible
    STATUS       current
    DESCRIPTION
        "Instance identifier of the managed object."
    ::= { cucsBiosVfSBMezz1OptionROMEntry 1 }

cucsBiosVfSBMezz1OptionROMDn OBJECT-TYPE
    SYNTAX       CucsManagedObjectDn
    MAX-ACCESS   read-only
    STATUS       current
    DESCRIPTION
        "Cisco UCS bios:VfSBMezz1OptionROM:dn managed object property"
    ::= { cucsBiosVfSBMezz1OptionROMEntry 2 }

cucsBiosVfSBMezz1OptionROMRn OBJECT-TYPE
    SYNTAX       SnmpAdminString
    MAX-ACCESS   read-only
    STATUS       current
    DESCRIPTION
        "Cisco UCS bios:VfSBMezz1OptionROM:rn managed object property"
    ::= { cucsBiosVfSBMezz1OptionROMEntry 3 }

cucsBiosVfSBMezz1OptionROMPropAcl OBJECT-TYPE
    SYNTAX       Unsigned64
    MAX-ACCESS   read-only
    STATUS       current
    DESCRIPTION
        "Cisco UCS bios:VfSBMezz1OptionROM:propAcl managed
        object property"
    ::= { cucsBiosVfSBMezz1OptionROMEntry 4 }

cucsBiosVfSBMezz1OptionROMSupportedByDefault OBJECT-TYPE
    SYNTAX       CucsBiosSupportedAction
    MAX-ACCESS   read-only
    STATUS       current
    DESCRIPTION
        "Cisco UCS bios:VfSBMezz1OptionROM:supportedByDefault
        managed object property"
    ::= { cucsBiosVfSBMezz1OptionROMEntry 5 }

cucsBiosVfSBMezz1OptionROMVpSBMezz1OptionROM OBJECT-TYPE
    SYNTAX       CucsBiosVfSBMezz1OptionROMVpSBMezz1OptionROM
    MAX-ACCESS   read-only
    STATUS       current
    DESCRIPTION
        "Cisco UCS bios:VfSBMezz1OptionROM:vpSBMezz1OptionROM
        managed object property"
    ::= { cucsBiosVfSBMezz1OptionROMEntry 6 }

cucsBiosVfSBNVMe1OptionROMTable OBJECT-TYPE
    SYNTAX           SEQUENCE OF CucsBiosVfSBNVMe1OptionROMEntry
    MAX-ACCESS       not-accessible
    STATUS           current
    DESCRIPTION
        "Cisco UCS bios:VfSBNVMe1OptionROM managed object table"
    ::= { cucsBiosObjects 107 }

cucsBiosVfSBNVMe1OptionROMEntry OBJECT-TYPE
    SYNTAX           CucsBiosVfSBNVMe1OptionROMEntry
    MAX-ACCESS       not-accessible
    STATUS           current
    DESCRIPTION
        "Entry for the cucsBiosVfSBNVMe1OptionROMTable table."
    INDEX { cucsBiosVfSBNVMe1OptionROMInstanceId }
    ::= { cucsBiosVfSBNVMe1OptionROMTable 1 }

CucsBiosVfSBNVMe1OptionROMEntry ::= SEQUENCE {
    cucsBiosVfSBNVMe1OptionROMInstanceId                             CucsManagedObjectId,
    cucsBiosVfSBNVMe1OptionROMDn                                     CucsManagedObjectDn,
    cucsBiosVfSBNVMe1OptionROMRn                                     SnmpAdminString,
    cucsBiosVfSBNVMe1OptionROMPropAcl                                Unsigned64,
    cucsBiosVfSBNVMe1OptionROMSupportedByDefault                     CucsBiosSupportedAction,
    cucsBiosVfSBNVMe1OptionROMVpSBNVMe1OptionROM                     CucsBiosVfSBNVMe1OptionROMVpSBNVMe1OptionROM
}

cucsBiosVfSBNVMe1OptionROMInstanceId OBJECT-TYPE
    SYNTAX       CucsManagedObjectId
    MAX-ACCESS   not-accessible
    STATUS       current
    DESCRIPTION
        "Instance identifier of the managed object."
    ::= { cucsBiosVfSBNVMe1OptionROMEntry 1 }

cucsBiosVfSBNVMe1OptionROMDn OBJECT-TYPE
    SYNTAX       CucsManagedObjectDn
    MAX-ACCESS   read-only
    STATUS       current
    DESCRIPTION
        "Cisco UCS bios:VfSBNVMe1OptionROM:dn managed object property"
    ::= { cucsBiosVfSBNVMe1OptionROMEntry 2 }

cucsBiosVfSBNVMe1OptionROMRn OBJECT-TYPE
    SYNTAX       SnmpAdminString
    MAX-ACCESS   read-only
    STATUS       current
    DESCRIPTION
        "Cisco UCS bios:VfSBNVMe1OptionROM:rn managed object property"
    ::= { cucsBiosVfSBNVMe1OptionROMEntry 3 }

cucsBiosVfSBNVMe1OptionROMPropAcl OBJECT-TYPE
    SYNTAX       Unsigned64
    MAX-ACCESS   read-only
    STATUS       current
    DESCRIPTION
        "Cisco UCS bios:VfSBNVMe1OptionROM:propAcl managed
        object property"
    ::= { cucsBiosVfSBNVMe1OptionROMEntry 4 }

cucsBiosVfSBNVMe1OptionROMSupportedByDefault OBJECT-TYPE
    SYNTAX       CucsBiosSupportedAction
    MAX-ACCESS   read-only
    STATUS       current
    DESCRIPTION
        "Cisco UCS bios:VfSBNVMe1OptionROM:supportedByDefault
        managed object property"
    ::= { cucsBiosVfSBNVMe1OptionROMEntry 5 }

cucsBiosVfSBNVMe1OptionROMVpSBNVMe1OptionROM OBJECT-TYPE
    SYNTAX       CucsBiosVfSBNVMe1OptionROMVpSBNVMe1OptionROM
    MAX-ACCESS   read-only
    STATUS       current
    DESCRIPTION
        "Cisco UCS bios:VfSBNVMe1OptionROM:vpSBNVMe1OptionROM
        managed object property"
    ::= { cucsBiosVfSBNVMe1OptionROMEntry 6 }

cucsBiosVfSIOC1OptionROMTable OBJECT-TYPE
    SYNTAX           SEQUENCE OF CucsBiosVfSIOC1OptionROMEntry
    MAX-ACCESS       not-accessible
    STATUS           current
    DESCRIPTION
        "Cisco UCS bios:VfSIOC1OptionROM managed object table"
    ::= { cucsBiosObjects 108 }

cucsBiosVfSIOC1OptionROMEntry OBJECT-TYPE
    SYNTAX           CucsBiosVfSIOC1OptionROMEntry
    MAX-ACCESS       not-accessible
    STATUS           current
    DESCRIPTION
        "Entry for the cucsBiosVfSIOC1OptionROMTable table."
    INDEX { cucsBiosVfSIOC1OptionROMInstanceId }
    ::= { cucsBiosVfSIOC1OptionROMTable 1 }

CucsBiosVfSIOC1OptionROMEntry ::= SEQUENCE {
    cucsBiosVfSIOC1OptionROMInstanceId                               CucsManagedObjectId,
    cucsBiosVfSIOC1OptionROMDn                                       CucsManagedObjectDn,
    cucsBiosVfSIOC1OptionROMRn                                       SnmpAdminString,
    cucsBiosVfSIOC1OptionROMPropAcl                                  Unsigned64,
    cucsBiosVfSIOC1OptionROMSupportedByDefault                       CucsBiosSupportedAction,
    cucsBiosVfSIOC1OptionROMVpSIOC1OptionROM                         CucsBiosVfSIOC1OptionROMVpSIOC1OptionROM
}

cucsBiosVfSIOC1OptionROMInstanceId OBJECT-TYPE
    SYNTAX       CucsManagedObjectId
    MAX-ACCESS   not-accessible
    STATUS       current
    DESCRIPTION
        "Instance identifier of the managed object."
    ::= { cucsBiosVfSIOC1OptionROMEntry 1 }

cucsBiosVfSIOC1OptionROMDn OBJECT-TYPE
    SYNTAX       CucsManagedObjectDn
    MAX-ACCESS   read-only
    STATUS       current
    DESCRIPTION
        "Cisco UCS bios:VfSIOC1OptionROM:dn managed object property"
    ::= { cucsBiosVfSIOC1OptionROMEntry 2 }

cucsBiosVfSIOC1OptionROMRn OBJECT-TYPE
    SYNTAX       SnmpAdminString
    MAX-ACCESS   read-only
    STATUS       current
    DESCRIPTION
        "Cisco UCS bios:VfSIOC1OptionROM:rn managed object property"
    ::= { cucsBiosVfSIOC1OptionROMEntry 3 }

cucsBiosVfSIOC1OptionROMPropAcl OBJECT-TYPE
    SYNTAX       Unsigned64
    MAX-ACCESS   read-only
    STATUS       current
    DESCRIPTION
        "Cisco UCS bios:VfSIOC1OptionROM:propAcl managed object property"
    ::= { cucsBiosVfSIOC1OptionROMEntry 4 }

cucsBiosVfSIOC1OptionROMSupportedByDefault OBJECT-TYPE
    SYNTAX       CucsBiosSupportedAction
    MAX-ACCESS   read-only
    STATUS       current
    DESCRIPTION
        "Cisco UCS bios:VfSIOC1OptionROM:supportedByDefault
        managed object property"
    ::= { cucsBiosVfSIOC1OptionROMEntry 5 }

cucsBiosVfSIOC1OptionROMVpSIOC1OptionROM OBJECT-TYPE
    SYNTAX       CucsBiosVfSIOC1OptionROMVpSIOC1OptionROM
    MAX-ACCESS   read-only
    STATUS       current
    DESCRIPTION
        "Cisco UCS bios:VfSIOC1OptionROM:vpSIOC1OptionROM
        managed object property"
    ::= { cucsBiosVfSIOC1OptionROMEntry 6 }

cucsBiosVfSIOC2OptionROMTable OBJECT-TYPE
    SYNTAX           SEQUENCE OF CucsBiosVfSIOC2OptionROMEntry
    MAX-ACCESS       not-accessible
    STATUS           current
    DESCRIPTION
        "Cisco UCS bios:VfSIOC2OptionROM managed object table"
    ::= { cucsBiosObjects 109 }

cucsBiosVfSIOC2OptionROMEntry OBJECT-TYPE
    SYNTAX           CucsBiosVfSIOC2OptionROMEntry
    MAX-ACCESS       not-accessible
    STATUS           current
    DESCRIPTION
        "Entry for the cucsBiosVfSIOC2OptionROMTable table."
    INDEX { cucsBiosVfSIOC2OptionROMInstanceId }
    ::= { cucsBiosVfSIOC2OptionROMTable 1 }

CucsBiosVfSIOC2OptionROMEntry ::= SEQUENCE {
    cucsBiosVfSIOC2OptionROMInstanceId                               CucsManagedObjectId,
    cucsBiosVfSIOC2OptionROMDn                                       CucsManagedObjectDn,
    cucsBiosVfSIOC2OptionROMRn                                       SnmpAdminString,
    cucsBiosVfSIOC2OptionROMPropAcl                                  Unsigned64,
    cucsBiosVfSIOC2OptionROMSupportedByDefault                       CucsBiosSupportedAction,
    cucsBiosVfSIOC2OptionROMVpSIOC2OptionROM                         CucsBiosVfSIOC2OptionROMVpSIOC2OptionROM
}

cucsBiosVfSIOC2OptionROMInstanceId OBJECT-TYPE
    SYNTAX       CucsManagedObjectId
    MAX-ACCESS   not-accessible
    STATUS       current
    DESCRIPTION
        "Instance identifier of the managed object."
    ::= { cucsBiosVfSIOC2OptionROMEntry 1 }

cucsBiosVfSIOC2OptionROMDn OBJECT-TYPE
    SYNTAX       CucsManagedObjectDn
    MAX-ACCESS   read-only
    STATUS       current
    DESCRIPTION
        "Cisco UCS bios:VfSIOC2OptionROM:dn managed object property"
    ::= { cucsBiosVfSIOC2OptionROMEntry 2 }

cucsBiosVfSIOC2OptionROMRn OBJECT-TYPE
    SYNTAX       SnmpAdminString
    MAX-ACCESS   read-only
    STATUS       current
    DESCRIPTION
        "Cisco UCS bios:VfSIOC2OptionROM:rn managed object property"
    ::= { cucsBiosVfSIOC2OptionROMEntry 3 }

cucsBiosVfSIOC2OptionROMPropAcl OBJECT-TYPE
    SYNTAX       Unsigned64
    MAX-ACCESS   read-only
    STATUS       current
    DESCRIPTION
        "Cisco UCS bios:VfSIOC2OptionROM:propAcl managed object property"
    ::= { cucsBiosVfSIOC2OptionROMEntry 4 }

cucsBiosVfSIOC2OptionROMSupportedByDefault OBJECT-TYPE
    SYNTAX       CucsBiosSupportedAction
    MAX-ACCESS   read-only
    STATUS       current
    DESCRIPTION
        "Cisco UCS bios:VfSIOC2OptionROM:supportedByDefault
        managed object property"
    ::= { cucsBiosVfSIOC2OptionROMEntry 5 }

cucsBiosVfSIOC2OptionROMVpSIOC2OptionROM OBJECT-TYPE
    SYNTAX       CucsBiosVfSIOC2OptionROMVpSIOC2OptionROM
    MAX-ACCESS   read-only
    STATUS       current
    DESCRIPTION
        "Cisco UCS bios:VfSIOC2OptionROM:vpSIOC2OptionROM
        managed object property"
    ::= { cucsBiosVfSIOC2OptionROMEntry 6 }

cucsBiosVfScrubPoliciesTable OBJECT-TYPE
    SYNTAX           SEQUENCE OF CucsBiosVfScrubPoliciesEntry
    MAX-ACCESS       not-accessible
    STATUS           current
    DESCRIPTION
        "Cisco UCS bios:VfScrubPolicies managed object table"
    ::= { cucsBiosObjects 75 }

cucsBiosVfScrubPoliciesEntry OBJECT-TYPE
    SYNTAX           CucsBiosVfScrubPoliciesEntry
    MAX-ACCESS       not-accessible
    STATUS           current
    DESCRIPTION
        "Entry for the cucsBiosVfScrubPoliciesTable table."
    INDEX { cucsBiosVfScrubPoliciesInstanceId }
    ::= { cucsBiosVfScrubPoliciesTable 1 }

CucsBiosVfScrubPoliciesEntry ::= SEQUENCE {
    cucsBiosVfScrubPoliciesInstanceId                                CucsManagedObjectId,
    cucsBiosVfScrubPoliciesDn                                        CucsManagedObjectDn,
    cucsBiosVfScrubPoliciesRn                                        SnmpAdminString,
    cucsBiosVfScrubPoliciesVpDemandScrub                             CucsBiosVfScrubPoliciesVpDemandScrub,
    cucsBiosVfScrubPoliciesVpPatrolScrub                             CucsBiosVfScrubPoliciesVpPatrolScrub,
    cucsBiosVfScrubPoliciesPropAcl                                   Unsigned64,
    cucsBiosVfScrubPoliciesSupportedByDefault                        CucsBiosSupportedAction
}

cucsBiosVfScrubPoliciesInstanceId OBJECT-TYPE
    SYNTAX       CucsManagedObjectId
    MAX-ACCESS   not-accessible
    STATUS       current
    DESCRIPTION
        "Instance identifier of the managed object."
    ::= { cucsBiosVfScrubPoliciesEntry 1 }

cucsBiosVfScrubPoliciesDn OBJECT-TYPE
    SYNTAX       CucsManagedObjectDn
    MAX-ACCESS   read-only
    STATUS       current
    DESCRIPTION
        "Cisco UCS bios:VfScrubPolicies:dn managed object property"
    ::= { cucsBiosVfScrubPoliciesEntry 2 }

cucsBiosVfScrubPoliciesRn OBJECT-TYPE
    SYNTAX       SnmpAdminString
    MAX-ACCESS   read-only
    STATUS       current
    DESCRIPTION
        "Cisco UCS bios:VfScrubPolicies:rn managed object property"
    ::= { cucsBiosVfScrubPoliciesEntry 3 }

cucsBiosVfScrubPoliciesVpDemandScrub OBJECT-TYPE
    SYNTAX       CucsBiosVfScrubPoliciesVpDemandScrub
    MAX-ACCESS   read-only
    STATUS       current
    DESCRIPTION
        "Cisco UCS bios:VfScrubPolicies:vpDemandScrub managed
        object property"
    ::= { cucsBiosVfScrubPoliciesEntry 4 }

cucsBiosVfScrubPoliciesVpPatrolScrub OBJECT-TYPE
    SYNTAX       CucsBiosVfScrubPoliciesVpPatrolScrub
    MAX-ACCESS   read-only
    STATUS       current
    DESCRIPTION
        "Cisco UCS bios:VfScrubPolicies:vpPatrolScrub managed
        object property"
    ::= { cucsBiosVfScrubPoliciesEntry 5 }

cucsBiosVfScrubPoliciesPropAcl OBJECT-TYPE
    SYNTAX       Unsigned64
    MAX-ACCESS   read-only
    STATUS       current
    DESCRIPTION
        "Cisco UCS bios:VfScrubPolicies:propAcl managed object property"
    ::= { cucsBiosVfScrubPoliciesEntry 6 }

cucsBiosVfScrubPoliciesSupportedByDefault OBJECT-TYPE
    SYNTAX       CucsBiosSupportedAction
    MAX-ACCESS   read-only
    STATUS       current
    DESCRIPTION
        "Cisco UCS bios:VfScrubPolicies:supportedByDefault
        managed object property"
    ::= { cucsBiosVfScrubPoliciesEntry 7 }

cucsBiosVfSelectMemoryRASConfigurationTable OBJECT-TYPE
    SYNTAX           SEQUENCE OF CucsBiosVfSelectMemoryRASConfigurationEntry
    MAX-ACCESS       not-accessible
    STATUS           current
    DESCRIPTION
        "Cisco UCS bios:VfSelectMemoryRASConfiguration
        managed object table"
    ::= { cucsBiosObjects 26 }

cucsBiosVfSelectMemoryRASConfigurationEntry OBJECT-TYPE
    SYNTAX           CucsBiosVfSelectMemoryRASConfigurationEntry
    MAX-ACCESS       not-accessible
    STATUS           current
    DESCRIPTION
        "Entry for the cucsBiosVfSelectMemoryRASConfigurationTable table."
    INDEX { cucsBiosVfSelectMemoryRASConfigurationInstanceId }
    ::= { cucsBiosVfSelectMemoryRASConfigurationTable 1 }

CucsBiosVfSelectMemoryRASConfigurationEntry ::= SEQUENCE {
    cucsBiosVfSelectMemoryRASConfigurationInstanceId                 CucsManagedObjectId,
    cucsBiosVfSelectMemoryRASConfigurationDn                         CucsManagedObjectDn,
    cucsBiosVfSelectMemoryRASConfigurationRn                         SnmpAdminString,
    cucsBiosVpSelectMemoryRASConfiguration                           CucsBiosVpSelectMemoryRASConfiguration,
    cucsBiosVfSelectMemoryRASConfigurationPropAcl                    Unsigned64,
    cucsBiosVfSelectMemoryRASConfigurationSupportedByDefault         CucsBiosSupportedAction
}

cucsBiosVfSelectMemoryRASConfigurationInstanceId OBJECT-TYPE
    SYNTAX       CucsManagedObjectId
    MAX-ACCESS   not-accessible
    STATUS       current
    DESCRIPTION
        "Instance identifier of the managed object."
    ::= { cucsBiosVfSelectMemoryRASConfigurationEntry 1 }

cucsBiosVfSelectMemoryRASConfigurationDn OBJECT-TYPE
    SYNTAX       CucsManagedObjectDn
    MAX-ACCESS   read-only
    STATUS       current
    DESCRIPTION
        "Cisco UCS bios:VfSelectMemoryRASConfiguration:dn
        managed object property"
    ::= { cucsBiosVfSelectMemoryRASConfigurationEntry 2 }

cucsBiosVfSelectMemoryRASConfigurationRn OBJECT-TYPE
    SYNTAX       SnmpAdminString
    MAX-ACCESS   read-only
    STATUS       current
    DESCRIPTION
        "Cisco UCS bios:VfSelectMemoryRASConfiguration:rn
        managed object property"
    ::= { cucsBiosVfSelectMemoryRASConfigurationEntry 3 }

cucsBiosVpSelectMemoryRASConfiguration OBJECT-TYPE
    SYNTAX       CucsBiosVpSelectMemoryRASConfiguration
    MAX-ACCESS   read-only
    STATUS       current
    DESCRIPTION
        "Cisco UCS bios:VfSelectMemoryRASConfiguration:vpSelectMemoryRASCo
        nfiguration managed object property"
    ::= { cucsBiosVfSelectMemoryRASConfigurationEntry 4 }

cucsBiosVfSelectMemoryRASConfigurationPropAcl OBJECT-TYPE
    SYNTAX       Unsigned64
    MAX-ACCESS   read-only
    STATUS       current
    DESCRIPTION
        "Cisco UCS bios:VfSelectMemoryRASConfiguration:propAcl
        managed object property"
    ::= { cucsBiosVfSelectMemoryRASConfigurationEntry 5 }

cucsBiosVfSelectMemoryRASConfigurationSupportedByDefault OBJECT-TYPE
    SYNTAX       CucsBiosSupportedAction
    MAX-ACCESS   read-only
    STATUS       current
    DESCRIPTION
        "Cisco UCS bios:VfSelectMemoryRASConfiguration:supportedByDefault
        managed object property"
    ::= { cucsBiosVfSelectMemoryRASConfigurationEntry 6 }

cucsBiosVfSerialPortAEnableTable OBJECT-TYPE
    SYNTAX           SEQUENCE OF CucsBiosVfSerialPortAEnableEntry
    MAX-ACCESS       not-accessible
    STATUS           current
    DESCRIPTION
        "Cisco UCS bios:VfSerialPortAEnable managed object table"
    ::= { cucsBiosObjects 38 }

cucsBiosVfSerialPortAEnableEntry OBJECT-TYPE
    SYNTAX           CucsBiosVfSerialPortAEnableEntry
    MAX-ACCESS       not-accessible
    STATUS           current
    DESCRIPTION
        "Entry for the cucsBiosVfSerialPortAEnableTable table."
    INDEX { cucsBiosVfSerialPortAEnableInstanceId }
    ::= { cucsBiosVfSerialPortAEnableTable 1 }

CucsBiosVfSerialPortAEnableEntry ::= SEQUENCE {
    cucsBiosVfSerialPortAEnableInstanceId                            CucsManagedObjectId,
    cucsBiosVfSerialPortAEnableDn                                    CucsManagedObjectDn,
    cucsBiosVfSerialPortAEnableRn                                    SnmpAdminString,
    cucsBiosVfSerialPortAEnableVpSerialPortAEnable                   CucsBiosVfSerialPortAEnableVpSerialPortAEnable,
    cucsBiosVfSerialPortAEnablePropAcl                               Unsigned64,
    cucsBiosVfSerialPortAEnableSupportedByDefault                    CucsBiosSupportedAction
}

cucsBiosVfSerialPortAEnableInstanceId OBJECT-TYPE
    SYNTAX       CucsManagedObjectId
    MAX-ACCESS   not-accessible
    STATUS       current
    DESCRIPTION
        "Instance identifier of the managed object."
    ::= { cucsBiosVfSerialPortAEnableEntry 1 }

cucsBiosVfSerialPortAEnableDn OBJECT-TYPE
    SYNTAX       CucsManagedObjectDn
    MAX-ACCESS   read-only
    STATUS       current
    DESCRIPTION
        "Cisco UCS bios:VfSerialPortAEnable:dn managed object property"
    ::= { cucsBiosVfSerialPortAEnableEntry 2 }

cucsBiosVfSerialPortAEnableRn OBJECT-TYPE
    SYNTAX       SnmpAdminString
    MAX-ACCESS   read-only
    STATUS       current
    DESCRIPTION
        "Cisco UCS bios:VfSerialPortAEnable:rn managed object property"
    ::= { cucsBiosVfSerialPortAEnableEntry 3 }

cucsBiosVfSerialPortAEnableVpSerialPortAEnable OBJECT-TYPE
    SYNTAX       CucsBiosVfSerialPortAEnableVpSerialPortAEnable
    MAX-ACCESS   read-only
    STATUS       current
    DESCRIPTION
        "Cisco UCS bios:VfSerialPortAEnable:vpSerialPortAEnable
        managed object property"
    ::= { cucsBiosVfSerialPortAEnableEntry 4 }

cucsBiosVfSerialPortAEnablePropAcl OBJECT-TYPE
    SYNTAX       Unsigned64
    MAX-ACCESS   read-only
    STATUS       current
    DESCRIPTION
        "Cisco UCS bios:VfSerialPortAEnable:propAcl managed
        object property"
    ::= { cucsBiosVfSerialPortAEnableEntry 5 }

cucsBiosVfSerialPortAEnableSupportedByDefault OBJECT-TYPE
    SYNTAX       CucsBiosSupportedAction
    MAX-ACCESS   read-only
    STATUS       current
    DESCRIPTION
        "Cisco UCS bios:VfSerialPortAEnable:supportedByDefault
        managed object property"
    ::= { cucsBiosVfSerialPortAEnableEntry 6 }

cucsBiosVfSparingModeTable OBJECT-TYPE
    SYNTAX           SEQUENCE OF CucsBiosVfSparingModeEntry
    MAX-ACCESS       not-accessible
    STATUS           current
    DESCRIPTION
        "Cisco UCS bios:VfSparingMode managed object table"
    ::= { cucsBiosObjects 37 }

cucsBiosVfSparingModeEntry OBJECT-TYPE
    SYNTAX           CucsBiosVfSparingModeEntry
    MAX-ACCESS       not-accessible
    STATUS           current
    DESCRIPTION
        "Entry for the cucsBiosVfSparingModeTable table."
    INDEX { cucsBiosVfSparingModeInstanceId }
    ::= { cucsBiosVfSparingModeTable 1 }

CucsBiosVfSparingModeEntry ::= SEQUENCE {
    cucsBiosVfSparingModeInstanceId                                  CucsManagedObjectId,
    cucsBiosVfSparingModeDn                                          CucsManagedObjectDn,
    cucsBiosVfSparingModeRn                                          SnmpAdminString,
    cucsBiosVfSparingModeVpSparingMode                               CucsBiosVfSparingModeVpSparingMode,
    cucsBiosVfSparingModePropAcl                                     Unsigned64,
    cucsBiosVfSparingModeSupportedByDefault                          CucsBiosSupportedAction
}

cucsBiosVfSparingModeInstanceId OBJECT-TYPE
    SYNTAX       CucsManagedObjectId
    MAX-ACCESS   not-accessible
    STATUS       current
    DESCRIPTION
        "Instance identifier of the managed object."
    ::= { cucsBiosVfSparingModeEntry 1 }

cucsBiosVfSparingModeDn OBJECT-TYPE
    SYNTAX       CucsManagedObjectDn
    MAX-ACCESS   read-only
    STATUS       current
    DESCRIPTION
        "Cisco UCS bios:VfSparingMode:dn managed object property"
    ::= { cucsBiosVfSparingModeEntry 2 }

cucsBiosVfSparingModeRn OBJECT-TYPE
    SYNTAX       SnmpAdminString
    MAX-ACCESS   read-only
    STATUS       current
    DESCRIPTION
        "Cisco UCS bios:VfSparingMode:rn managed object property"
    ::= { cucsBiosVfSparingModeEntry 3 }

cucsBiosVfSparingModeVpSparingMode OBJECT-TYPE
    SYNTAX       CucsBiosVfSparingModeVpSparingMode
    MAX-ACCESS   read-only
    STATUS       current
    DESCRIPTION
        "Cisco UCS bios:VfSparingMode:vpSparingMode managed
        object property"
    ::= { cucsBiosVfSparingModeEntry 4 }

cucsBiosVfSparingModePropAcl OBJECT-TYPE
    SYNTAX       Unsigned64
    MAX-ACCESS   read-only
    STATUS       current
    DESCRIPTION
        "Cisco UCS bios:VfSparingMode:propAcl managed object property"
    ::= { cucsBiosVfSparingModeEntry 5 }

cucsBiosVfSparingModeSupportedByDefault OBJECT-TYPE
    SYNTAX       CucsBiosSupportedAction
    MAX-ACCESS   read-only
    STATUS       current
    DESCRIPTION
        "Cisco UCS bios:VfSparingMode:supportedByDefault
        managed object property"
    ::= { cucsBiosVfSparingModeEntry 6 }

cucsBiosVfSriovConfigTable OBJECT-TYPE
    SYNTAX           SEQUENCE OF CucsBiosVfSriovConfigEntry
    MAX-ACCESS       not-accessible
    STATUS           current
    DESCRIPTION
        "Cisco UCS bios:VfSriovConfig managed object table"
    ::= { cucsBiosObjects 60 }

cucsBiosVfSriovConfigEntry OBJECT-TYPE
    SYNTAX           CucsBiosVfSriovConfigEntry
    MAX-ACCESS       not-accessible
    STATUS           current
    DESCRIPTION
        "Entry for the cucsBiosVfSriovConfigTable table."
    INDEX { cucsBiosVfSriovConfigInstanceId }
    ::= { cucsBiosVfSriovConfigTable 1 }

CucsBiosVfSriovConfigEntry ::= SEQUENCE {
    cucsBiosVfSriovConfigInstanceId                                  CucsManagedObjectId,
    cucsBiosVfSriovConfigDn                                          CucsManagedObjectDn,
    cucsBiosVfSriovConfigRn                                          SnmpAdminString,
    cucsBiosVfSriovConfigVpSriov                                     CucsBiosVfSriovConfigVpSriov,
    cucsBiosVfSriovConfigPropAcl                                     Unsigned64,
    cucsBiosVfSriovConfigSupportedByDefault                          CucsBiosSupportedAction
}

cucsBiosVfSriovConfigInstanceId OBJECT-TYPE
    SYNTAX       CucsManagedObjectId
    MAX-ACCESS   not-accessible
    STATUS       current
    DESCRIPTION
        "Instance identifier of the managed object."
    ::= { cucsBiosVfSriovConfigEntry 1 }

cucsBiosVfSriovConfigDn OBJECT-TYPE
    SYNTAX       CucsManagedObjectDn
    MAX-ACCESS   read-only
    STATUS       current
    DESCRIPTION
        "Cisco UCS bios:VfSriovConfig:dn managed object property"
    ::= { cucsBiosVfSriovConfigEntry 2 }

cucsBiosVfSriovConfigRn OBJECT-TYPE
    SYNTAX       SnmpAdminString
    MAX-ACCESS   read-only
    STATUS       current
    DESCRIPTION
        "Cisco UCS bios:VfSriovConfig:rn managed object property"
    ::= { cucsBiosVfSriovConfigEntry 3 }

cucsBiosVfSriovConfigVpSriov OBJECT-TYPE
    SYNTAX       CucsBiosVfSriovConfigVpSriov
    MAX-ACCESS   read-only
    STATUS       current
    DESCRIPTION
        "Cisco UCS bios:VfSriovConfig:vpSriov managed object property"
    ::= { cucsBiosVfSriovConfigEntry 4 }

cucsBiosVfSriovConfigPropAcl OBJECT-TYPE
    SYNTAX       Unsigned64
    MAX-ACCESS   read-only
    STATUS       current
    DESCRIPTION
        "Cisco UCS bios:VfSriovConfig:propAcl managed object property"
    ::= { cucsBiosVfSriovConfigEntry 5 }

cucsBiosVfSriovConfigSupportedByDefault OBJECT-TYPE
    SYNTAX       CucsBiosSupportedAction
    MAX-ACCESS   read-only
    STATUS       current
    DESCRIPTION
        "Cisco UCS bios:VfSriovConfig:supportedByDefault
        managed object property"
    ::= { cucsBiosVfSriovConfigEntry 6 }

cucsBiosVfTPMPendingOperationTable OBJECT-TYPE
    SYNTAX           SEQUENCE OF CucsBiosVfTPMPendingOperationEntry
    MAX-ACCESS       not-accessible
    STATUS           current
    DESCRIPTION
        "Cisco UCS bios:VfTPMPendingOperation managed object table"
    ::= { cucsBiosObjects 90 }

cucsBiosVfTPMPendingOperationEntry OBJECT-TYPE
    SYNTAX           CucsBiosVfTPMPendingOperationEntry
    MAX-ACCESS       not-accessible
    STATUS           current
    DESCRIPTION
        "Entry for the cucsBiosVfTPMPendingOperationTable table."
    INDEX { cucsBiosVfTPMPendingOperationInstanceId }
    ::= { cucsBiosVfTPMPendingOperationTable 1 }

CucsBiosVfTPMPendingOperationEntry ::= SEQUENCE {
    cucsBiosVfTPMPendingOperationInstanceId                          CucsManagedObjectId,
    cucsBiosVfTPMPendingOperationDn                                  CucsManagedObjectDn,
    cucsBiosVfTPMPendingOperationRn                                  SnmpAdminString,
    cucsBiosVfTPMPendingOperationVpTPMPendingOperation               CucsBiosVfTPMPendingOperationVpTPMPendingOperation,
    cucsBiosVfTPMPendingOperationSupportedByDefault                  CucsBiosSupportedAction,
    cucsBiosVfTPMPendingOperationPropAcl                             Unsigned64
}

cucsBiosVfTPMPendingOperationInstanceId OBJECT-TYPE
    SYNTAX       CucsManagedObjectId
    MAX-ACCESS   not-accessible
    STATUS       current
    DESCRIPTION
        "Instance identifier of the managed object."
    ::= { cucsBiosVfTPMPendingOperationEntry 1 }

cucsBiosVfTPMPendingOperationDn OBJECT-TYPE
    SYNTAX       CucsManagedObjectDn
    MAX-ACCESS   read-only
    STATUS       current
    DESCRIPTION
        "Cisco UCS bios:VfTPMPendingOperation:dn managed object property"
    ::= { cucsBiosVfTPMPendingOperationEntry 2 }

cucsBiosVfTPMPendingOperationRn OBJECT-TYPE
    SYNTAX       SnmpAdminString
    MAX-ACCESS   read-only
    STATUS       current
    DESCRIPTION
        "Cisco UCS bios:VfTPMPendingOperation:rn managed object property"
    ::= { cucsBiosVfTPMPendingOperationEntry 3 }

cucsBiosVfTPMPendingOperationVpTPMPendingOperation OBJECT-TYPE
    SYNTAX       CucsBiosVfTPMPendingOperationVpTPMPendingOperation
    MAX-ACCESS   read-only
    STATUS       current
    DESCRIPTION
        "Cisco UCS bios:VfTPMPendingOperation:vpTPMPendingOperation
        managed object property"
    ::= { cucsBiosVfTPMPendingOperationEntry 4 }

cucsBiosVfTPMPendingOperationSupportedByDefault OBJECT-TYPE
    SYNTAX       CucsBiosSupportedAction
    MAX-ACCESS   read-only
    STATUS       current
    DESCRIPTION
        "Cisco UCS bios:VfTPMPendingOperation:supportedByDefault
        managed object property"
    ::= { cucsBiosVfTPMPendingOperationEntry 5 }

cucsBiosVfTPMPendingOperationPropAcl OBJECT-TYPE
    SYNTAX       Unsigned64
    MAX-ACCESS   read-only
    STATUS       current
    DESCRIPTION
        "Cisco UCS bios:VfTPMPendingOperation:propAcl managed
        object property"
    ::= { cucsBiosVfTPMPendingOperationEntry 6 }

cucsBiosVfTPMSupportTable OBJECT-TYPE
    SYNTAX           SEQUENCE OF CucsBiosVfTPMSupportEntry
    MAX-ACCESS       not-accessible
    STATUS           current
    DESCRIPTION
        "Cisco UCS bios:VfTPMSupport managed object table"
    ::= { cucsBiosObjects 79 }

cucsBiosVfTPMSupportEntry OBJECT-TYPE
    SYNTAX           CucsBiosVfTPMSupportEntry
    MAX-ACCESS       not-accessible
    STATUS           current
    DESCRIPTION
        "Entry for the cucsBiosVfTPMSupportTable table."
    INDEX { cucsBiosVfTPMSupportInstanceId }
    ::= { cucsBiosVfTPMSupportTable 1 }

CucsBiosVfTPMSupportEntry ::= SEQUENCE {
    cucsBiosVfTPMSupportInstanceId                                   CucsManagedObjectId,
    cucsBiosVfTPMSupportDn                                           CucsManagedObjectDn,
    cucsBiosVfTPMSupportRn                                           SnmpAdminString,
    cucsBiosVfTPMSupportVpTPMSupport                                 CucsBiosVfTPMSupportVpTPMSupport,
    cucsBiosVfTPMSupportPropAcl                                      Unsigned64,
    cucsBiosVfTPMSupportSupportedByDefault                           CucsBiosSupportedAction
}

cucsBiosVfTPMSupportInstanceId OBJECT-TYPE
    SYNTAX       CucsManagedObjectId
    MAX-ACCESS   not-accessible
    STATUS       current
    DESCRIPTION
        "Instance identifier of the managed object."
    ::= { cucsBiosVfTPMSupportEntry 1 }

cucsBiosVfTPMSupportDn OBJECT-TYPE
    SYNTAX       CucsManagedObjectDn
    MAX-ACCESS   read-only
    STATUS       current
    DESCRIPTION
        "Cisco UCS bios:VfTPMSupport:dn managed object property"
    ::= { cucsBiosVfTPMSupportEntry 2 }

cucsBiosVfTPMSupportRn OBJECT-TYPE
    SYNTAX       SnmpAdminString
    MAX-ACCESS   read-only
    STATUS       current
    DESCRIPTION
        "Cisco UCS bios:VfTPMSupport:rn managed object property"
    ::= { cucsBiosVfTPMSupportEntry 3 }

cucsBiosVfTPMSupportVpTPMSupport OBJECT-TYPE
    SYNTAX       CucsBiosVfTPMSupportVpTPMSupport
    MAX-ACCESS   read-only
    STATUS       current
    DESCRIPTION
        "Cisco UCS bios:VfTPMSupport:vpTPMSupport managed object property"
    ::= { cucsBiosVfTPMSupportEntry 4 }

cucsBiosVfTPMSupportPropAcl OBJECT-TYPE
    SYNTAX       Unsigned64
    MAX-ACCESS   read-only
    STATUS       current
    DESCRIPTION
        "Cisco UCS bios:VfTPMSupport:propAcl managed object property"
    ::= { cucsBiosVfTPMSupportEntry 5 }

cucsBiosVfTPMSupportSupportedByDefault OBJECT-TYPE
    SYNTAX       CucsBiosSupportedAction
    MAX-ACCESS   read-only
    STATUS       current
    DESCRIPTION
        "Cisco UCS bios:VfTPMSupport:supportedByDefault
        managed object property"
    ::= { cucsBiosVfTPMSupportEntry 6 }

cucsBiosVfTrustedPlatformModuleTable OBJECT-TYPE
    SYNTAX           SEQUENCE OF CucsBiosVfTrustedPlatformModuleEntry
    MAX-ACCESS       not-accessible
    STATUS           current
    DESCRIPTION
        "Cisco UCS bios:VfTrustedPlatformModule managed object table"
    ::= { cucsBiosObjects 91 }

cucsBiosVfTrustedPlatformModuleEntry OBJECT-TYPE
    SYNTAX           CucsBiosVfTrustedPlatformModuleEntry
    MAX-ACCESS       not-accessible
    STATUS           current
    DESCRIPTION
        "Entry for the cucsBiosVfTrustedPlatformModuleTable table."
    INDEX { cucsBiosVfTrustedPlatformModuleInstanceId }
    ::= { cucsBiosVfTrustedPlatformModuleTable 1 }

CucsBiosVfTrustedPlatformModuleEntry ::= SEQUENCE {
    cucsBiosVfTrustedPlatformModuleInstanceId                        CucsManagedObjectId,
    cucsBiosVfTrustedPlatformModuleDn                                CucsManagedObjectDn,
    cucsBiosVfTrustedPlatformModuleRn                                SnmpAdminString,
    cucsBiosVfTrustedPlatformModuleVpTrustedPlatformModuleSupport    CucsBiosVfTrustedPlatformModuleVpTrustedPlatformModuleSupport,
    cucsBiosVfTrustedPlatformModuleSupportedByDefault                CucsBiosSupportedAction,
    cucsBiosVfTrustedPlatformModulePropAcl                           Unsigned64
}

cucsBiosVfTrustedPlatformModuleInstanceId OBJECT-TYPE
    SYNTAX       CucsManagedObjectId
    MAX-ACCESS   not-accessible
    STATUS       current
    DESCRIPTION
        "Instance identifier of the managed object."
    ::= { cucsBiosVfTrustedPlatformModuleEntry 1 }

cucsBiosVfTrustedPlatformModuleDn OBJECT-TYPE
    SYNTAX       CucsManagedObjectDn
    MAX-ACCESS   read-only
    STATUS       current
    DESCRIPTION
        "Cisco UCS bios:VfTrustedPlatformModule:dn managed
        object property"
    ::= { cucsBiosVfTrustedPlatformModuleEntry 2 }

cucsBiosVfTrustedPlatformModuleRn OBJECT-TYPE
    SYNTAX       SnmpAdminString
    MAX-ACCESS   read-only
    STATUS       current
    DESCRIPTION
        "Cisco UCS bios:VfTrustedPlatformModule:rn managed
        object property"
    ::= { cucsBiosVfTrustedPlatformModuleEntry 3 }

cucsBiosVfTrustedPlatformModuleVpTrustedPlatformModuleSupport OBJECT-TYPE
    SYNTAX       CucsBiosVfTrustedPlatformModuleVpTrustedPlatformModuleSupport
    MAX-ACCESS   read-only
    STATUS       current
    DESCRIPTION
        "Cisco UCS bios:VfTrustedPlatformModule:vpTrustedPlatformModuleSup
        port managed object property"
    ::= { cucsBiosVfTrustedPlatformModuleEntry 4 }

cucsBiosVfTrustedPlatformModuleSupportedByDefault OBJECT-TYPE
    SYNTAX       CucsBiosSupportedAction
    MAX-ACCESS   read-only
    STATUS       current
    DESCRIPTION
        "Cisco UCS bios:VfTrustedPlatformModule:supportedByDefault
        managed object property"
    ::= { cucsBiosVfTrustedPlatformModuleEntry 5 }

cucsBiosVfTrustedPlatformModulePropAcl OBJECT-TYPE
    SYNTAX       Unsigned64
    MAX-ACCESS   read-only
    STATUS       current
    DESCRIPTION
        "Cisco UCS bios:VfTrustedPlatformModule:propAcl
        managed object property"
    ::= { cucsBiosVfTrustedPlatformModuleEntry 6 }

cucsBiosVfUCSMBootModeControlTable OBJECT-TYPE
    SYNTAX           SEQUENCE OF CucsBiosVfUCSMBootModeControlEntry
    MAX-ACCESS       not-accessible
    STATUS           current
    DESCRIPTION
        "Cisco UCS bios:VfUCSMBootModeControl managed object table"
    ::= { cucsBiosObjects 63 }

cucsBiosVfUCSMBootModeControlEntry OBJECT-TYPE
    SYNTAX           CucsBiosVfUCSMBootModeControlEntry
    MAX-ACCESS       not-accessible
    STATUS           current
    DESCRIPTION
        "Entry for the cucsBiosVfUCSMBootModeControlTable table."
    INDEX { cucsBiosVfUCSMBootModeControlInstanceId }
    ::= { cucsBiosVfUCSMBootModeControlTable 1 }

CucsBiosVfUCSMBootModeControlEntry ::= SEQUENCE {
    cucsBiosVfUCSMBootModeControlInstanceId                          CucsManagedObjectId,
    cucsBiosVfUCSMBootModeControlDn                                  CucsManagedObjectDn,
    cucsBiosVfUCSMBootModeControlRn                                  SnmpAdminString,
    cucsBiosVfUCSMBootModeControlVpUEFIBootMode                      CucsBiosVfUCSMBootModeControlVpUEFIBootMode,
    cucsBiosVfUCSMBootModeControlPropAcl                             Unsigned64,
    cucsBiosVfUCSMBootModeControlSupportedByDefault                  CucsBiosSupportedAction
}

cucsBiosVfUCSMBootModeControlInstanceId OBJECT-TYPE
    SYNTAX       CucsManagedObjectId
    MAX-ACCESS   not-accessible
    STATUS       current
    DESCRIPTION
        "Instance identifier of the managed object."
    ::= { cucsBiosVfUCSMBootModeControlEntry 1 }

cucsBiosVfUCSMBootModeControlDn OBJECT-TYPE
    SYNTAX       CucsManagedObjectDn
    MAX-ACCESS   read-only
    STATUS       current
    DESCRIPTION
        "Cisco UCS bios:VfUCSMBootModeControl:dn managed object property"
    ::= { cucsBiosVfUCSMBootModeControlEntry 2 }

cucsBiosVfUCSMBootModeControlRn OBJECT-TYPE
    SYNTAX       SnmpAdminString
    MAX-ACCESS   read-only
    STATUS       current
    DESCRIPTION
        "Cisco UCS bios:VfUCSMBootModeControl:rn managed object property"
    ::= { cucsBiosVfUCSMBootModeControlEntry 3 }

cucsBiosVfUCSMBootModeControlVpUEFIBootMode OBJECT-TYPE
    SYNTAX       CucsBiosVfUCSMBootModeControlVpUEFIBootMode
    MAX-ACCESS   read-only
    STATUS       current
    DESCRIPTION
        "Cisco UCS bios:VfUCSMBootModeControl:vpUEFIBootMode
        managed object property"
    ::= { cucsBiosVfUCSMBootModeControlEntry 4 }

cucsBiosVfUCSMBootModeControlPropAcl OBJECT-TYPE
    SYNTAX       Unsigned64
    MAX-ACCESS   read-only
    STATUS       current
    DESCRIPTION
        "Cisco UCS bios:VfUCSMBootModeControl:propAcl managed
        object property"
    ::= { cucsBiosVfUCSMBootModeControlEntry 5 }

cucsBiosVfUCSMBootModeControlSupportedByDefault OBJECT-TYPE
    SYNTAX       CucsBiosSupportedAction
    MAX-ACCESS   read-only
    STATUS       current
    DESCRIPTION
        "Cisco UCS bios:VfUCSMBootModeControl:supportedByDefault
        managed object property"
    ::= { cucsBiosVfUCSMBootModeControlEntry 6 }

cucsBiosVfUCSMBootOrderRuleControlTable OBJECT-TYPE
    SYNTAX           SEQUENCE OF CucsBiosVfUCSMBootOrderRuleControlEntry
    MAX-ACCESS       not-accessible
    STATUS           current
    DESCRIPTION
        "Cisco UCS bios:VfUCSMBootOrderRuleControl managed object table"
    ::= { cucsBiosObjects 48 }

cucsBiosVfUCSMBootOrderRuleControlEntry OBJECT-TYPE
    SYNTAX           CucsBiosVfUCSMBootOrderRuleControlEntry
    MAX-ACCESS       not-accessible
    STATUS           current
    DESCRIPTION
        "Entry for the cucsBiosVfUCSMBootOrderRuleControlTable table."
    INDEX { cucsBiosVfUCSMBootOrderRuleControlInstanceId }
    ::= { cucsBiosVfUCSMBootOrderRuleControlTable 1 }

CucsBiosVfUCSMBootOrderRuleControlEntry ::= SEQUENCE {
    cucsBiosVfUCSMBootOrderRuleControlInstanceId                     CucsManagedObjectId,
    cucsBiosVfUCSMBootOrderRuleControlDn                             CucsManagedObjectDn,
    cucsBiosVfUCSMBootOrderRuleControlRn                             SnmpAdminString,
    cucsBiosVfUCSMBootOrderRuleControlVpUCSMBootOrderRule            CucsBiosVfUCSMBootOrderRuleControlVpUCSMBootOrderRule,
    cucsBiosVfUCSMBootOrderRuleControlPropAcl                        Unsigned64,
    cucsBiosVfUCSMBootOrderRuleControlSupportedByDefault             CucsBiosSupportedAction
}

cucsBiosVfUCSMBootOrderRuleControlInstanceId OBJECT-TYPE
    SYNTAX       CucsManagedObjectId
    MAX-ACCESS   not-accessible
    STATUS       current
    DESCRIPTION
        "Instance identifier of the managed object."
    ::= { cucsBiosVfUCSMBootOrderRuleControlEntry 1 }

cucsBiosVfUCSMBootOrderRuleControlDn OBJECT-TYPE
    SYNTAX       CucsManagedObjectDn
    MAX-ACCESS   read-only
    STATUS       current
    DESCRIPTION
        "Cisco UCS bios:VfUCSMBootOrderRuleControl:dn managed
        object property"
    ::= { cucsBiosVfUCSMBootOrderRuleControlEntry 2 }

cucsBiosVfUCSMBootOrderRuleControlRn OBJECT-TYPE
    SYNTAX       SnmpAdminString
    MAX-ACCESS   read-only
    STATUS       current
    DESCRIPTION
        "Cisco UCS bios:VfUCSMBootOrderRuleControl:rn managed
        object property"
    ::= { cucsBiosVfUCSMBootOrderRuleControlEntry 3 }

cucsBiosVfUCSMBootOrderRuleControlVpUCSMBootOrderRule OBJECT-TYPE
    SYNTAX       CucsBiosVfUCSMBootOrderRuleControlVpUCSMBootOrderRule
    MAX-ACCESS   read-only
    STATUS       current
    DESCRIPTION
        "Cisco UCS bios:VfUCSMBootOrderRuleControl:vpUCSMBootOrderRule
        managed object property"
    ::= { cucsBiosVfUCSMBootOrderRuleControlEntry 4 }

cucsBiosVfUCSMBootOrderRuleControlPropAcl OBJECT-TYPE
    SYNTAX       Unsigned64
    MAX-ACCESS   read-only
    STATUS       current
    DESCRIPTION
        "Cisco UCS bios:VfUCSMBootOrderRuleControl:propAcl
        managed object property"
    ::= { cucsBiosVfUCSMBootOrderRuleControlEntry 5 }

cucsBiosVfUCSMBootOrderRuleControlSupportedByDefault OBJECT-TYPE
    SYNTAX       CucsBiosSupportedAction
    MAX-ACCESS   read-only
    STATUS       current
    DESCRIPTION
        "Cisco UCS bios:VfUCSMBootOrderRuleControl:supportedByDefault
        managed object property"
    ::= { cucsBiosVfUCSMBootOrderRuleControlEntry 6 }

cucsBiosVfUEFIOSUseLegacyVideoTable OBJECT-TYPE
    SYNTAX           SEQUENCE OF CucsBiosVfUEFIOSUseLegacyVideoEntry
    MAX-ACCESS       not-accessible
    STATUS           current
    DESCRIPTION
        "Cisco UCS bios:VfUEFIOSUseLegacyVideo managed object table"
    ::= { cucsBiosObjects 34 }

cucsBiosVfUEFIOSUseLegacyVideoEntry OBJECT-TYPE
    SYNTAX           CucsBiosVfUEFIOSUseLegacyVideoEntry
    MAX-ACCESS       not-accessible
    STATUS           current
    DESCRIPTION
        "Entry for the cucsBiosVfUEFIOSUseLegacyVideoTable table."
    INDEX { cucsBiosVfUEFIOSUseLegacyVideoInstanceId }
    ::= { cucsBiosVfUEFIOSUseLegacyVideoTable 1 }

CucsBiosVfUEFIOSUseLegacyVideoEntry ::= SEQUENCE {
    cucsBiosVfUEFIOSUseLegacyVideoInstanceId                         CucsManagedObjectId,
    cucsBiosVfUEFIOSUseLegacyVideoDn                                 CucsManagedObjectDn,
    cucsBiosVfUEFIOSUseLegacyVideoRn                                 SnmpAdminString,
    cucsBiosVfUEFIOSUseLegacyVideoVpUEFIOSUseLegacyVideo             CucsBiosVfUEFIOSUseLegacyVideoVpUEFIOSUseLegacyVideo,
    cucsBiosVfUEFIOSUseLegacyVideoPropAcl                            Unsigned64,
    cucsBiosVfUEFIOSUseLegacyVideoSupportedByDefault                 CucsBiosSupportedAction
}

cucsBiosVfUEFIOSUseLegacyVideoInstanceId OBJECT-TYPE
    SYNTAX       CucsManagedObjectId
    MAX-ACCESS   not-accessible
    STATUS       current
    DESCRIPTION
        "Instance identifier of the managed object."
    ::= { cucsBiosVfUEFIOSUseLegacyVideoEntry 1 }

cucsBiosVfUEFIOSUseLegacyVideoDn OBJECT-TYPE
    SYNTAX       CucsManagedObjectDn
    MAX-ACCESS   read-only
    STATUS       current
    DESCRIPTION
        "Cisco UCS bios:VfUEFIOSUseLegacyVideo:dn managed object property"
    ::= { cucsBiosVfUEFIOSUseLegacyVideoEntry 2 }

cucsBiosVfUEFIOSUseLegacyVideoRn OBJECT-TYPE
    SYNTAX       SnmpAdminString
    MAX-ACCESS   read-only
    STATUS       current
    DESCRIPTION
        "Cisco UCS bios:VfUEFIOSUseLegacyVideo:rn managed object property"
    ::= { cucsBiosVfUEFIOSUseLegacyVideoEntry 3 }

cucsBiosVfUEFIOSUseLegacyVideoVpUEFIOSUseLegacyVideo OBJECT-TYPE
    SYNTAX       CucsBiosVfUEFIOSUseLegacyVideoVpUEFIOSUseLegacyVideo
    MAX-ACCESS   read-only
    STATUS       current
    DESCRIPTION
        "Cisco UCS bios:VfUEFIOSUseLegacyVideo:vpUEFIOSUseLegacyVideo
        managed object property"
    ::= { cucsBiosVfUEFIOSUseLegacyVideoEntry 4 }

cucsBiosVfUEFIOSUseLegacyVideoPropAcl OBJECT-TYPE
    SYNTAX       Unsigned64
    MAX-ACCESS   read-only
    STATUS       current
    DESCRIPTION
        "Cisco UCS bios:VfUEFIOSUseLegacyVideo:propAcl
        managed object property"
    ::= { cucsBiosVfUEFIOSUseLegacyVideoEntry 5 }

cucsBiosVfUEFIOSUseLegacyVideoSupportedByDefault OBJECT-TYPE
    SYNTAX       CucsBiosSupportedAction
    MAX-ACCESS   read-only
    STATUS       current
    DESCRIPTION
        "Cisco UCS bios:VfUEFIOSUseLegacyVideo:supportedByDefault
        managed object property"
    ::= { cucsBiosVfUEFIOSUseLegacyVideoEntry 6 }

cucsBiosVfUSBBootConfigTable OBJECT-TYPE
    SYNTAX           SEQUENCE OF CucsBiosVfUSBBootConfigEntry
    MAX-ACCESS       not-accessible
    STATUS           current
    DESCRIPTION
        "Cisco UCS bios:VfUSBBootConfig managed object table"
    ::= { cucsBiosObjects 32 }

cucsBiosVfUSBBootConfigEntry OBJECT-TYPE
    SYNTAX           CucsBiosVfUSBBootConfigEntry
    MAX-ACCESS       not-accessible
    STATUS           current
    DESCRIPTION
        "Entry for the cucsBiosVfUSBBootConfigTable table."
    INDEX { cucsBiosVfUSBBootConfigInstanceId }
    ::= { cucsBiosVfUSBBootConfigTable 1 }

CucsBiosVfUSBBootConfigEntry ::= SEQUENCE {
    cucsBiosVfUSBBootConfigInstanceId                                CucsManagedObjectId,
    cucsBiosVfUSBBootConfigDn                                        CucsManagedObjectDn,
    cucsBiosVfUSBBootConfigRn                                        SnmpAdminString,
    cucsBiosVfUSBBootConfigVpMakeDeviceNonBootable                   CucsBiosVfUSBBootConfigVpMakeDeviceNonBootable,
    cucsBiosVfUSBBootConfigVpLegacyUSBSupport                        CucsBiosVfUSBBootConfigVpLegacyUSBSupport,
    cucsBiosVfUSBBootConfigPropAcl                                   Unsigned64,
    cucsBiosVfUSBBootConfigSupportedByDefault                        CucsBiosSupportedAction
}

cucsBiosVfUSBBootConfigInstanceId OBJECT-TYPE
    SYNTAX       CucsManagedObjectId
    MAX-ACCESS   not-accessible
    STATUS       current
    DESCRIPTION
        "Instance identifier of the managed object."
    ::= { cucsBiosVfUSBBootConfigEntry 1 }

cucsBiosVfUSBBootConfigDn OBJECT-TYPE
    SYNTAX       CucsManagedObjectDn
    MAX-ACCESS   read-only
    STATUS       current
    DESCRIPTION
        "Cisco UCS bios:VfUSBBootConfig:dn managed object property"
    ::= { cucsBiosVfUSBBootConfigEntry 2 }

cucsBiosVfUSBBootConfigRn OBJECT-TYPE
    SYNTAX       SnmpAdminString
    MAX-ACCESS   read-only
    STATUS       current
    DESCRIPTION
        "Cisco UCS bios:VfUSBBootConfig:rn managed object property"
    ::= { cucsBiosVfUSBBootConfigEntry 3 }

cucsBiosVfUSBBootConfigVpMakeDeviceNonBootable OBJECT-TYPE
    SYNTAX       CucsBiosVfUSBBootConfigVpMakeDeviceNonBootable
    MAX-ACCESS   read-only
    STATUS       current
    DESCRIPTION
        "Cisco UCS bios:VfUSBBootConfig:vpMakeDeviceNonBootable
        managed object property"
    ::= { cucsBiosVfUSBBootConfigEntry 4 }

cucsBiosVfUSBBootConfigVpLegacyUSBSupport OBJECT-TYPE
    SYNTAX       CucsBiosVfUSBBootConfigVpLegacyUSBSupport
    MAX-ACCESS   read-only
    STATUS       current
    DESCRIPTION
        "Cisco UCS bios:VfUSBBootConfig:vpLegacyUSBSupport
        managed object property"
    ::= { cucsBiosVfUSBBootConfigEntry 5 }

cucsBiosVfUSBBootConfigPropAcl OBJECT-TYPE
    SYNTAX       Unsigned64
    MAX-ACCESS   read-only
    STATUS       current
    DESCRIPTION
        "Cisco UCS bios:VfUSBBootConfig:propAcl managed object property"
    ::= { cucsBiosVfUSBBootConfigEntry 6 }

cucsBiosVfUSBBootConfigSupportedByDefault OBJECT-TYPE
    SYNTAX       CucsBiosSupportedAction
    MAX-ACCESS   read-only
    STATUS       current
    DESCRIPTION
        "Cisco UCS bios:VfUSBBootConfig:supportedByDefault
        managed object property"
    ::= { cucsBiosVfUSBBootConfigEntry 7 }

cucsBiosVfUSBConfigurationTable OBJECT-TYPE
    SYNTAX           SEQUENCE OF CucsBiosVfUSBConfigurationEntry
    MAX-ACCESS       not-accessible
    STATUS           current
    DESCRIPTION
        "Cisco UCS bios:VfUSBConfiguration managed object table"
    ::= { cucsBiosObjects 80 }

cucsBiosVfUSBConfigurationEntry OBJECT-TYPE
    SYNTAX           CucsBiosVfUSBConfigurationEntry
    MAX-ACCESS       not-accessible
    STATUS           current
    DESCRIPTION
        "Entry for the cucsBiosVfUSBConfigurationTable table."
    INDEX { cucsBiosVfUSBConfigurationInstanceId }
    ::= { cucsBiosVfUSBConfigurationTable 1 }

CucsBiosVfUSBConfigurationEntry ::= SEQUENCE {
    cucsBiosVfUSBConfigurationInstanceId                             CucsManagedObjectId,
    cucsBiosVfUSBConfigurationDn                                     CucsManagedObjectDn,
    cucsBiosVfUSBConfigurationRn                                     SnmpAdminString,
    cucsBiosVfUSBConfigurationVpLegacyUSBSupport                     CucsBiosVfUSBConfigurationVpLegacyUSBSupport,
    cucsBiosVfUSBConfigurationVpXHCIMode                             CucsBiosVfUSBConfigurationVpXHCIMode,
    cucsBiosVfUSBConfigurationPropAcl                                Unsigned64,
    cucsBiosVfUSBConfigurationSupportedByDefault                     CucsBiosSupportedAction
}

cucsBiosVfUSBConfigurationInstanceId OBJECT-TYPE
    SYNTAX       CucsManagedObjectId
    MAX-ACCESS   not-accessible
    STATUS       current
    DESCRIPTION
        "Instance identifier of the managed object."
    ::= { cucsBiosVfUSBConfigurationEntry 1 }

cucsBiosVfUSBConfigurationDn OBJECT-TYPE
    SYNTAX       CucsManagedObjectDn
    MAX-ACCESS   read-only
    STATUS       current
    DESCRIPTION
        "Cisco UCS bios:VfUSBConfiguration:dn managed object property"
    ::= { cucsBiosVfUSBConfigurationEntry 2 }

cucsBiosVfUSBConfigurationRn OBJECT-TYPE
    SYNTAX       SnmpAdminString
    MAX-ACCESS   read-only
    STATUS       current
    DESCRIPTION
        "Cisco UCS bios:VfUSBConfiguration:rn managed object property"
    ::= { cucsBiosVfUSBConfigurationEntry 3 }

cucsBiosVfUSBConfigurationVpLegacyUSBSupport OBJECT-TYPE
    SYNTAX       CucsBiosVfUSBConfigurationVpLegacyUSBSupport
    MAX-ACCESS   read-only
    STATUS       current
    DESCRIPTION
        "Cisco UCS bios:VfUSBConfiguration:vpLegacyUSBSupport
        managed object property"
    ::= { cucsBiosVfUSBConfigurationEntry 4 }

cucsBiosVfUSBConfigurationVpXHCIMode OBJECT-TYPE
    SYNTAX       CucsBiosVfUSBConfigurationVpXHCIMode
    MAX-ACCESS   read-only
    STATUS       current
    DESCRIPTION
        "Cisco UCS bios:VfUSBConfiguration:vpXHCIMode managed
        object property"
    ::= { cucsBiosVfUSBConfigurationEntry 5 }

cucsBiosVfUSBConfigurationPropAcl OBJECT-TYPE
    SYNTAX       Unsigned64
    MAX-ACCESS   read-only
    STATUS       current
    DESCRIPTION
        "Cisco UCS bios:VfUSBConfiguration:propAcl managed
        object property"
    ::= { cucsBiosVfUSBConfigurationEntry 6 }

cucsBiosVfUSBConfigurationSupportedByDefault OBJECT-TYPE
    SYNTAX       CucsBiosSupportedAction
    MAX-ACCESS   read-only
    STATUS       current
    DESCRIPTION
        "Cisco UCS bios:VfUSBConfiguration:supportedByDefault
        managed object property"
    ::= { cucsBiosVfUSBConfigurationEntry 7 }

cucsBiosVfUSBFrontPanelAccessLockTable OBJECT-TYPE
    SYNTAX           SEQUENCE OF CucsBiosVfUSBFrontPanelAccessLockEntry
    MAX-ACCESS       not-accessible
    STATUS           current
    DESCRIPTION
        "Cisco UCS bios:VfUSBFrontPanelAccessLock managed object table"
    ::= { cucsBiosObjects 49 }

cucsBiosVfUSBFrontPanelAccessLockEntry OBJECT-TYPE
    SYNTAX           CucsBiosVfUSBFrontPanelAccessLockEntry
    MAX-ACCESS       not-accessible
    STATUS           current
    DESCRIPTION
        "Entry for the cucsBiosVfUSBFrontPanelAccessLockTable table."
    INDEX { cucsBiosVfUSBFrontPanelAccessLockInstanceId }
    ::= { cucsBiosVfUSBFrontPanelAccessLockTable 1 }

CucsBiosVfUSBFrontPanelAccessLockEntry ::= SEQUENCE {
    cucsBiosVfUSBFrontPanelAccessLockInstanceId                      CucsManagedObjectId,
    cucsBiosVfUSBFrontPanelAccessLockDn                              CucsManagedObjectDn,
    cucsBiosVfUSBFrontPanelAccessLockRn                              SnmpAdminString,
    cucsBiosVfUSBFrontPanelAccessLockVpUSBFrontPanelLock             CucsBiosVfUSBFrontPanelAccessLockVpUSBFrontPanelLock,
    cucsBiosVfUSBFrontPanelAccessLockPropAcl                         Unsigned64,
    cucsBiosVfUSBFrontPanelAccessLockSupportedByDefault              CucsBiosSupportedAction
}

cucsBiosVfUSBFrontPanelAccessLockInstanceId OBJECT-TYPE
    SYNTAX       CucsManagedObjectId
    MAX-ACCESS   not-accessible
    STATUS       current
    DESCRIPTION
        "Instance identifier of the managed object."
    ::= { cucsBiosVfUSBFrontPanelAccessLockEntry 1 }

cucsBiosVfUSBFrontPanelAccessLockDn OBJECT-TYPE
    SYNTAX       CucsManagedObjectDn
    MAX-ACCESS   read-only
    STATUS       current
    DESCRIPTION
        "Cisco UCS bios:VfUSBFrontPanelAccessLock:dn managed
        object property"
    ::= { cucsBiosVfUSBFrontPanelAccessLockEntry 2 }

cucsBiosVfUSBFrontPanelAccessLockRn OBJECT-TYPE
    SYNTAX       SnmpAdminString
    MAX-ACCESS   read-only
    STATUS       current
    DESCRIPTION
        "Cisco UCS bios:VfUSBFrontPanelAccessLock:rn managed
        object property"
    ::= { cucsBiosVfUSBFrontPanelAccessLockEntry 3 }

cucsBiosVfUSBFrontPanelAccessLockVpUSBFrontPanelLock OBJECT-TYPE
    SYNTAX       CucsBiosVfUSBFrontPanelAccessLockVpUSBFrontPanelLock
    MAX-ACCESS   read-only
    STATUS       current
    DESCRIPTION
        "Cisco UCS bios:VfUSBFrontPanelAccessLock:vpUSBFrontPanelLock
        managed object property"
    ::= { cucsBiosVfUSBFrontPanelAccessLockEntry 4 }

cucsBiosVfUSBFrontPanelAccessLockPropAcl OBJECT-TYPE
    SYNTAX       Unsigned64
    MAX-ACCESS   read-only
    STATUS       current
    DESCRIPTION
        "Cisco UCS bios:VfUSBFrontPanelAccessLock:propAcl
        managed object property"
    ::= { cucsBiosVfUSBFrontPanelAccessLockEntry 5 }

cucsBiosVfUSBFrontPanelAccessLockSupportedByDefault OBJECT-TYPE
    SYNTAX       CucsBiosSupportedAction
    MAX-ACCESS   read-only
    STATUS       current
    DESCRIPTION
        "Cisco UCS bios:VfUSBFrontPanelAccessLock:supportedByDefault
        managed object property"
    ::= { cucsBiosVfUSBFrontPanelAccessLockEntry 6 }

cucsBiosVfUSBPortConfigurationTable OBJECT-TYPE
    SYNTAX           SEQUENCE OF CucsBiosVfUSBPortConfigurationEntry
    MAX-ACCESS       not-accessible
    STATUS           current
    DESCRIPTION
        "Cisco UCS bios:VfUSBPortConfiguration managed object table"
    ::= { cucsBiosObjects 76 }

cucsBiosVfUSBPortConfigurationEntry OBJECT-TYPE
    SYNTAX           CucsBiosVfUSBPortConfigurationEntry
    MAX-ACCESS       not-accessible
    STATUS           current
    DESCRIPTION
        "Entry for the cucsBiosVfUSBPortConfigurationTable table."
    INDEX { cucsBiosVfUSBPortConfigurationInstanceId }
    ::= { cucsBiosVfUSBPortConfigurationTable 1 }

CucsBiosVfUSBPortConfigurationEntry ::= SEQUENCE {
    cucsBiosVfUSBPortConfigurationInstanceId                         CucsManagedObjectId,
    cucsBiosVfUSBPortConfigurationDn                                 CucsManagedObjectDn,
    cucsBiosVfUSBPortConfigurationRn                                 SnmpAdminString,
    cucsBiosVfUSBPortConfigurationVpPort6064Emulation                CucsBiosVfUSBPortConfigurationVpPort6064Emulation,
    cucsBiosVfUSBPortConfigurationVpUSBPortFront                     CucsBiosVfUSBPortConfigurationVpUSBPortFront,
    cucsBiosVfUSBPortConfigurationVpUSBPortInternal                  CucsBiosVfUSBPortConfigurationVpUSBPortInternal,
    cucsBiosVfUSBPortConfigurationVpUSBPortKVM                       CucsBiosVfUSBPortConfigurationVpUSBPortKVM,
    cucsBiosVfUSBPortConfigurationVpUSBPortRear                      CucsBiosVfUSBPortConfigurationVpUSBPortRear,
    cucsBiosVfUSBPortConfigurationVpUSBPortSDCard                    CucsBiosVfUSBPortConfigurationVpUSBPortSDCard,
    cucsBiosVfUSBPortConfigurationVpUSBPortVMedia                    CucsBiosVfUSBPortConfigurationVpUSBPortVMedia,
    cucsBiosVfUSBPortConfigurationPropAcl                            Unsigned64,
    cucsBiosVfUSBPortConfigurationSupportedByDefault                 CucsBiosSupportedAction
}

cucsBiosVfUSBPortConfigurationInstanceId OBJECT-TYPE
    SYNTAX       CucsManagedObjectId
    MAX-ACCESS   not-accessible
    STATUS       current
    DESCRIPTION
        "Instance identifier of the managed object."
    ::= { cucsBiosVfUSBPortConfigurationEntry 1 }

cucsBiosVfUSBPortConfigurationDn OBJECT-TYPE
    SYNTAX       CucsManagedObjectDn
    MAX-ACCESS   read-only
    STATUS       current
    DESCRIPTION
        "Cisco UCS bios:VfUSBPortConfiguration:dn managed object property"
    ::= { cucsBiosVfUSBPortConfigurationEntry 2 }

cucsBiosVfUSBPortConfigurationRn OBJECT-TYPE
    SYNTAX       SnmpAdminString
    MAX-ACCESS   read-only
    STATUS       current
    DESCRIPTION
        "Cisco UCS bios:VfUSBPortConfiguration:rn managed object property"
    ::= { cucsBiosVfUSBPortConfigurationEntry 3 }

cucsBiosVfUSBPortConfigurationVpPort6064Emulation OBJECT-TYPE
    SYNTAX       CucsBiosVfUSBPortConfigurationVpPort6064Emulation
    MAX-ACCESS   read-only
    STATUS       current
    DESCRIPTION
        "Cisco UCS bios:VfUSBPortConfiguration:vpPort6064Emulation
        managed object property"
    ::= { cucsBiosVfUSBPortConfigurationEntry 4 }

cucsBiosVfUSBPortConfigurationVpUSBPortFront OBJECT-TYPE
    SYNTAX       CucsBiosVfUSBPortConfigurationVpUSBPortFront
    MAX-ACCESS   read-only
    STATUS       current
    DESCRIPTION
        "Cisco UCS bios:VfUSBPortConfiguration:vpUSBPortFront
        managed object property"
    ::= { cucsBiosVfUSBPortConfigurationEntry 5 }

cucsBiosVfUSBPortConfigurationVpUSBPortInternal OBJECT-TYPE
    SYNTAX       CucsBiosVfUSBPortConfigurationVpUSBPortInternal
    MAX-ACCESS   read-only
    STATUS       current
    DESCRIPTION
        "Cisco UCS bios:VfUSBPortConfiguration:vpUSBPortInternal
        managed object property"
    ::= { cucsBiosVfUSBPortConfigurationEntry 6 }

cucsBiosVfUSBPortConfigurationVpUSBPortKVM OBJECT-TYPE
    SYNTAX       CucsBiosVfUSBPortConfigurationVpUSBPortKVM
    MAX-ACCESS   read-only
    STATUS       current
    DESCRIPTION
        "Cisco UCS bios:VfUSBPortConfiguration:vpUSBPortKVM
        managed object property"
    ::= { cucsBiosVfUSBPortConfigurationEntry 7 }

cucsBiosVfUSBPortConfigurationVpUSBPortRear OBJECT-TYPE
    SYNTAX       CucsBiosVfUSBPortConfigurationVpUSBPortRear
    MAX-ACCESS   read-only
    STATUS       current
    DESCRIPTION
        "Cisco UCS bios:VfUSBPortConfiguration:vpUSBPortRear
        managed object property"
    ::= { cucsBiosVfUSBPortConfigurationEntry 8 }

cucsBiosVfUSBPortConfigurationVpUSBPortSDCard OBJECT-TYPE
    SYNTAX       CucsBiosVfUSBPortConfigurationVpUSBPortSDCard
    MAX-ACCESS   read-only
    STATUS       current
    DESCRIPTION
        "Cisco UCS bios:VfUSBPortConfiguration:vpUSBPortSDCard
        managed object property"
    ::= { cucsBiosVfUSBPortConfigurationEntry 9 }

cucsBiosVfUSBPortConfigurationVpUSBPortVMedia OBJECT-TYPE
    SYNTAX       CucsBiosVfUSBPortConfigurationVpUSBPortVMedia
    MAX-ACCESS   read-only
    STATUS       current
    DESCRIPTION
        "Cisco UCS bios:VfUSBPortConfiguration:vpUSBPortVMedia
        managed object property"
    ::= { cucsBiosVfUSBPortConfigurationEntry 10 }

cucsBiosVfUSBPortConfigurationPropAcl OBJECT-TYPE
    SYNTAX       Unsigned64
    MAX-ACCESS   read-only
    STATUS       current
    DESCRIPTION
        "Cisco UCS bios:VfUSBPortConfiguration:propAcl
        managed object property"
    ::= { cucsBiosVfUSBPortConfigurationEntry 11 }

cucsBiosVfUSBPortConfigurationSupportedByDefault OBJECT-TYPE
    SYNTAX       CucsBiosSupportedAction
    MAX-ACCESS   read-only
    STATUS       current
    DESCRIPTION
        "Cisco UCS bios:VfUSBPortConfiguration:supportedByDefault
        managed object property"
    ::= { cucsBiosVfUSBPortConfigurationEntry 12 }

cucsBiosVfUSBSystemIdlePowerOptimizingSettingTable OBJECT-TYPE
    SYNTAX           SEQUENCE OF CucsBiosVfUSBSystemIdlePowerOptimizingSettingEntry
    MAX-ACCESS       not-accessible
    STATUS           current
    DESCRIPTION
        "Cisco UCS bios:VfUSBSystemIdlePowerOptimizingSetting
        managed object table"
    ::= { cucsBiosObjects 50 }

cucsBiosVfUSBSystemIdlePowerOptimizingSettingEntry OBJECT-TYPE
    SYNTAX           CucsBiosVfUSBSystemIdlePowerOptimizingSettingEntry
    MAX-ACCESS       not-accessible
    STATUS           current
    DESCRIPTION
        "Entry for the cucsBiosVfUSBSystemIdlePowerOptimizingSettingTable table."
    INDEX { cucsBiosVfUSBSystemIdlePowerOptimizingSettingInstanceId }
    ::= { cucsBiosVfUSBSystemIdlePowerOptimizingSettingTable 1 }

CucsBiosVfUSBSystemIdlePowerOptimizingSettingEntry ::= SEQUENCE {
    cucsBiosVfUSBSystemIdlePowerOptimizingSettingInstanceId          CucsManagedObjectId,
    cucsBiosVfUSBSystemIdlePowerOptimizingSettingDn                  CucsManagedObjectDn,
    cucsBiosVfUSBSystemIdlePowerOptimizingSettingRn                  SnmpAdminString,
    cucsBiosVfUSBSysIdlePowerOptimizingSettingVpUSBIdlePowerOptimize CucsBiosVfUSBSysIdlePowerOptimizingSettingVpUSBIdlePowerOptimize,
    cucsBiosVfUSBSystemIdlePowerOptimizingSettingPropAcl             Unsigned64,
    cucsBiosVfUSBSystemIdlePowerOptimizingSettingSupportedByDefault  CucsBiosSupportedAction
}

cucsBiosVfUSBSystemIdlePowerOptimizingSettingInstanceId OBJECT-TYPE
    SYNTAX       CucsManagedObjectId
    MAX-ACCESS   not-accessible
    STATUS       current
    DESCRIPTION
        "Instance identifier of the managed object."
    ::= { cucsBiosVfUSBSystemIdlePowerOptimizingSettingEntry 1 }

cucsBiosVfUSBSystemIdlePowerOptimizingSettingDn OBJECT-TYPE
    SYNTAX       CucsManagedObjectDn
    MAX-ACCESS   read-only
    STATUS       current
    DESCRIPTION
        "Cisco UCS bios:VfUSBSystemIdlePowerOptimizingSetting:dn
        managed object property"
    ::= { cucsBiosVfUSBSystemIdlePowerOptimizingSettingEntry 2 }

cucsBiosVfUSBSystemIdlePowerOptimizingSettingRn OBJECT-TYPE
    SYNTAX       SnmpAdminString
    MAX-ACCESS   read-only
    STATUS       current
    DESCRIPTION
        "Cisco UCS bios:VfUSBSystemIdlePowerOptimizingSetting:rn
        managed object property"
    ::= { cucsBiosVfUSBSystemIdlePowerOptimizingSettingEntry 3 }

cucsBiosVfUSBSysIdlePowerOptimizingSettingVpUSBIdlePowerOptimize OBJECT-TYPE
    SYNTAX       CucsBiosVfUSBSysIdlePowerOptimizingSettingVpUSBIdlePowerOptimize
    MAX-ACCESS   read-only
    STATUS       current
    DESCRIPTION
        "Cisco UCS bios:VfUSBSystemIdlePowerOptimizingSetting:vpUSBIdlePow
        erOptimizing managed object property"
    ::= { cucsBiosVfUSBSystemIdlePowerOptimizingSettingEntry 4 }

cucsBiosVfUSBSystemIdlePowerOptimizingSettingPropAcl OBJECT-TYPE
    SYNTAX       Unsigned64
    MAX-ACCESS   read-only
    STATUS       current
    DESCRIPTION
        "Cisco UCS bios:VfUSBSystemIdlePowerOptimizingSetting:propAcl
        managed object property"
    ::= { cucsBiosVfUSBSystemIdlePowerOptimizingSettingEntry 5 }

cucsBiosVfUSBSystemIdlePowerOptimizingSettingSupportedByDefault OBJECT-TYPE
    SYNTAX       CucsBiosSupportedAction
    MAX-ACCESS   read-only
    STATUS       current
    DESCRIPTION
        "Cisco UCS bios:VfUSBSystemIdlePowerOptimizingSetting:supportedByD
        efault managed object property"
    ::= { cucsBiosVfUSBSystemIdlePowerOptimizingSettingEntry 6 }

cucsBiosVfVGAPriorityTable OBJECT-TYPE
    SYNTAX           SEQUENCE OF CucsBiosVfVGAPriorityEntry
    MAX-ACCESS       not-accessible
    STATUS           current
    DESCRIPTION
        "Cisco UCS bios:VfVGAPriority managed object table"
    ::= { cucsBiosObjects 77 }

cucsBiosVfVGAPriorityEntry OBJECT-TYPE
    SYNTAX           CucsBiosVfVGAPriorityEntry
    MAX-ACCESS       not-accessible
    STATUS           current
    DESCRIPTION
        "Entry for the cucsBiosVfVGAPriorityTable table."
    INDEX { cucsBiosVfVGAPriorityInstanceId }
    ::= { cucsBiosVfVGAPriorityTable 1 }

CucsBiosVfVGAPriorityEntry ::= SEQUENCE {
    cucsBiosVfVGAPriorityInstanceId                                  CucsManagedObjectId,
    cucsBiosVfVGAPriorityDn                                          CucsManagedObjectDn,
    cucsBiosVfVGAPriorityRn                                          SnmpAdminString,
    cucsBiosVfVGAPriorityVpVGAPriority                               CucsBiosVfVGAPriorityVpVGAPriority,
    cucsBiosVfVGAPriorityPropAcl                                     Unsigned64,
    cucsBiosVfVGAPrioritySupportedByDefault                          CucsBiosSupportedAction
}

cucsBiosVfVGAPriorityInstanceId OBJECT-TYPE
    SYNTAX       CucsManagedObjectId
    MAX-ACCESS   not-accessible
    STATUS       current
    DESCRIPTION
        "Instance identifier of the managed object."
    ::= { cucsBiosVfVGAPriorityEntry 1 }

cucsBiosVfVGAPriorityDn OBJECT-TYPE
    SYNTAX       CucsManagedObjectDn
    MAX-ACCESS   read-only
    STATUS       current
    DESCRIPTION
        "Cisco UCS bios:VfVGAPriority:dn managed object property"
    ::= { cucsBiosVfVGAPriorityEntry 2 }

cucsBiosVfVGAPriorityRn OBJECT-TYPE
    SYNTAX       SnmpAdminString
    MAX-ACCESS   read-only
    STATUS       current
    DESCRIPTION
        "Cisco UCS bios:VfVGAPriority:rn managed object property"
    ::= { cucsBiosVfVGAPriorityEntry 3 }

cucsBiosVfVGAPriorityVpVGAPriority OBJECT-TYPE
    SYNTAX       CucsBiosVfVGAPriorityVpVGAPriority
    MAX-ACCESS   read-only
    STATUS       current
    DESCRIPTION
        "Cisco UCS bios:VfVGAPriority:vpVGAPriority managed
        object property"
    ::= { cucsBiosVfVGAPriorityEntry 4 }

cucsBiosVfVGAPriorityPropAcl OBJECT-TYPE
    SYNTAX       Unsigned64
    MAX-ACCESS   read-only
    STATUS       current
    DESCRIPTION
        "Cisco UCS bios:VfVGAPriority:propAcl managed object property"
    ::= { cucsBiosVfVGAPriorityEntry 5 }

cucsBiosVfVGAPrioritySupportedByDefault OBJECT-TYPE
    SYNTAX       CucsBiosSupportedAction
    MAX-ACCESS   read-only
    STATUS       current
    DESCRIPTION
        "Cisco UCS bios:VfVGAPriority:supportedByDefault
        managed object property"
    ::= { cucsBiosVfVGAPriorityEntry 6 }

cucsBiosVfWorkloadConfigurationTable OBJECT-TYPE
    SYNTAX           SEQUENCE OF CucsBiosVfWorkloadConfigurationEntry
    MAX-ACCESS       not-accessible
    STATUS           current
    DESCRIPTION
        "Cisco UCS bios:VfWorkloadConfiguration managed object table"
    ::= { cucsBiosObjects 110 }

cucsBiosVfWorkloadConfigurationEntry OBJECT-TYPE
    SYNTAX           CucsBiosVfWorkloadConfigurationEntry
    MAX-ACCESS       not-accessible
    STATUS           current
    DESCRIPTION
        "Entry for the cucsBiosVfWorkloadConfigurationTable table."
    INDEX { cucsBiosVfWorkloadConfigurationInstanceId }
    ::= { cucsBiosVfWorkloadConfigurationTable 1 }

CucsBiosVfWorkloadConfigurationEntry ::= SEQUENCE {
    cucsBiosVfWorkloadConfigurationInstanceId                        CucsManagedObjectId,
    cucsBiosVfWorkloadConfigurationDn                                CucsManagedObjectDn,
    cucsBiosVfWorkloadConfigurationRn                                SnmpAdminString,
    cucsBiosVfWorkloadConfigurationPropAcl                           Unsigned64,
    cucsBiosVfWorkloadConfigurationSupportedByDefault                CucsBiosSupportedAction,
    cucsBiosVfWorkloadConfigurationVpWorkloadConfiguration           CucsBiosVfWorkloadConfigurationVpWorkloadConfiguration
}

cucsBiosVfWorkloadConfigurationInstanceId OBJECT-TYPE
    SYNTAX       CucsManagedObjectId
    MAX-ACCESS   not-accessible
    STATUS       current
    DESCRIPTION
        "Instance identifier of the managed object."
    ::= { cucsBiosVfWorkloadConfigurationEntry 1 }

cucsBiosVfWorkloadConfigurationDn OBJECT-TYPE
    SYNTAX       CucsManagedObjectDn
    MAX-ACCESS   read-only
    STATUS       current
    DESCRIPTION
        "Cisco UCS bios:VfWorkloadConfiguration:dn managed
        object property"
    ::= { cucsBiosVfWorkloadConfigurationEntry 2 }

cucsBiosVfWorkloadConfigurationRn OBJECT-TYPE
    SYNTAX       SnmpAdminString
    MAX-ACCESS   read-only
    STATUS       current
    DESCRIPTION
        "Cisco UCS bios:VfWorkloadConfiguration:rn managed
        object property"
    ::= { cucsBiosVfWorkloadConfigurationEntry 3 }

cucsBiosVfWorkloadConfigurationPropAcl OBJECT-TYPE
    SYNTAX       Unsigned64
    MAX-ACCESS   read-only
    STATUS       current
    DESCRIPTION
        "Cisco UCS bios:VfWorkloadConfiguration:propAcl
        managed object property"
    ::= { cucsBiosVfWorkloadConfigurationEntry 4 }

cucsBiosVfWorkloadConfigurationSupportedByDefault OBJECT-TYPE
    SYNTAX       CucsBiosSupportedAction
    MAX-ACCESS   read-only
    STATUS       current
    DESCRIPTION
        "Cisco UCS bios:VfWorkloadConfiguration:supportedByDefault
        managed object property"
    ::= { cucsBiosVfWorkloadConfigurationEntry 5 }

cucsBiosVfWorkloadConfigurationVpWorkloadConfiguration OBJECT-TYPE
    SYNTAX       CucsBiosVfWorkloadConfigurationVpWorkloadConfiguration
    MAX-ACCESS   read-only
    STATUS       current
    DESCRIPTION
        "Cisco UCS bios:VfWorkloadConfiguration:vpWorkloadConfiguration
        managed object property"
    ::= { cucsBiosVfWorkloadConfigurationEntry 6 }

END
