CTRON-OIDS DEFINITIONS ::= BEGIN

IMPORTS
    enterprises
            FROM RFC1155-SMI;

cabletron OBJECT IDENTIFIER ::= { enterprises 52 }

--  Organization
--    Enterasys Networks
--  ContactInfo
--    Postal:  Enterasys Networks
--             50 Minuteman Rd.
--             Andover, MA 01801-1008
--             USA
--    Phone:   +1 978 684 1000
--    E-mail: support@enterasys.com
--    WWW:    http://www.enterasys.com
--  Description
--    ctron-oids.txt
--    Part Number: 2170562-01
--    LAST-UPDATED "200311041539Z"  - Tue Nov  4 15:39 GMT 2003
--    REVISION     "200311041539Z"  - Tue Nov  4 15:39 GMT 2003
--    DESCRIPTION  "Added OIDs for powerPC8241 and powerPC8245."
--
--    REVISION     "September 11, 2001"
--    DESCRIPTION  "Revision: 1.19.15"
--
--    This module provides authoritative definitions for part
--    of the naming tree below:
--
--    cabletron { enterprises 52 }
--
--    This module will be extended, as additional sub-sections
--    of this naming tree are defined.
--
--    Enterasys Networks reserves the right to make changes in
--    specification and other information contained in this document
--    without prior notice.  The reader should consult Enterasys Networks
--    to determine whether any such changes have been made.
--
--    In no event shall Enterasys Networks be liable for any incidental,
--    indirect, special, or consequential damages whatsoever (including
--    but not limited to lost profits) arising out of or related to this
--    document or the information contained in it, even if Enterasys
--    Networks has been advised of, known, or should have known, the
--    possibility of such damages.
--
--    Enterasys grants vendors, end-users, and other interested parties
--    a non-exclusive license to use this Specification in connection
--    with the management of Enterasys or Cabletron products.
--
--    Copyright February 1999 Cabletron Systems
--    Copyright September 2001 Enterasys Networks
--
--    The assigned enterprise MIB tree for Cabletron System

namingTree OBJECT IDENTIFIER ::= { cabletron 3 }
-- OBJECT-IDENTITY
--  Status
--    mandatory
--  Descr
--    All Cabletron identification object identifiers.

v2conformance OBJECT IDENTIFIER ::= { cabletron 5 }
-- OBJECT-IDENTITY
--  Status
--    mandatory
--  Descr
--    Cabletron v2conformance tree.  All MIBs which comply to v2
--    standards are identified under this branch.  The actual
--    object definitions for the compliance statements and agent
--    ability statements are contained in their corresponding
--    MIB module.

trapDefinitions OBJECT IDENTIFIER ::= { cabletron 6 }
-- OBJECT-IDENTITY
--  Status
--    mandatory
--  Descr
--    With the advent of SNMPv2 all traps are identified via
--    an OID.  This branch of the Cabletron naming tree is
--    reserved for all Cabletron trap definitions.

chassisType OBJECT IDENTIFIER ::= { namingTree 1 }
-- OBJECT-IDENTITY
--  Status
--    mandatory
--  Descr
--    This is the chassis type naming tree.  Every chassis has a
--    unique value in this branch.

ctUnknown OBJECT IDENTIFIER ::= { chassisType 1 }
-- OBJECT-IDENTITY
--  Status
--    mandatory
--  Descr
--    If the chassis type is unknown this value is used.

ctMMAC8 OBJECT IDENTIFIER ::= { chassisType 2 }
-- OBJECT-IDENTITY
--  Status
--    mandatory
--  Descr
--    The MMAC8 chassis.

ctMMAC5 OBJECT IDENTIFIER ::= { chassisType 3 }
-- OBJECT-IDENTITY
--  Status
--    mandatory
--  Descr
--    The MMAC5 chassis type.

ctMMAC3 OBJECT IDENTIFIER ::= { chassisType 4 }
-- OBJECT-IDENTITY
--  Status
--    mandatory
--  Descr
--    The MMAC3 chassis type.

ctMINIMMAC OBJECT IDENTIFIER ::= { chassisType 5 }
-- OBJECT-IDENTITY
--  Status
--    mandatory
--  Descr
--    The Mini-MMAC chassis type.

ctMRXI OBJECT IDENTIFIER ::= { chassisType 6 }
-- OBJECT-IDENTITY
--  Status
--    mandatory
--  Descr
--    The MRXi-24 chassis type.

ctM3FNBShunt OBJECT IDENTIFIER ::= { chassisType 7 }
-- OBJECT-IDENTITY
--  Status
--    mandatory

ctM5FNBShunt OBJECT IDENTIFIER ::= { chassisType 8 }
-- OBJECT-IDENTITY
--  Status
--    mandatory

ctM8FNB OBJECT IDENTIFIER ::= { chassisType 9 }
-- OBJECT-IDENTITY
--  Status
--    mandatory

ctNonFNB OBJECT IDENTIFIER ::= { chassisType 10 }
-- OBJECT-IDENTITY
--  Status
--    mandatory
--  Descr
--    The non FNB chassis type.

ctMMAC3FNBShunt OBJECT IDENTIFIER ::= { chassisType 11 }
-- OBJECT-IDENTITY
--  Status
--    mandatory

ctMMAC5FNBShunt OBJECT IDENTIFIER ::= { chassisType 12 }
-- OBJECT-IDENTITY
--  Status
--    mandatory

ctMMAC8FNBShunt OBJECT IDENTIFIER ::= { chassisType 13 }
-- OBJECT-IDENTITY
--  Status
--    mandatory

ctM8FNBShunt OBJECT IDENTIFIER ::= { chassisType 14 }
-- OBJECT-IDENTITY
--  Status
--    mandatory

ctTRXI OBJECT IDENTIFIER ::= { chassisType 15 }
-- OBJECT-IDENTITY
--  Status
--    mandatory
--  Descr
--    The TRXI chassis type.

ctStandAlone OBJECT IDENTIFIER ::= { chassisType 16 }
-- OBJECT-IDENTITY
--  Status
--    mandatory
--  Descr
--    This type is used for all standalone chassis.

ctMMACPlus14 OBJECT IDENTIFIER ::= { chassisType 17 }
-- OBJECT-IDENTITY
--  Status
--    mandatory
--  Descr
--    The 14 device slot MMAC Plus chassis.

ctMMACPlus6 OBJECT IDENTIFIER ::= { chassisType 18 }
-- OBJECT-IDENTITY
--  Status
--    mandatory
--  Descr
--    The 6 device slot MMAC Plus chassis.

ctWanCyberSwitchNE2000 OBJECT IDENTIFIER ::= { chassisType 19 }
-- OBJECT-IDENTITY
--  Status
--    mandatory
--  Descr
--    LAN/WAN Bridge/Router with 3 slots to accomodate multiple WAN
--    technologies.  Up to 8 ISDN BRI ports or 2 PRI ports, Digital
--    Modem, V.35 and Dedicated Lines. Supports TCP/IP and optionally
--    IPX, Frame Relay and X.25.  Supports ML-PPP and compression.  Single
--    or dual port Ethernet capability.

ctWanCyberSwitchNe4000 OBJECT IDENTIFIER ::= { chassisType 20 }
-- OBJECT-IDENTITY
--  Status
--    mandatory
--  Descr
--    LAN/WAN Bridge/Router with 6 slots to accomodate multiple WAN
--    technologies.  Up to 16 ISDN BRI ports or 4 PRI ports, Digital
--    Modem, V.35 and Dedicated Lines. Supports TCP/IP and optionally
--    IPX, Frame Relay and X.25.  Supports ML-PPP and compression.  Single
--    or dual port Ethernet capability.

ctWanCyberSwitchNE5000 OBJECT IDENTIFIER ::= { chassisType 21 }
-- OBJECT-IDENTITY
--  Status
--    mandatory
--  Descr
--    LAN/WAN Bridge/Router with 8 slots to accomodate multiple WAN
--    technologies.  Up to 24 ISDN BRI ports or 6 PRI ports, Digital
--    Modem, V.35 and Dedicated Lines. Supports TCP/IP and optionally
--    IPX, Frame Relay and X.25.  Supports ML-PPP and compression.  Single
--    or dual port Ethernet capability.

moduleType OBJECT IDENTIFIER ::= { namingTree 2 }
-- OBJECT-IDENTITY
--  Status
--    mandatory
--  Descr
--    This naming tree is for all older Cabletron modules.  Newer
--    devices are defined under { namingTree 9 }.

mtThinMim1 OBJECT IDENTIFIER ::= { moduleType 16 }
-- OBJECT-IDENTITY
--  Status
--    mandatory

mtFDMMIM24 OBJECT IDENTIFIER ::= { moduleType 32 }
-- OBJECT-IDENTITY
--  Status
--    mandatory

mtFDMMIM14to46 OBJECT IDENTIFIER ::= { moduleType 33 }
-- OBJECT-IDENTITY
--  Status
--    mandatory
--  Descr
--    FDDI to Ethernet Bridge/Management (MIM MMF A/B and 4 STP M ports,
--    6 STP DB 9 M ports, 6 UTP M ports, 6 STP RJ45 M ports)

mtFDMMIM04To44 OBJECT IDENTIFIER ::= { moduleType 34 }
-- OBJECT-IDENTITY
--  Status
--    mandatory
--  Descr
--    FDDI to Ethernet Bridge/Management MIM 4 SAS to 4 STP M ports

mtFDMMIM00 OBJECT IDENTIFIER ::= { moduleType 35 }
-- OBJECT-IDENTITY
--  Status
--    mandatory
--  Descr
--    FDDI to Ethernet Bridge/Management MIM

mtFDMMIM30 OBJECT IDENTIFIER ::= { moduleType 39 }
-- OBJECT-IDENTITY
--  Status
--    mandatory
--  Descr
--    FDDI to Ethernet Bridge/Management SMF A/B

mtFDCMIM28 OBJECT IDENTIFIER ::= { moduleType 40 }
-- OBJECT-IDENTITY
--  Status
--    mandatory
--  Descr
--    FDDI Concentrator with 8 UTP M ports

mtFDCMIM18 OBJECT IDENTIFIER ::= { moduleType 41 }
-- OBJECT-IDENTITY
--  Status
--    mandatory
--  Descr
--    FDDI Concentrator with 8 STP M ports

mtFDCMIM08 OBJECT IDENTIFIER ::= { moduleType 42 }
-- OBJECT-IDENTITY
--  Status
--    mandatory
--  Descr
--    FDDI Concentrator with 8 PMD M ports

mtFDCMIM04 OBJECT IDENTIFIER ::= { moduleType 43 }
-- OBJECT-IDENTITY
--  Status
--    mandatory
--  Descr
--    FDDI Concentrator with 4 PMD M ports

mtFDCMIM24 OBJECT IDENTIFIER ::= { moduleType 44 }
-- OBJECT-IDENTITY
--  Status
--    mandatory
--  Descr
--    FDDI Concentrator with 4 UTP M ports

mtFDCMIM14 OBJECT IDENTIFIER ::= { moduleType 45 }
-- OBJECT-IDENTITY
--  Status
--    mandatory
--  Descr
--    FDDI Concentrator with 4 STP M ports

mtFDCMIM38 OBJECT IDENTIFIER ::= { moduleType 46 }
-- OBJECT-IDENTITY
--  Status
--    mandatory
--  Descr
--    FDDI Concentrator with 8 SMF M ports

mtFDCMIM34 OBJECT IDENTIFIER ::= { moduleType 47 }
-- OBJECT-IDENTITY
--  Status
--    mandatory
--  Descr
--    FDDI Concentrator with 4 SMF M ports

mtTRMIM12 OBJECT IDENTIFIER ::= { moduleType 48 }
-- OBJECT-IDENTITY
--  Status
--    mandatory
--  Descr
--    12 Port STP DB9s

mtTRMIM10R OBJECT IDENTIFIER ::= { moduleType 49 }
-- OBJECT-IDENTITY
--  Status
--    mandatory
--  Descr
--    10 Port STP DB9s, Ring-In/Ring-Out copper

mtTRMIM22 OBJECT IDENTIFIER ::= { moduleType 50 }
-- OBJECT-IDENTITY
--  Status
--    mandatory
--  Descr
--    12 Port UTP with RJ45s

mtTRMIM20R OBJECT IDENTIFIER ::= { moduleType 51 }
-- OBJECT-IDENTITY
--  Status
--    mandatory
--  Descr
--    10 Port UTP with RJ45 with Ring-In/Ring-Out DB9

mtTRMIM62A OBJECT IDENTIFIER ::= { moduleType 52 }
-- OBJECT-IDENTITY
--  Status
--    mandatory
--  Descr
--    12 port COAX with BNC connectors.

mtTRMIM24ToA OBJECT IDENTIFIER ::= { moduleType 54 }
-- OBJECT-IDENTITY
--  Status
--    mandatory
--  Descr
--    24 Port UTP with RJ45, passive to active

mtTRMIM22ToA OBJECT IDENTIFIER ::= { moduleType 55 }
-- OBJECT-IDENTITY
--  Status
--    mandatory
--  Descr
--    12 Port UTP with RJ45, passive to active

mtTRFMIM28 OBJECT IDENTIFIER ::= { moduleType 56 }
-- OBJECT-IDENTITY
--  Status
--    mandatory
--  Descr
--    18 Port with multi-mode fiber ST connectors

mtTRFMIM22 OBJECT IDENTIFIER ::= { moduleType 57 }
-- OBJECT-IDENTITY
--  Status
--    mandatory
--  Descr
--    12 Port multi-mode fiber with ST connectors

mtTRRMIMA OBJECT IDENTIFIER ::= { moduleType 58 }
-- OBJECT-IDENTITY
--  Status
--    mandatory
--  Descr
--    Token-Ring Repeater with copper/fiber Ring-In/Ring-Out

mtTRFMIM26 OBJECT IDENTIFIER ::= { moduleType 59 }
-- OBJECT-IDENTITY
--  Status
--    mandatory
--  Descr
--    6 Port multi-mode fiber with ST connectors

mtTRMIM34A OBJECT IDENTIFIER ::= { moduleType 60 }
-- OBJECT-IDENTITY
--  Status
--    mandatory
--  Descr
--    24 Port active UTP with 2 50 Pos

mtTRMIM32A OBJECT IDENTIFIER ::= { moduleType 61 }
-- OBJECT-IDENTITY
--  Status
--    mandatory
--  Descr
--    12 Port active UTP with 1 50 Pos

mtTRMIM44ToA OBJECT IDENTIFIER ::= { moduleType 62 }
-- OBJECT-IDENTITY
--  Status
--    mandatory
--  Descr
--    24 Port STP with shielded RJ45s, passive to active

mtTRMIM42ToA OBJECT IDENTIFIER ::= { moduleType 63 }
-- OBJECT-IDENTITY
--  Status
--    mandatory
--  Descr
--    12 Port STP with shielded RJ45s, passive to active

mtTPMIMT1 OBJECT IDENTIFIER ::= { moduleType 65 }
-- OBJECT-IDENTITY
--  Status
--    mandatory
--  Descr
--    10Base-T, 12 DB9s, non-ASIC based

mtTPMIMT OBJECT IDENTIFIER ::= { moduleType 66 }
-- OBJECT-IDENTITY
--  Status
--    mandatory
--  Descr
--    10Base-T, 12 RJ45s non-ASIC based

mtTPMIMT3 OBJECT IDENTIFIER ::= { moduleType 67 }
-- OBJECT-IDENTITY
--  Status
--    mandatory
--  Descr
--    10Base-T, 1 50 Pos., non-ASIC based

mtThinMim2 OBJECT IDENTIFIER ::= { moduleType 80 }
-- OBJECT-IDENTITY
--  Status
--    mandatory

mtTPMIM24 OBJECT IDENTIFIER ::= { moduleType 96 }
-- OBJECT-IDENTITY
--  Status
--    mandatory
--  Descr
--    10Base-T, 24 RJ45s, ASIC based

mtTPMIM22 OBJECT IDENTIFIER ::= { moduleType 97 }
-- OBJECT-IDENTITY
--  Status
--    mandatory
--  Descr
--    10Base-T, 12 RJ45s, ASIC based

mtTPMIM34 OBJECT IDENTIFIER ::= { moduleType 98 }
-- OBJECT-IDENTITY
--  Status
--    mandatory
--  Descr
--    10Base-T, 2 50 Pos, ASIC based

mtTPMIM32 OBJECT IDENTIFIER ::= { moduleType 99 }
-- OBJECT-IDENTITY
--  Status
--    mandatory
--  Descr
--    10Base-T, 1 50 Pos, ASIC based

mtTPRMIM100I OBJECT IDENTIFIER ::= { moduleType 111 }
-- OBJECT-IDENTITY
--  Status
--    mandatory
--  Descr
--    MMAC Module - 22 port (RJ45 with one EPIM slot)
--    100Base-TX repeater module with management

mtTPRMIM33 OBJECT IDENTIFIER ::= { moduleType 112 }
-- OBJECT-IDENTITY
--  Status
--    mandatory
--  Descr
--    13 Port 10Base-T, 1 50 Post with Ethernet Port Interface Module

mtTPRMIM36 OBJECT IDENTIFIER ::= { moduleType 113 }
-- OBJECT-IDENTITY
--  Status
--    mandatory
--  Descr
--    26 Port 10Base-T, 2 50 Pos, AUI/Ethernet Port Interface Module

mtCXRMIM OBJECT IDENTIFIER ::= { moduleType 114 }
-- OBJECT-IDENTITY
--  Status
--    mandatory
--  Descr
--    13 Port 10Base-2, with Ethernet Port Interface Module

mtFORMIM22 OBJECT IDENTIFIER ::= { moduleType 115 }
-- OBJECT-IDENTITY
--  Status
--    mandatory
--  Descr
--    12 Port 10Base-FF/FOIRL, ST

mtTPRMIM20 OBJECT IDENTIFIER ::= { moduleType 116 }
-- OBJECT-IDENTITY
--  Status
--    mandatory
--  Descr
--    9 Port 10Base-T RJ45s, with Ethernet Port Interface Module

mtTPRMIM22 OBJECT IDENTIFIER ::= { moduleType 117 }
-- OBJECT-IDENTITY
--  Status
--    mandatory
--  Descr
--    21 Port 10Base-T RJ45s, with Ethernet Port Interface Module

mtTPRMIM20S OBJECT IDENTIFIER ::= { moduleType 118 }
-- OBJECT-IDENTITY
--  Status
--    mandatory
--  Descr
--    9 Port 10Base-T RJ45s with one EPIM all ports support
--    LANVIEW/SECURE

mtTPRMIM22S OBJECT IDENTIFIER ::= { moduleType 119 }
-- OBJECT-IDENTITY
--  Status
--    mandatory
--  Descr
--    21 Port 10Base-T RJ45s with one EPIM all ports support
--    LANVIEW/SECURE.

mtTPRMIM33S OBJECT IDENTIFIER ::= { moduleType 120 }
-- OBJECT-IDENTITY
--  Status
--    mandatory
--  Descr
--    13 Port 10Base-T 1 50 Post with EPIM all ports support
--    LANVIEW/SECURE.

mtTPRMIM36S OBJECT IDENTIFIER ::= { moduleType 121 }
-- OBJECT-IDENTITY
--  Status
--    mandatory
--  Descr
--    26 Port 10Base-T 2 50 Post with EPIM all ports support
--    LANVIEW/SECURE.

mtCXRMIMs OBJECT IDENTIFIER ::= { moduleType 122 }
-- OBJECT-IDENTITY
--  Status
--    mandatory
--  Descr
--    13 Port 10Base-2 with EPIM all ports support
--    LANVIEW/SECURE.

mtFormim22S OBJECT IDENTIFIER ::= { moduleType 123 }
-- OBJECT-IDENTITY
--  Status
--    mandatory
--  Descr
--    12 Port 10Base-FF/FIORL, ST all ports support
--    LANVIEW/SECURE.

mtFBRMIM26 OBJECT IDENTIFIER ::= { moduleType 126 }
-- OBJECT-IDENTITY
--  Status
--    mandatory
--  Descr
--    6 Port 10Base-FB RIC Media Interface Module

mtFBRMIM22 OBJECT IDENTIFIER ::= { moduleType 127 }
-- OBJECT-IDENTITY
--  Status
--    mandatory
--  Descr
--    12 Port 10Base-FB RIC Media Interface Module

mtFOMIM18 OBJECT IDENTIFIER ::= { moduleType 144 }
-- OBJECT-IDENTITY
--  Status
--    mandatory
--  Descr
--    FOIRL, 18 Ports, SMA ASIC based

mtFOMIM12 OBJECT IDENTIFIER ::= { moduleType 146 }
-- OBJECT-IDENTITY
--  Status
--    mandatory
--  Descr
--    FOIRL, 12 Ports, SMA ASIC based

mtFOMIM16 OBJECT IDENTIFIER ::= { moduleType 147 }
-- OBJECT-IDENTITY
--  Status
--    mandatory
--  Descr
--    FOIRL, 6 Ports, SMA ASIC based

mtFOMIM28 OBJECT IDENTIFIER ::= { moduleType 148 }
-- OBJECT-IDENTITY
--  Status
--    mandatory
--  Descr
--    FOIRL, 18 Ports, ST ASIC based

mtFOMIM22 OBJECT IDENTIFIER ::= { moduleType 150 }
-- OBJECT-IDENTITY
--  Status
--    mandatory
--  Descr
--    FOIRL, 12 Ports, ST ASIC based

mtFOMIM26 OBJECT IDENTIFIER ::= { moduleType 151 }
-- OBJECT-IDENTITY
--  Status
--    mandatory
--  Descr
--    FOIRL, 6 Ports, ST ASIC based

mtFOMIM38 OBJECT IDENTIFIER ::= { moduleType 152 }
-- OBJECT-IDENTITY
--  Status
--    mandatory
--  Descr
--    Single Mode Fiber, 18 Ports, ST

mtFOMIM32 OBJECT IDENTIFIER ::= { moduleType 154 }
-- OBJECT-IDENTITY
--  Status
--    mandatory
--  Descr
--    Single Mode Fiber, 12 Ports, ST

mtFOMIM36 OBJECT IDENTIFIER ::= { moduleType 155 }
-- OBJECT-IDENTITY
--  Status
--    mandatory
--  Descr
--    Single Mode Fiber, 6 Ports, ST

mtMT8MIM OBJECT IDENTIFIER ::= { moduleType 160 }
-- OBJECT-IDENTITY
--  Status
--    mandatory

mtIRM2 OBJECT IDENTIFIER ::= { moduleType 176 }
-- OBJECT-IDENTITY
--  Status
--    mandatory
--  Descr
--    ASIC Based IRM for Ethernet

mtIRBM OBJECT IDENTIFIER ::= { moduleType 177 }
-- OBJECT-IDENTITY
--  Status
--    mandatory
--  Descr
--    2 Port Bridging/Management Module

mtIRM3 OBJECT IDENTIFIER ::= { moduleType 178 }
-- OBJECT-IDENTITY
--  Status
--    mandatory
--  Descr
--    Advanced IRM-2

mtTRMM1 OBJECT IDENTIFIER ::= { moduleType 179 }
-- OBJECT-IDENTITY
--  Status
--    mandatory
--  Descr
--    New TRMM

mtTRMM2 OBJECT IDENTIFIER ::= { moduleType 180 }
-- OBJECT-IDENTITY
--  Status
--    mandatory
--  Descr
--    Token Ring to Token Ring Module-One frontpanel one
--    backplane

mtTRMMIM1 OBJECT IDENTIFIER ::= { moduleType 181 }
-- OBJECT-IDENTITY
--  Status
--    mandatory
--  Descr
--    Mid Chassis TRMM

mtEFDMIM OBJECT IDENTIFIER ::= { moduleType 182 }
-- OBJECT-IDENTITY
--  Status
--    mandatory
--  Descr
--    Ethernet to FDDI Bridge

mtTRMM4 OBJECT IDENTIFIER ::= { moduleType 183 }
-- OBJECT-IDENTITY
--  Status
--    mandatory
--  Descr
--    4 port Token Ring Management Module.

mtTRBMIM OBJECT IDENTIFIER ::= { moduleType 184 }
-- OBJECT-IDENTITY
--  Status
--    mandatory
--  Descr
--    Token Ring to Token Ring Bridge module.

mtEMME OBJECT IDENTIFIER ::= { moduleType 185 }
-- OBJECT-IDENTITY
--  Status
--    mandatory
--  Descr
--    Ethernet 4 Port Bridging/Management

mtESXMIM OBJECT IDENTIFIER ::= { moduleType 186 }
-- OBJECT-IDENTITY
--  Status
--    mandatory
--  Descr
--    Ethernet Switching Module, IMIM

mtTRMM OBJECT IDENTIFIER ::= { moduleType 187 }
-- OBJECT-IDENTITY
--  Status
--    mandatory
--  Descr
--    Token Ring Management Module, slot 1

mtTRMMIM2 OBJECT IDENTIFIER ::= { moduleType 188 }
-- OBJECT-IDENTITY
--  Status
--    mandatory
--  Descr
--    Token Ring to Token Ring Bridge/Management Media Interface Modules

mtETWMIM OBJECT IDENTIFIER ::= { moduleType 189 }
-- OBJECT-IDENTITY
--  Status
--    mandatory
--  Descr
--    Ethernet/Token Ring/WAN Bridge

mtTRMMIM OBJECT IDENTIFIER ::= { moduleType 190 }
-- OBJECT-IDENTITY
--  Status
--    mandatory
--  Descr
--    Mid Chassis TRMM

mtESXMIMF2 OBJECT IDENTIFIER ::= { moduleType 191 }
-- OBJECT-IDENTITY
--  Status
--    mandatory
--  Descr
--    Ethernet switching module with multimode fiber ST
--    connectors.

mtFOT12or22 OBJECT IDENTIFIER ::= { moduleType 192 }
-- OBJECT-IDENTITY
--  Status
--    mandatory

-- RESERVED for ESXMIM22 OBJECT IDENTIFIER ::= { moduleType 200 }
-- reserved for Jerry Baur
-- OBJECT-IDENTITY
--  Status
--    mandatory

-- RESERVED for 100TPRMIM OBJECT IDENTIFIER ::= { moduleType 201 }
-- reserved for Jerry Baur
-- OBJECT-IDENTITY
--  Status
--    mandatory

mtTPTMIM OBJECT IDENTIFIER ::= { moduleType 208 }
-- OBJECT-IDENTITY
--  Status
--    mandatory

mtFOT16or26 OBJECT IDENTIFIER ::= { moduleType 224 }
-- OBJECT-IDENTITY
--  Status
--    mandatory

mtSNACRS232wRS232 OBJECT IDENTIFIER ::= { moduleType 240 }
-- OBJECT-IDENTITY
--  Status
--    mandatory
--  Descr
--    RS232 with RS232 DB

mtSNACRS232wV35 OBJECT IDENTIFIER ::= { moduleType 241 }
-- OBJECT-IDENTITY
--  Status
--    mandatory
--  Descr
--    RS232 with V.35 DB

mtSNACRS232wRS530 OBJECT IDENTIFIER ::= { moduleType 242 }
-- OBJECT-IDENTITY
--  Status
--    mandatory
--  Descr
--    RS232 with RS530 DB

mtSNACRS232wNoDB OBJECT IDENTIFIER ::= { moduleType 243 }
-- OBJECT-IDENTITY
--  Status
--    mandatory
--  Descr
--    RS232 without DB

mtSNACV35wRS232 OBJECT IDENTIFIER ::= { moduleType 244 }
-- OBJECT-IDENTITY
--  Status
--    mandatory
--  Descr
--    V.35 with RS232 DB

mtSNACV35wV35 OBJECT IDENTIFIER ::= { moduleType 245 }
-- OBJECT-IDENTITY
--  Status
--    mandatory
--  Descr
--    V.35 with V.35 DB

mtSNACV35wRS350 OBJECT IDENTIFIER ::= { moduleType 246 }
-- OBJECT-IDENTITY
--  Status
--    mandatory
--  Descr
--    V.35 with RS530 DB

mtSNACV35wNoDB OBJECT IDENTIFIER ::= { moduleType 247 }
-- OBJECT-IDENTITY
--  Status
--    mandatory
--  Descr
--    V.35 without DB

mtSNACRS530wRS232 OBJECT IDENTIFIER ::= { moduleType 248 }
-- OBJECT-IDENTITY
--  Status
--    mandatory
--  Descr
--    RS530 with RS232 DB

mtSNACRS530wV35 OBJECT IDENTIFIER ::= { moduleType 249 }
-- OBJECT-IDENTITY
--  Status
--    mandatory
--  Descr
--    RS530 with V.35 DB

mtSNACRS530wRS530 OBJECT IDENTIFIER ::= { moduleType 250 }
-- OBJECT-IDENTITY
--  Status
--    mandatory
--  Descr
--    RS530 with RS530 DB

mtSNACRS530wNoDB OBJECT IDENTIFIER ::= { moduleType 251 }
-- OBJECT-IDENTITY
--  Status
--    mandatory
--  Descr
--    RS530 without DB

mtSNACMIMConnectivity OBJECT IDENTIFIER ::= { moduleType 252 }
-- OBJECT-IDENTITY
--  Status
--    mandatory
--  Descr
--    SNA Connectivity Media Interface Module

mtSNACConnectivityMIM OBJECT IDENTIFIER ::= { moduleType 253 }
-- OBJECT-IDENTITY
--  Status
--    mandatory
--  Descr
--    SNA Connectivity Media Interface Module

mtSNACConnectivity OBJECT IDENTIFIER ::= { moduleType 254 }
-- OBJECT-IDENTITY
--  Status
--    mandatory
--  Descr
--    SNA Connectivity Media Interface Module

mtNull OBJECT IDENTIFIER ::= { moduleType 255 }
-- OBJECT-IDENTITY
--  Status
--    mandatory
--  Descr
--    No Media Interface Module Installed

mtTRMIMa10R OBJECT IDENTIFIER ::= { moduleType 305 }
-- OBJECT-IDENTITY
--  Status
--    mandatory
--  Descr
--    10 Port STP DB9s, Ring-In/Ring-Out with autowrap feature

mtTRMIMa20R OBJECT IDENTIFIER ::= { moduleType 307 }
-- OBJECT-IDENTITY
--  Status
--    mandatory
--  Descr
--    10 Port UTP with RJ45s with Ring-In/Ring-Out DB9 with autowrap feature

mtTRMIM22ARO OBJECT IDENTIFIER ::= { moduleType 311 }
-- OBJECT-IDENTITY
--  Status
--    mandatory
--  Descr
--    active MIM with 12 UTP ports with Ring-Out capabilities (93 series)

mtTRRMIM2A OBJECT IDENTIFIER ::= { moduleType 314 }
-- OBJECT-IDENTITY
--  Status
--    mandatory
--  Descr
--    Token-Ring Repeater with 12 UTP RJ45s, DB9/Fiber Optic
--    Ring-In/Ring-Out

mtTRMIM24ARO OBJECT IDENTIFIER ::= { moduleType 566 }
-- OBJECT-IDENTITY
--  Status
--    mandatory
--  Descr
--    active MIM with 24 UTP ports with Ring-Out capabilities (93 series)

mtTRRMIM4A OBJECT IDENTIFIER ::= { moduleType 570 }
-- OBJECT-IDENTITY
--  Status
--    mandatory
--  Descr
--    Token-Ring Repeater with 12 STP RJ45s, DB9/Fiber Optic
--    Ring-In/Ring-Out

mtTRRMIMAT OBJECT IDENTIFIER ::= { moduleType 826 }
-- OBJECT-IDENTITY
--  Status
--    mandatory
--  Descr
--    repeater with no stations and TPIM Ring-In/Ring-Out

mtTRMIM42ARO OBJECT IDENTIFIER ::= { moduleType 831 }
-- OBJECT-IDENTITY
--  Status
--    mandatory
--  Descr
--    active MIM with 12 STP ports with Ring-Out capabilities (93 series)

mtTRRMIM2AT OBJECT IDENTIFIER ::= { moduleType 1082 }
-- OBJECT-IDENTITY
--  Status
--    mandatory
--  Descr
--    repeater with 12 active UTP stations and TPIM Ring-In/Ring-Out

mtTRMIM44ARO OBJECT IDENTIFIER ::= { moduleType 1086 }
-- OBJECT-IDENTITY
--  Status
--    mandatory
--  Descr
--    active MIM with 24 STP ports with Ring-Out capabilities (93 series)

mtTRRMIM4AT OBJECT IDENTIFIER ::= { moduleType 1338 }
-- OBJECT-IDENTITY
--  Status
--    mandatory
--  Descr
--    repeater with 12 active STP stations with TPIM Ring-In/Ring-Out

mtMPIMX OBJECT IDENTIFIER ::= { moduleType 65536 }
-- OBJECT-IDENTITY
--  Status
--    mandatory
--  Descr
--    MiniMMAC XCVR 8 Male AUIs

mtMPIMA OBJECT IDENTIFIER ::= { moduleType 65537 }
-- OBJECT-IDENTITY
--  Status
--    mandatory
--  Descr
--    MiniMMAC XCVR 8 Female AUIs

mtMPIMC OBJECT IDENTIFIER ::= { moduleType 65538 }
-- OBJECT-IDENTITY
--  Status
--    mandatory
--  Descr
--    MiniMMAC Coax 6 Ports

mtMPIMT OBJECT IDENTIFIER ::= { moduleType 65539 }
-- OBJECT-IDENTITY
--  Status
--    mandatory
--  Descr
--    MiniMMAC TP 6 UTP Ports

mtMPIMF2 OBJECT IDENTIFIER ::= { moduleType 65540 }
-- OBJECT-IDENTITY
--  Status
--    mandatory
--  Descr
--    MiniMMAC FO 6 ST Ports

mtMPIMF1 OBJECT IDENTIFIER ::= { moduleType 65541 }
-- OBJECT-IDENTITY
--  Status
--    mandatory
--  Descr
--    MiniMMAC FO 6 SMA Ports

mtMPIMT1 OBJECT IDENTIFIER ::= { moduleType 65542 }
-- OBJECT-IDENTITY
--  Status
--    mandatory
--  Descr
--    MiniMMAC STP 6 DB-9 Ports

mtMPIMB OBJECT IDENTIFIER ::= { moduleType 65543 }
-- OBJECT-IDENTITY
--  Status
--    mandatory
--  Descr
--    MiniMMAC Blank Plate (empty slot)

mtMiniMMAC OBJECT IDENTIFIER ::= { moduleType 65552 }
-- OBJECT-IDENTITY
--  Status
--    mandatory
--  Descr
--    80186 based with IRM-2 Management

mtMRXIE OBJECT IDENTIFIER ::= { moduleType 65568 }
-- OBJECT-IDENTITY
--  Status
--    mandatory
--  Descr
--    80186 Based with 50 Pin and 2 Single Port Interface Modules

mtMRXI24 OBJECT IDENTIFIER ::= { moduleType 65569 }
-- OBJECT-IDENTITY
--  Status
--    mandatory
--  Descr
--    i960 Based MRXI 24 RJ45 with 2 Ethernet Port Interface Modules

mtMRXI22 OBJECT IDENTIFIER ::= { moduleType 65570 }
-- OBJECT-IDENTITY
--  Status
--    mandatory
--  Descr
--    i960 Based MRXI 12 RJ45 with 1 Ethernet Port Interface Module

mtMRXI34 OBJECT IDENTIFIER ::= { moduleType 65571 }
-- OBJECT-IDENTITY
--  Status
--    mandatory
--  Descr
--    i960 Based MRXI 2x50 Pin with 2 Ethernet Port Interface Modules

mtMRXI32 OBJECT IDENTIFIER ::= { moduleType 65572 }
-- OBJECT-IDENTITY
--  Status
--    mandatory
--  Descr
--    i960 Based MRXI 1x50 Pin with 1 Ethernet Port Interface Module

mtMRXI2E OBJECT IDENTIFIER ::= { moduleType 65584 }
-- OBJECT-IDENTITY
--  Status
--    mandatory
--  Descr
--    80186 Based with 50 Pin and 2 Single Port Interface Modules

mtSPIMX OBJECT IDENTIFIER ::= { moduleType 131072 }
-- OBJECT-IDENTITY
--  Status
--    mandatory
--  Descr
--    One port XCVR port Male

mtSPIMA OBJECT IDENTIFIER ::= { moduleType 131073 }
-- OBJECT-IDENTITY
--  Status
--    mandatory
--  Descr
--    One port AUI port Female

mtSPIMC OBJECT IDENTIFIER ::= { moduleType 131074 }
-- OBJECT-IDENTITY
--  Status
--    mandatory
--  Descr
--    One port Coax BNC

mtSPIMT OBJECT IDENTIFIER ::= { moduleType 131075 }
-- OBJECT-IDENTITY
--  Status
--    mandatory
--  Descr
--    One port 10Base-T RJ45

mtSPIMF2 OBJECT IDENTIFIER ::= { moduleType 131076 }
-- OBJECT-IDENTITY
--  Status
--    mandatory
--  Descr
--    One port MultiMode Fiber with ST

mtSPIMF1 OBJECT IDENTIFIER ::= { moduleType 131077 }
-- OBJECT-IDENTITY
--  Status
--    mandatory
--  Descr
--    One Port MultiMode Fiber with SMA

mtSPIMT1 OBJECT IDENTIFIER ::= { moduleType 131078 }
-- OBJECT-IDENTITY
--  Status
--    mandatory
--  Descr
--    One Port 10Base-T with DB9

mtSPIMB OBJECT IDENTIFIER ::= { moduleType 131079 }
-- OBJECT-IDENTITY
--  Status
--    mandatory

mtEPIMB OBJECT IDENTIFIER ::= { moduleType 196608 }
-- OBJECT-IDENTITY
--  Status
--    mandatory
--  Descr
--    Blank Plate (empty slot)

mtEPIMA OBJECT IDENTIFIER ::= { moduleType 196609 }
-- OBJECT-IDENTITY
--  Status
--    mandatory
--  Descr
--    One Port AUI Female

mtEPIMC OBJECT IDENTIFIER ::= { moduleType 196610 }
-- OBJECT-IDENTITY
--  Status
--    mandatory
--  Descr
--    One Port XCVR Male

mtEPIMT OBJECT IDENTIFIER ::= { moduleType 196611 }
-- OBJECT-IDENTITY
--  Status
--    mandatory
--  Descr
--    One Port 10Base-T RJ45

mtEPIMF2 OBJECT IDENTIFIER ::= { moduleType 196612 }
-- OBJECT-IDENTITY
--  Status
--    mandatory
--  Descr
--    One Port MultiMode FO with ST

mtEPIMF1 OBJECT IDENTIFIER ::= { moduleType 196613 }
-- OBJECT-IDENTITY
--  Status
--    mandatory
--  Descr
--    One Port MultiMode FO with SMA

mtEPIMT1 OBJECT IDENTIFIER ::= { moduleType 196614 }
-- OBJECT-IDENTITY
--  Status
--    mandatory
--  Descr
--    One Port 10Base-T DB9

mtEPIMF3 OBJECT IDENTIFIER ::= { moduleType 196615 }
-- OBJECT-IDENTITY
--  Status
--    mandatory
--  Descr
--    One Port Single Mode FO with ST

mtEPIMX OBJECT IDENTIFIER ::= { moduleType 196616 }
-- OBJECT-IDENTITY
--  Status
--    mandatory
--  Descr
--    One Port XCVR Male

mtEPIMTfd OBJECT IDENTIFIER ::= { moduleType 196619 }
-- OBJECT-IDENTITY
--  Status
--    mandatory
--  Descr
--    One Port 10Base-T RJ45 with full duplex support

mtEPIMF2fd OBJECT IDENTIFIER ::= { moduleType 196620 }
-- OBJECT-IDENTITY
--  Status
--    mandatory
--  Descr
--    One Port MultiMode FO with ST with full duplex support

mtEPIMF1fd OBJECT IDENTIFIER ::= { moduleType 196621 }
-- OBJECT-IDENTITY
--  Status
--    mandatory
--  Descr
--    One Port MultiMode FO with SMA with full duplex support

mtEPIMF3fd OBJECT IDENTIFIER ::= { moduleType 196622 }
-- OBJECT-IDENTITY
--  Status
--    mandatory
--  Descr
--    One Port Single Mode FO with ST with full duplex support

mtEPIMFIXED OBJECT IDENTIFIER ::= { moduleType 196623 }
-- OBJECT-IDENTITY
--  Status
--    mandatory
--  Descr
--    ??????

mtMRXI OBJECT IDENTIFIER ::= { moduleType 196674 }
-- OBJECT-IDENTITY
--  Status
--    mandatory
--  Descr
--    80186 Based with 50 Pin and 2 Single Port Interface Modules

mtMRXI2 OBJECT IDENTIFIER ::= { moduleType 196675 }
-- OBJECT-IDENTITY
--  Status
--    mandatory
--  Descr
--    80186 Based with 12 RJ45 and 2 Single Port Interface Modules

slotClass OBJECT IDENTIFIER ::= { namingTree 3 }
-- OBJECT-IDENTITY
--  Status
--    mandatory

csUnknown OBJECT IDENTIFIER ::= { slotClass 1 }
-- OBJECT-IDENTITY
--  Status
--    mandatory

csPwrSup OBJECT IDENTIFIER ::= { slotClass 2 }
-- OBJECT-IDENTITY
--  Status
--    mandatory

csMgmt OBJECT IDENTIFIER ::= { slotClass 3 }
-- OBJECT-IDENTITY
--  Status
--    mandatory

csMgmtRelay OBJECT IDENTIFIER ::= { slotClass 4 }
-- OBJECT-IDENTITY
--  Status
--    mandatory

csMIM OBJECT IDENTIFIER ::= { slotClass 5 }
-- OBJECT-IDENTITY
--  Status
--    mandatory

backplaneType OBJECT IDENTIFIER ::= { namingTree 4 }
-- OBJECT-IDENTITY
--  Status
--    mandatory

btUnknown OBJECT IDENTIFIER ::= { backplaneType 1 }
-- OBJECT-IDENTITY
--  Status
--    mandatory

btBusA OBJECT IDENTIFIER ::= { backplaneType 2 }
-- OBJECT-IDENTITY
--  Status
--    mandatory

btBusB OBJECT IDENTIFIER ::= { backplaneType 3 }
-- OBJECT-IDENTITY
--  Status
--    mandatory

btBusC OBJECT IDENTIFIER ::= { backplaneType 4 }
-- OBJECT-IDENTITY
--  Status
--    mandatory

componentType OBJECT IDENTIFIER ::= { namingTree 5 }
-- OBJECT-IDENTITY
--  Status
--    mandatory
--  Descr
--    This branch defines the different component types defined
--    within Cabletron.
--
--    A component is defined as major device functionality such as
--    repeating, routing, bridging, switching, or other applications
--    running on the device.  In general the definition of component
--    does not include basic device requirements (required for device
--    operation) such as SNMP, IP protocol stack, telnet, download,
--    and media connectivity.  The existance of operational
--    functions are clearly defined by various MIB variables.  For
--    example media connectivity is defined by ifType in MIB-II.

cptUnknown OBJECT IDENTIFIER ::= { componentType 1 }
-- OBJECT-IDENTITY
--  Status
--    mandatory
--  Descr
--    Defines an unknown type of component.
--
--    This may be used if a new function is defined but a component
--    type has yet to be assigned.  Usage of this should be very
--    limited.

cptRepeater OBJECT IDENTIFIER ::= { componentType 2 }
-- OBJECT-IDENTITY
--  Status
--    mandatory
--  Descr
--    A repeater for ethernet also a concentrator for FDDI.
--    This implies the existance of management for the device.

cptMau OBJECT IDENTIFIER ::= { componentType 3 }
-- OBJECT-IDENTITY
--  Status
--    mandatory
--  Descr
--    An instance of a ring in a Token Ring environment.  This
--    includes the ability to manage and get statistics for the
--    ring.

cptBridge OBJECT IDENTIFIER ::= { componentType 4 }
-- OBJECT-IDENTITY
--  Status
--    mandatory
--  Descr
--    Bridging which includes implementation of bridge MIBs.

cptRouter OBJECT IDENTIFIER ::= { componentType 5 }
-- OBJECT-IDENTITY
--  Status
--    mandatory
--  Descr
--    Routing which includes implementation of routing specific
--    MIBs.

cptRmon OBJECT IDENTIFIER ::= { componentType 6 }
-- OBJECT-IDENTITY
--  Status
--    mandatory
--  Descr
--    Any implementation of RMON.  This is independent of media
--    type.

cptAgent OBJECT IDENTIFIER ::= { componentType 7 }
-- OBJECT-IDENTITY
--  Status
--    mandatory
--  Descr
--    The chassis manager component.  This is a central entity
--    that implements the chassis MIB and therefore provides
--    knowledge of the entire chassis.

cptLim OBJECT IDENTIFIER ::= { componentType 8 }
-- OBJECT-IDENTITY
--  Status
--    mandatory
--  Descr
--    Local management

cptHostSvcs OBJECT IDENTIFIER ::= { componentType 9 }
-- OBJECT-IDENTITY
--  Status
--    mandatory
--  Descr
--    This includes such functionality as the protocol
--    stack, SNMP, telnet.

cptIngMIM OBJECT IDENTIFIER ::= { componentType 10 }
-- OBJECT-IDENTITY
--  Status
--    mandatory
--  Descr
--    An intelligent MIM within a MMAC chassis.  Intelligent MIMs
--    are managable via SNMP and may also support an implementation
--    of a chassis MIB for it's management domain.

cptDLM OBJECT IDENTIFIER ::= { componentType 11 }
-- OBJECT-IDENTITY
--  Status
--    mandatory
--  Descr
--    The Distributed Lan Monitor

cptMIBNavigator OBJECT IDENTIFIER ::= { componentType 12 }
-- OBJECT-IDENTITY
--  Status
--    mandatory
--  Descr
--    The MIB Navigator that is accessible via telnet to the
--    device.

cptRmonHost OBJECT IDENTIFIER ::= { componentType 13 }
-- OBJECT-IDENTITY
--  Status
--    mandatory
--  Descr
--    Implementation of the RMON host, topn, matrix groups.

cptRmonCapture OBJECT IDENTIFIER ::= { componentType 14 }
-- OBJECT-IDENTITY
--  Status
--    mandatory
--  Descr
--    Implementation of the RMON packet capture and filter
--    groups.

cptMibMgr OBJECT IDENTIFIER ::= { componentType 15 }
-- OBJECT-IDENTITY
--  Status
--    obsolete
--  Descr
--    Initially defined to allow for separate MIB views for the
--    chassis MIB and MIB-II.  No longer in use.

cptFddiSmt OBJECT IDENTIFIER ::= { componentType 16 }
-- OBJECT-IDENTITY
--  Status
--    mandatory
--  Descr
--    Implementation of SMT within a FDDI network.

cptSFPS OBJECT IDENTIFIER ::= { componentType 17 }
-- OBJECT-IDENTITY
--  Status
--    mandatory
--  Descr
--    The secure fast packet switch.

cptModuleMgmt OBJECT IDENTIFIER ::= { componentType 18 }
-- OBJECT-IDENTITY
--  Status
--    mandatory
--  Descr
--    An intelligent module that maintains it's own management
--    environment.

cptOrphan OBJECT IDENTIFIER ::= { componentType 19 }
-- OBJECT-IDENTITY
--  Status
--    mandatory
--  Descr
--    A Mau type of component for which control information
--    exists but no statistical information.

cptATM OBJECT IDENTIFIER ::= { componentType 20 }
-- OBJECT-IDENTITY
--  Status
--    mandatory
--  Descr
--    The device has at least 1 ATM interface.

cptWebview OBJECT IDENTIFIER ::= { componentType 21 }
-- OBJECT-IDENTITY
--  Status
--    mandatory
--  Descr
--    The embedded WEB server application used for web
--    based device management.

cpt802p1Q OBJECT IDENTIFIER ::= { componentType 22 }
-- OBJECT-IDENTITY
--  Status
--    mandatory
--  Descr
--    Component type for IEEE 802.1Q refers to VLANs (industry standard
--    via IEEE).

cpt802p1p OBJECT IDENTIFIER ::= { componentType 23 }
-- OBJECT-IDENTITY
--  Status
--    mandatory
--  Descr
--    Component type for IEEE 802.1p refers to priority queuing/dynamic
--    Multicast filtering.

cptTrafficGen OBJECT IDENTIFIER ::= { componentType 24 }
-- OBJECT-IDENTITY
--  Status
--    mandatory
--  Descr
--    Component type for Traffic Generation capabilities.

thrPtyModType OBJECT IDENTIFIER ::= { namingTree 6 }
-- OBJECT-IDENTITY
--  Status
--    mandatory
--  Descr
--    Third Party Modules

tpMtETSMIM OBJECT IDENTIFIER ::= { thrPtyModType 2 }
-- OBJECT-IDENTITY
--  Status
--    mandatory
--  Descr
--    Xyplex 16 port terminal server

tpMtDNSMIM OBJECT IDENTIFIER ::= { thrPtyModType 3 }
-- OBJECT-IDENTITY
--  Status
--    mandatory
--  Descr
--    SGI Media Interface Module

tpMtGatorMIM OBJECT IDENTIFIER ::= { thrPtyModType 4 }
-- OBJECT-IDENTITY
--  Status
--    mandatory
--  Descr
--    Cayman Localtalk to Ethernet Gateway

tpMtLanternMIM OBJECT IDENTIFIER ::= { thrPtyModType 5 }
-- OBJECT-IDENTITY
--  Status
--    mandatory
--  Descr
--    Novell Protocol Analyzer

tpMtCRML OBJECT IDENTIFIER ::= { thrPtyModType 6 }
-- OBJECT-IDENTITY
--  Status
--    mandatory
--  Descr
--    cisco Ethernet to Ethernet router

tpMtCRM OBJECT IDENTIFIER ::= { thrPtyModType 7 }
-- OBJECT-IDENTITY
--  Status
--    mandatory
--  Descr
--    cisco Ethernet to WAN router

networkType OBJECT IDENTIFIER ::= { namingTree 7 }
-- OBJECT-IDENTITY
--  Status
--    mandatory

ntManagementTypes OBJECT IDENTIFIER ::= { networkType 10 }
-- OBJECT-IDENTITY
--  Status
--    mandatory
--  Descr
--    This branch defines the types of management that
--    may exist.

ntInbandMgmt OBJECT IDENTIFIER ::= { ntManagementTypes 1 }
-- OBJECT-IDENTITY
--  Status
--    mandatory
--  Descr
--    Management over inband network.

ntSideBandMgmt OBJECT IDENTIFIER ::= { ntManagementTypes 2 }
-- OBJECT-IDENTITY
--  Status
--    mandatory
--  Descr
--    Management over 'side band' non-inband network.  A
--    standalone ethernet for example.

ntOutOfBandMgmt OBJECT IDENTIFIER ::= { ntManagementTypes 3 }
-- OBJECT-IDENTITY
--  Status
--    mandatory
--  Descr
--    Management over out of band network for example a serial
--    bus.

physicalType OBJECT IDENTIFIER ::= { namingTree 8 }
-- OBJECT-IDENTITY
--  Status
--    mandatory

portType OBJECT IDENTIFIER ::= { physicalType 1 }
-- OBJECT-IDENTITY
--  Status
--    mandatory

hardwareType OBJECT IDENTIFIER ::= { physicalType 2 }
-- OBJECT-IDENTITY
--  Status
--    mandatory

portStandard OBJECT IDENTIFIER ::= { portType 1 }
-- OBJECT-IDENTITY
--  Status
--    mandatory

portXpim OBJECT IDENTIFIER ::= { portType 2 }
-- OBJECT-IDENTITY
--  Status
--    mandatory

portXnim OBJECT IDENTIFIER ::= { portType 3 }
-- OBJECT-IDENTITY
--  Status
--    mandatory

portVirtualType OBJECT IDENTIFIER ::= { portType 4 }
-- OBJECT-IDENTITY
--  Status
--    mandatory

portVirtualTypeSvc OBJECT IDENTIFIER ::= { portVirtualType 1 }
-- OBJECT-IDENTITY
--  Status
--    mandatory
-- Descr
--    Switched Virtual Circuit.

portVirtualTypePvcLlc OBJECT IDENTIFIER ::= { portVirtualType 2 }
-- OBJECT-IDENTITY
--  Status
--    mandatory
-- Descr
--    LLC Encapsulation Permanent Virtual Circuit

portVirtualTypePvcVcmux OBJECT IDENTIFIER ::= { portVirtualType 3 }
-- OBJECT-IDENTITY
--  Status
--    mandatory
--  Descr
--    VC Multiplexed Permanent Virtual Circuit

portVirtualSMB OBJECT IDENTIFIER ::= { portType 5 }
-- OBJECT-IDENTITY
--  Status
--    mandatory
--  Descr
--    Virtual interface used by SmartSwitch 6000 for Distributed
--    Chassis Management

portCATV OBJECT IDENTIFIER ::= { portType 6 }
-- OBJECT-IDENTITY
--  Status
--    mandatory
--  Descr
--    A branch describing the possible port types used to interface a
--    device to a Cable TV infrastructure (CATV).

portCATVUnknown OBJECT IDENTIFIER ::= { portCATV 1 }
-- OBJECT-IDENTITY
--  Status
--    mandatory
--  Descr
--    The physical port type is unrecognized.

port75ohmFemaleFType OBJECT IDENTIFIER ::= { portCATV 2 }
-- OBJECT-IDENTITY
--  Status
--    mandatory
--  Descr
--    The CATV interface utilizes a female, 75 Ohm, F-Type connector.

portEthernet OBJECT IDENTIFIER ::= { portStandard 1 }
-- OBJECT-IDENTITY
--  Status
--    mandatory

portTokenRing OBJECT IDENTIFIER ::= { portStandard 2 }
-- OBJECT-IDENTITY
--  Status
--    mandatory

portFDDI OBJECT IDENTIFIER ::= { portStandard 3 }
-- OBJECT-IDENTITY
--  Status
--    mandatory

portNotPresent OBJECT IDENTIFIER ::= { portStandard 4 }
-- OBJECT-IDENTITY
--  Status
--    mandatory

portATM OBJECT IDENTIFIER ::= { portStandard 5 }
-- OBJECT-IDENTITY
--  Status
--    mandatory
--  Descr
--    Standard ATM port identifiers.

portBackplane OBJECT IDENTIFIER ::= { portStandard 6 }
-- OBJECT-IDENTITY
--  Status
--    mandatory
--  Descr
--    A backplane port connection.

portInternal OBJECT IDENTIFIER ::= { portStandard 7 }
-- OBJECT-IDENTITY
--  Status
--    mandatory
--  Descr
--    An internal port connection.

portFastEthernet OBJECT IDENTIFIER ::= { portStandard 8 }
-- OBJECT-IDENTITY
--  Status
--    mandatory

portGigEthernet OBJECT IDENTIFIER ::= { portStandard 9 }
-- OBJECT-IDENTITY
--  Status
--    mandatory
--  Descr
--    Standard identifiers for fixed Gigabit Ethernet ports.

portSc1000SX OBJECT IDENTIFIER ::= { portGigEthernet 1 }
-- OBJECT-IDENTITY
--  Status
--    mandatory
--  Descr
--    Fixed mount 1000Base-SX port supporting multimode fiber
--    with a SC connector.

portSc1000LX OBJECT IDENTIFIER ::= { portGigEthernet 2 }
-- OBJECT-IDENTITY
--  Status
--    mandatory
--  Descr
--    Fixed mount 1000Base-LX port supporting either multimode or
--    single mode fiber with a SC connector.

portRJ451000T OBJECT IDENTIFIER ::= { portGigEthernet 3 }
-- OBJECT-IDENTITY
--  Status
--    mandatory
--  Descr
--    Fixed mount 1000Base-T port supporting UTP cable with
--    a RJ-45 connectors.


portEpim OBJECT IDENTIFIER ::= { portXpim 1 }
-- OBJECT-IDENTITY
--  Status
--    mandatory

portTpim OBJECT IDENTIFIER ::= { portXpim 2 }
-- OBJECT-IDENTITY
--  Status
--    mandatory

portFpim OBJECT IDENTIFIER ::= { portXpim 3 }
-- OBJECT-IDENTITY
--  Status
--    mandatory

portApim OBJECT IDENTIFIER ::= { portXpim 4 }
-- OBJECT-IDENTITY
--  Status
--    mandatory
--  Descr
--    This branch describes all ATM PIMs as port types.

portWpim OBJECT IDENTIFIER ::= { portXpim 5 }
-- OBJECT-IDENTITY
--  Status
--    mandatory
--  Descr
--    This branch describes all WAN PIMs as port types.

portFEpim OBJECT IDENTIFIER ::= { portXpim 6 }
-- OBJECT-IDENTITY
--  Status
--    mandatory
--  Descr
--    This branch describes all fast ethernet PIMs as port types.

portGpim OBJECT IDENTIFIER ::= { portXpim 7 }
-- OBJECT-IDENTITY
--  Status
--    mandatory
--  Descr
--    This branch describes all Gigabit PIMs as port types.

portVapim OBJECT IDENTIFIER ::= { portXpim 8 }
-- OBJECT-IDENTITY
--  Status
--    mandatory
--  Descr
--    This branch describes all VAPIMs as port types.  VAPIMS
--    are designed to be the interface module for devices
--    complying with ATM VHSIM architecture.

portUnknown OBJECT IDENTIFIER ::= { portEthernet 1 }
-- OBJECT-IDENTITY
--  Status
--    mandatory

portBNC OBJECT IDENTIFIER ::= { portEthernet 2 }
-- OBJECT-IDENTITY
--  Status
--    mandatory

portAUI OBJECT IDENTIFIER ::= { portEthernet 3 }
-- OBJECT-IDENTITY
--  Status
--    mandatory

portTrans OBJECT IDENTIFIER ::= { portEthernet 4 }
-- OBJECT-IDENTITY
--  Status
--    mandatory

portCTp OBJECT IDENTIFIER ::= { portEthernet 5 }
-- OBJECT-IDENTITY
--  Status
--    mandatory

portRJ45 OBJECT IDENTIFIER ::= { portEthernet 6 }
-- OBJECT-IDENTITY
--  Status
--    mandatory

portDb9 OBJECT IDENTIFIER ::= { portEthernet 7 }
-- OBJECT-IDENTITY
--  Status
--    mandatory

portRJ71 OBJECT IDENTIFIER ::= { portEthernet 8 }
-- OBJECT-IDENTITY
--  Status
--    mandatory

portMmfSMA OBJECT IDENTIFIER ::= { portEthernet 9 }
-- OBJECT-IDENTITY
--  Status
--    mandatory

portMmfST OBJECT IDENTIFIER ::= { portEthernet 10 }
-- OBJECT-IDENTITY
--  Status
--    mandatory

portSmfST OBJECT IDENTIFIER ::= { portEthernet 11 }
-- OBJECT-IDENTITY
--  Status
--    mandatory

portBPlaneA OBJECT IDENTIFIER ::= { portEthernet 12 }
-- OBJECT-IDENTITY
--  Status
--    mandatory

portBPlaneB OBJECT IDENTIFIER ::= { portEthernet 13 }
-- OBJECT-IDENTITY
--  Status
--    mandatory

portBPlaneC OBJECT IDENTIFIER ::= { portEthernet 14 }
-- OBJECT-IDENTITY
--  Status
--    mandatory

portMmfMTRJb10FL OBJECT IDENTIFIER ::= { portEthernet 15 }
-- OBJECT-IDENTITY
--  Status
--    mandatory
--  Descr
--    10Base-FL Multimode fiber mini MT-RJ

portTRUnknown OBJECT IDENTIFIER ::= { portTokenRing 1 }
-- OBJECT-IDENTITY
--  Status
--    mandatory

portLobeUtpRJ45 OBJECT IDENTIFIER ::= { portTokenRing 2 }
-- OBJECT-IDENTITY
--  Status
--    mandatory

portLobeStpDb9 OBJECT IDENTIFIER ::= { portTokenRing 3 }
-- OBJECT-IDENTITY
--  Status
--    mandatory

portLobeStpRJ45 OBJECT IDENTIFIER ::= { portTokenRing 4 }
-- OBJECT-IDENTITY
--  Status
--    mandatory

portLobeMmfST OBJECT IDENTIFIER ::= { portTokenRing 5 }
-- OBJECT-IDENTITY
--  Status
--    mandatory

portLobeSmfST OBJECT IDENTIFIER ::= { portTokenRing 6 }
-- OBJECT-IDENTITY
--  Status
--    mandatory

portRingpStpDb9 OBJECT IDENTIFIER ::= { portTokenRing 7 }
-- OBJECT-IDENTITY
--  Status
--    mandatory

portRingpMmfST OBJECT IDENTIFIER ::= { portTokenRing 8 }
-- OBJECT-IDENTITY
--  Status
--    mandatory

portLobeUtpStpRJ45 OBJECT IDENTIFIER ::= { portTokenRing 9 }
-- OBJECT-IDENTITY
--  Status
--    mandatory

portFDDIUnknown OBJECT IDENTIFIER ::= { portFDDI 1 }
-- OBJECT-IDENTITY
--  Status
--    mandatory

portFDDIMmfMic OBJECT IDENTIFIER ::= { portFDDI 2 }
-- OBJECT-IDENTITY
--  Status
--    mandatory
--  Descr
--    Multimode Fiber MIC.

portFDDIUtpRJ45 OBJECT IDENTIFIER ::= { portFDDI 3 }
-- OBJECT-IDENTITY
--  Status
--    mandatory
--  Descr
--    Level V/category 5 UTP RJ45 connector.

portFDDIStpRJ45 OBJECT IDENTIFIER ::= { portFDDI 4 }
-- OBJECT-IDENTITY
--  Status
--    mandatory
--  Descr
--    Level V/Category 5  STP RJ45 connector.

portFDDISmfMic1 OBJECT IDENTIFIER ::= { portFDDI 5 }
-- OBJECT-IDENTITY
--  Status
--    mandatory
--  Descr
--    Single mode Fiber MIC class 1 laser.

portFDDIMmfSc OBJECT IDENTIFIER ::= { portFDDI 6 }
-- OBJECT-IDENTITY
--  Status
--    mandatory
--  Descr
--    Multimode fiber SC connector.

portFDDISmfSc OBJECT IDENTIFIER ::= { portFDDI 7 }
-- OBJECT-IDENTITY
--  Status
--    mandatory
--  Descr
--    Single mode fiber SC connector.

portFDDIMmfSt OBJECT IDENTIFIER ::= { portFDDI 8 }
-- OBJECT-IDENTITY
--  Status
--    mandatory
--  Descr
--    Multimode fiber ST connector.

portFDDISmfSt OBJECT IDENTIFIER ::= { portFDDI 9 }
-- OBJECT-IDENTITY
--  Status
--    mandatory
--  Descr
--    Single mode fiber ST connector.

portFDDISmLrfSc OBJECT IDENTIFIER ::= { portFDDI 17 }
-- OBJECT-IDENTITY
--  Status
--    mandatory
--  Descr
--    Single mode long range fiber SC connector.

portATM155MMF OBJECT IDENTIFIER ::= { portATM 1 }
-- OBJECT-IDENTITY
--  Status
--    mandatory
--  Descr
--    155 MPS MMF SC duplex Sonet/SDH ATM port.

portATM155SMF OBJECT IDENTIFIER ::= { portATM 2 }
-- OBJECT-IDENTITY
--  Status
--    mandatory
--  Descr
--    155 MPS SMF SC duplex Sonet/SDH ATM port.

portUnknownb100 OBJECT IDENTIFIER ::= { portFastEthernet 1 }
-- OBJECT-IDENTITY
--  Status
--    mandatory

portRJ45b100TX OBJECT IDENTIFIER ::= { portFastEthernet 2 }
-- OBJECT-IDENTITY
--  Status
--    mandatory
--  Descr
--    100Base-TX RJ45.

portRJ45b100T4 OBJECT IDENTIFIER ::= { portFastEthernet 3 }
-- OBJECT-IDENTITY
--  Status
--    mandatory
--  Descr
--    100Base-T4 RJ45.

portRJ45b100T2 OBJECT IDENTIFIER ::= { portFastEthernet 4 }
-- OBJECT-IDENTITY
--  Status
--    mandatory
--  Descr
--    100Base-T2 RJ45.

portMmfScb100FX OBJECT IDENTIFIER ::= { portFastEthernet 5 }
-- OBJECT-IDENTITY
--  Status
--    mandatory
--  Descr
--    100Base-FX Multimode fiber SC.

portSmfScb100FX OBJECT IDENTIFIER ::= { portFastEthernet 6 }
-- OBJECT-IDENTITY
--  Status
--    mandatory
--  Descr
--    100Base-FX Singlemode fiber SC.

portRJ71b100TX OBJECT IDENTIFIER ::= { portFastEthernet 7 }
-- OBJECT-IDENTITY
--  Status
--    mandatory

portMmfMTRJb100FX OBJECT IDENTIFIER ::= { portFastEthernet 8 }
-- OBJECT-IDENTITY
--  Status
--    mandatory
--  Descr
--   100Base-FX Multimode fiber mini MT-RJ

portSmfMTRJb100FX OBJECT IDENTIFIER ::= { portFastEthernet 9 }
-- OBJECT-IDENTITY
--  Status
--    mandatory
--  Descr
--   100Base-FX Singlemode fiber mini MT-RJ

portEpimUnknown OBJECT IDENTIFIER ::= { portEpim 1 }
-- OBJECT-IDENTITY
--  Status
--    mandatory

portEpimAUI OBJECT IDENTIFIER ::= { portEpim 2 }
-- OBJECT-IDENTITY
--  Status
--    mandatory
--  Descr
--    EPIM with AUI connector

portEpimBNC OBJECT IDENTIFIER ::= { portEpim 3 }
-- OBJECT-IDENTITY
--  Status
--    mandatory
--  Descr
--    EPIM with BNC type connector.

portEpimRJ45 OBJECT IDENTIFIER ::= { portEpim 4 }
-- OBJECT-IDENTITY
--  Status
--    mandatory
--  Descr
--    EPIM with RJ45 port.

portEpimMmfST OBJECT IDENTIFIER ::= { portEpim 5 }
-- OBJECT-IDENTITY
--  Status
--    mandatory

portEpimMmfSMA OBJECT IDENTIFIER ::= { portEpim 6 }
-- OBJECT-IDENTITY
--  Status
--    mandatory

portEpimSmfST OBJECT IDENTIFIER ::= { portEpim 8 }
-- OBJECT-IDENTITY
--  Status
--    mandatory

portEpimTrans OBJECT IDENTIFIER ::= { portEpim 9 }
-- OBJECT-IDENTITY
--  Status
--    mandatory

portEpimThirdParty OBJECT IDENTIFIER ::= { portEpim 10 }
-- OBJECT-IDENTITY
--  Status
--    mandatory
--  Descr
--    Epim with internal connection to third party BRIM.

portEpimRJ45fd OBJECT IDENTIFIER ::= { portEpim 12 }
-- OBJECT-IDENTITY
--  Status
--    mandatory
--  Descr
--    Full duplex epim with RJ45 connector.

portEpimMmfSTfd OBJECT IDENTIFIER ::= { portEpim 13 }
-- OBJECT-IDENTITY
--  Status
--    mandatory
--  Descr
--    Full duplex epim with multi-mode fiber ST connector.

portEpimMmfSMAfd OBJECT IDENTIFIER ::= { portEpim 14 }
-- OBJECT-IDENTITY
--  Status
--    mandatory
--  Descr
--    Full duplex epim with multi-mode fiber SMA connector.

portEpimSmfSTfd OBJECT IDENTIFIER ::= { portEpim 15 }
-- OBJECT-IDENTITY
--  Status
--    mandatory
--  Descr
--    Full duplex epim with single-mode fiber ST connector.

portEpimHWAUI OBJECT IDENTIFIER ::= { portEpim 16 }
-- OBJECT-IDENTITY
--  Status
--    mandatory

portEpim100Tx OBJECT IDENTIFIER ::= { portEpim 17 }
-- OBJECT-IDENTITY
--  Status
--    mandatory
--  Descr
--    100 Base TX RJ45 Epim.

portEpim100Fx OBJECT IDENTIFIER ::= { portEpim 18 }
-- OBJECT-IDENTITY
--  Status
--    mandatory
--  Descr
--    100 Base FX multi-mode fiber SC Epim.

portEpim100Fmb OBJECT IDENTIFIER ::= { portEpim 19 }
-- OBJECT-IDENTITY
--  Status
--    mandatory
--  Descr
--    A forward only bridge used in 100BaseTX devices,
--    populates an EPIM slot.

portEpim1002F2 OBJECT IDENTIFIER ::= { portEpim 20 }
-- OBJECT-IDENTITY
--  Status
--    mandatory
--  Descr
--    2 port 100 Base FX multi-mode expansion module

portEpim1002F3 OBJECT IDENTIFIER ::= { portEpim 21 }
-- OBJECT-IDENTITY
--  Status
--    mandatory
--  Descr
--    2 port 100 Base FX single-mode expansion module.

portEpim1002F4 OBJECT IDENTIFIER ::= { portEpim 22 }
-- OBJECT-IDENTITY
--  Status
--    mandatory
--  Descr
--    2 port 100 Base FX expansion module with a
--    singlemode port and a multimode port.

portEpimThirdPartyBrim OBJECT IDENTIFIER ::= { portEpimThirdParty 1 }
-- OBJECT-IDENTITY
--  Status
--    mandatory
--  Descr
--    Epim with internal connection to third party BRIMs.

portEpimThirdPartyNonBrim OBJECT IDENTIFIER ::= { portEpimThirdParty 2 }
-- OBJECT-IDENTITY
--  Status
--    mandatory
--  Descr
--    Epim with internal connection to third party daughter
--    cards.

portEpimThirdPartyUnknown OBJECT IDENTIFIER ::= { portEpimThirdParty 3 }
-- OBJECT-IDENTITY
--  Status
--    mandatory
--  Descr
--    Unknown EPIM connection type.

portEpimThirdPartyCABO OBJECT IDENTIFIER ::= { portEpimThirdPartyBrim 1 }
-- OBJECT-IDENTITY
--  Status
--    mandatory
--  Descr
--    Cisco CABO-E daughter card 'BRIM'.

portTpimUnkown OBJECT IDENTIFIER ::= { portTpim 1 }
-- OBJECT-IDENTITY
--  Status
--    mandatory
--  Descr
--    Unknown TPIM

portTpimT1 OBJECT IDENTIFIER ::= { portTpim 2 }
-- OBJECT-IDENTITY
--  Status
--    mandatory
--  Descr
--    TPIM with STP DB9 connection

portTpimF2 OBJECT IDENTIFIER ::= { portTpim 4 }
-- OBJECT-IDENTITY
--  Status
--    mandatory
--  Descr
--    TPIM with ST multimode fiber connectors

portTpimT2 OBJECT IDENTIFIER ::= { portTpim 5 }
-- OBJECT-IDENTITY
--  Status
--    mandatory
--  Descr
--    TPIM with UTP RJ45

portTpimF3 OBJECT IDENTIFIER ::= { portTpim 6 }
-- OBJECT-IDENTITY
--  Status
--    mandatory
--  Descr
--    TPIM w/single mode fiber, ST connectors

portTpimT4 OBJECT IDENTIFIER ::= { portTpim 7 }
-- OBJECT-IDENTITY
--  Status
--    mandatory
--  Descr
--    TPIM with STP RJ45 connectors.

portFpimUnknown OBJECT IDENTIFIER ::= { portFpim 1 }
-- OBJECT-IDENTITY
--  Status
--    mandatory

portFpim0 OBJECT IDENTIFIER ::= { portFpim 2 }
-- OBJECT-IDENTITY
--  Status
--    mandatory
--  Descr
--    Multimode Fiber MIC.

portFpim2 OBJECT IDENTIFIER ::= { portFpim 3 }
-- OBJECT-IDENTITY
--  Status
--    mandatory
--  Descr
--    Level V/category 5 UTP RJ45 connector.

portFpim4 OBJECT IDENTIFIER ::= { portFpim 4 }
-- OBJECT-IDENTITY
--  Status
--    mandatory
--  Descr
--    Level V/Category 5  STP RJ45 connector.

portFpim5 OBJECT IDENTIFIER ::= { portFpim 5 }
-- OBJECT-IDENTITY
--  Status
--    mandatory
--  Descr
--    Single mode Fiber MIC class 1 laser.

portFpim1 OBJECT IDENTIFIER ::= { portFpim 6 }
-- OBJECT-IDENTITY
--  Status
--    mandatory
--  Descr
--    Multimode fiber SC connector.

portFpim7 OBJECT IDENTIFIER ::= { portFpim 7 }
-- OBJECT-IDENTITY
--  Status
--    mandatory
--  Descr
--    Single mode fiber SC connector.

portFpim8 OBJECT IDENTIFIER ::= { portFpim 8 }
-- OBJECT-IDENTITY
--  Status
--    mandatory
--  Descr
--    Multimode fiber ST connector.

portFpim9 OBJECT IDENTIFIER ::= { portFpim 9 }
-- OBJECT-IDENTITY
--  Status
--    mandatory
--  Descr
--    Single mode fiber ST connector.

portApim02 OBJECT IDENTIFIER ::= { portApim 1 }
-- OBJECT-IDENTITY
--  Status
--    mandatory
--  Descr
--    51 Mbps, OC1, UTP, RJ45

portApim11 OBJECT IDENTIFIER ::= { portApim 2 }
-- OBJECT-IDENTITY
--  Status
--    mandatory
--  Descr
--    100 Mbps, TAXI, MMF, SC

portApim21 OBJECT IDENTIFIER ::= { portApim 3 }
-- OBJECT-IDENTITY
--  Status
--    mandatory
--  Descr
--    155 Mbps, OC3, MMF, SC

portApim29 OBJECT IDENTIFIER ::= { portApim 4 }
-- OBJECT-IDENTITY
--  Status
--    mandatory
--  Descr
--    155 Mbps, OC3, SMF, SC

portApim67 OBJECT IDENTIFIER ::= { portApim 5 }
-- OBJECT-IDENTITY
--  Status
--    mandatory
--  Descr
--    45 Mbps, DS3, Coax, BNC

portApim28 OBJECT IDENTIFIER ::= { portApim 6 }
-- OBJECT-IDENTITY
--  Status
--    mandatory
--  Descr
--    155 Mbps, OC3, multi-mode fiber, ST

portApim22 OBJECT IDENTIFIER ::= { portApim 7 }
-- OBJECT-IDENTITY
--  Status
--    mandatory
--  Descr
--    155 Mbps, STS3, UTP, RJ45

portApimUnknown OBJECT IDENTIFIER ::= { portApim 8 }
-- OBJECT-IDENTITY
--  Status
--    mandatory
--  Descr
--    An unknown APIM

portApim29LR OBJECT IDENTIFIER ::= { portApim 9 }
-- OBJECT-IDENTITY
--  Status
--    mandatory
--  Descr
--    155 Mbps, OC3, SMF-LR, SC

portApim31 OBJECT IDENTIFIER ::= { portApim 10 }
-- OBJECT-IDENTITY
--  Status
--    deprecated
--  Descr
--    622 Mbps, OC12, MMF, SC

portApim39 OBJECT IDENTIFIER ::= { portApim 11 }
-- OBJECT-IDENTITY
--  Status
--    deprecated
--  Descr
--    622 Mbps, OC12, SMF-SR, SC

portApim39LR OBJECT IDENTIFIER ::= { portApim 12 }
-- OBJECT-IDENTITY
--  Status
--    deprecated
--  Descr
--    622 Mbps, OC12, SMF-LR, SC


portVapim31 OBJECT IDENTIFIER ::= { portVapim 1 }
-- OBJECT-IDENTITY
--  Status
--    mandatory
--  Descr
--    622 Mbps, OC12, MMF, SC for ATM VHSIM

portVapim39 OBJECT IDENTIFIER ::= { portVapim 2 }
-- OBJECT-IDENTITY
--  Status
--    mandatory
--  Descr
--    622 Mbps, OC12, SMF-SR, SC for ATM VHSIM

portVapim39LR OBJECT IDENTIFIER ::= { portVapim 3 }
-- OBJECT-IDENTITY
--  Status
--    mandatory
--  Descr
--    622 Mbps, OC12, SMF-LR, SC for ATM VHSIM

portWpimUnknown OBJECT IDENTIFIER ::= { portWpim 1 }
-- OBJECT-IDENTITY
--  Status
--    mandatory
--  Descr
--    Unknown type of WPIM.

portWpimT1 OBJECT IDENTIFIER ::= { portWpim 2 }
-- OBJECT-IDENTITY
--  Status
--    mandatory
--  Descr
--    WPIM supporting a T1/PRI CSU/DSU

portWpimE1 OBJECT IDENTIFIER ::= { portWpim 3 }
-- OBJECT-IDENTITY
--  Status
--    mandatory
--  Descr
--    WPIM supporting a E1/PRI CSU/DSU

portWpimSy OBJECT IDENTIFIER ::= { portWpim 4 }
-- OBJECT-IDENTITY
--  Status
--    mandatory
--  Descr
--    WPIM supporting a Synchronous Serial Interface

portWpimDDS OBJECT IDENTIFIER ::= { portWpim 5 }
-- OBJECT-IDENTITY
--  Status
--    mandatory
--  Descr
--    WPIM supporting a DDS/SW56 CSU/DSU

portWpimDI OBJECT IDENTIFIER ::= { portWpim 6 }
-- OBJECT-IDENTITY
--  Status
--    mandatory
--  Descr
--    WPIM supporting drop and insert.

portWpimHDSL OBJECT IDENTIFIER ::= { portWpim 7 }
-- OBJECT-IDENTITY
--  Status
--    mandatory
--  Descr
--    WPIM supporting HDSL.

portWpimBRI OBJECT IDENTIFIER ::= { portWpim 8 }
-- OBJECT-IDENTITY
--  Status
--    mandatory
--  Descr
--    WPIM supporting a ISDN basic rate Interface

portWpimDS30 OBJECT IDENTIFIER ::= { portWpim 9 }
-- OBJECT-IDENTITY
--  Status
--    mandatory
--  Descr
--    WPIM supporting DS30.

portWpimDataCapableDI  OBJECT IDENTIFIER ::= { portWpim 10 }
-- OBJECT-IDENTITY
--  Status
--    mandatory
--  Descr
--    WPIM supporting Drop and Inser with capability to
--    process data from D/I interface.

portWpimT1DDS OBJECT IDENTIFIER ::= { portWpim 11 }
-- OBJECT-IDENTITY
--  Status
--    mandatory
--  Descr
--    WPIM supporting mode switching from DDS to T1
--    and vice versa.

portWpimRDDS OBJECT IDENTIFIER ::= { portWpim 12 }
-- OBJECT-IDENTITY
--  Status
--    mandatory
--  Descr
--    Respin of WPIM supporting a DDS/SW56 CSU/DSU

portWpimRT1 OBJECT IDENTIFIER ::= { portWpim 13 }
-- OBJECT-IDENTITY
--  Status
--    mandatory
--  Descr
--    Respin of WPIM supporting a T1/PRI CSU/DSU

portWpimRE1 OBJECT IDENTIFIER ::= { portWpim 14 }
-- OBJECT-IDENTITY
--  Status
--    mandatory
--  Descr
--    Respin of WPIM supporting a E1/PRI CSU/DSU

portFEUnknown OBJECT IDENTIFIER ::= { portFEpim 1 }
-- OBJECT-IDENTITY
--  Status
--    mandatory
--  Descr
--    Unknown fast ethernet module.

portFE100TxUTP OBJECT IDENTIFIER ::= { portFEpim 2 }
-- OBJECT-IDENTITY
--  Status
--    mandatory
--  Descr
--    100BaseTX Fast LAN Switch Interface RJ 45 UTP plug in
--    module.

portFE100TxSTP OBJECT IDENTIFIER ::= { portFEpim 3 }
-- OBJECT-IDENTITY
--  Status
--    mandatory
--  Descr
--    100BaseTX Fast LAN Switch Interface DB9 STP plug in
--    module.

portFE100Fx OBJECT IDENTIFIER ::= { portFEpim 4 }
-- OBJECT-IDENTITY
--  Status
--    mandatory
--  Descr
--    100BaseFX Fast LAN Switch Interface Multimode fiber SC
--    connector, plug in module.

portFE100VG4 OBJECT IDENTIFIER ::= { portFEpim 5 }
-- OBJECT-IDENTITY
--  Status
--    mandatory
--  Descr
--    100Base-VG Interface module supports RJ45 connector
--    for UTP 4 pair.

portFE100VGF OBJECT IDENTIFIER ::= { portFEpim 6 }
-- OBJECT-IDENTITY
--  Status
--    mandatory
--  Descr
--    100Base-VG Interface module supports multimode fiber
--    SC connector.

portFE100F3 OBJECT IDENTIFIER ::= { portFEpim 7 }
-- OBJECT-IDENTITY
--  Status
--    mandatory
--  Descr
--    100BaseFX Fast LAN Switch Interface singlemode fiber SC
--    connector, plug in module.

portFE100S1 OBJECT IDENTIFIER ::= { portFEpim 8 }
-- OBJECT-IDENTITY
--  Status
--    mandatory
--  Descr
--    Fast ethernet to SONET PIM with multimode fiber
--    SC connector.

portFE100S3 OBJECT IDENTIFIER ::= { portFEpim 9 }
-- OBJECT-IDENTITY
--  Status
--    mandatory
--  Descr
--    Fast ethernet to SONET PIM with single mode fiber
--    SC connector.

portFE100S5 OBJECT IDENTIFIER ::= { portFEpim 10 }
-- OBJECT-IDENTITY
--  Status
--    mandatory
--  Descr
--    Fast ethernet to SONET PIM with single mode fiber
--    SC connector, long reach.

portFE100LH OBJECT IDENTIFIER ::= { portFEpim 11 }
-- OBJECT-IDENTITY
--  Status
--    mandatory
--  Descr
--    100BaseFX Fast LAN Switch Interface singlemode fiber SC
--    connector, extended distance plug in module.

portGpimF01 OBJECT IDENTIFIER ::= { portGpim 1 }
-- OBJECT-IDENTITY
--  Status
--    mandatory
--  Descr
--    1 Gigabit Fiber Channel with multimode fiber SC connectors.

portGpimF09 OBJECT IDENTIFIER ::= { portGpim 2 }
-- OBJECT-IDENTITY
--  Status
--    mandatory
--  Descr
--    1 Gigabit Fiber Channel with singlemode fiber SC connectors.

portGpimS41 OBJECT IDENTIFIER ::= { portGpim 3 }
-- OBJECT-IDENTITY
--  Status
--    mandatory
--  Descr
--    1.2 Gigabit SONET with multimode fiber SC connectors.

portGpimS49 OBJECT IDENTIFIER ::= { portGpim 4 }
-- OBJECT-IDENTITY
--  Status
--    mandatory
--  Descr
--    1.2 Gigabit SONET with singlemode fiber SC connectors.

portGpimS51 OBJECT IDENTIFIER ::= { portGpim 5 }
-- OBJECT-IDENTITY
--  Status
--    mandatory
--  Descr
--    2.4 Gigabit SONET with multimode fiber SC connectors.

portGpimS59 OBJECT IDENTIFIER ::= { portGpim 6 }
-- OBJECT-IDENTITY
--  Status
--    mandatory
--  Descr
--    2.4 Gigabit SONET with singlemode fiber SC connectors.

portGpimS31 OBJECT IDENTIFIER ::= { portGpim 7 }
-- OBJECT-IDENTITY
--  Status
--    mandatory
--  Descr
--    622 Megabit SONET with multimode fiber SC connectors.

portGpimS39 OBJECT IDENTIFIER ::= { portGpim 8 }
-- OBJECT-IDENTITY
--  Status
--    mandatory
--  Descr
--    622 Megabit SONET with singlemode fiber SC connectors.

portGpim01 OBJECT IDENTIFIER ::= { portGpim 9 }
-- OBJECT-IDENTITY
--  Status
--    mandatory
--  Descr
--    1000Base-SX with multimode fiber SC connectors. The
--    laser is an 850 nanometer optical laser.

portGpim04 OBJECT IDENTIFIER ::= { portGpim 10 }
-- OBJECT-IDENTITY
--  Status
--    mandatory
--  Descr
--    1000Base-CX with 150 ohm shielded style 2 connectors

portGpim09 OBJECT IDENTIFIER ::= { portGpim 11 }
-- OBJECT-IDENTITY
--  Status
--    mandatory
--  Descr
--    1000Base-LX with single or multi-mode fiber SC
--    connector. The laser is a 1300 nanometer optical laser

portGpim08 OBJECT IDENTIFIER ::= { portGpim 12 }
-- OBJECT-IDENTITY
--  Status
--    mandatory
--  Descr
--    1000Base-LX extended distance with single-mode fiber SC.

portAnim OBJECT IDENTIFIER ::= { portXnim 1 }
-- OBJECT-IDENTITY
--  Status
--    mandatory
--  Descr
--    This branch describes all ATM NIMs as port types.

portAnim21p3 OBJECT IDENTIFIER ::= { portAnim 1 }
-- OBJECT-IDENTITY
--  Status
--    mandatory
--  Descr
--    3 port I/O module, 155 Mbps, OC3c, with multimode fiber SC connector.

portAnim29p3 OBJECT IDENTIFIER ::= { portAnim 2 }
-- OBJECT-IDENTITY
--  Status
--    mandatory
--  Descr
--    3 port I/O module, 155 Mbps, OC3c, with singlemode fiber SC connector.

portAnim22p4 OBJECT IDENTIFIER ::= { portAnim 3 }
-- OBJECT-IDENTITY
--  Status
--    mandatory
--  Descr
--    4 port I/O module, 155 Mbps, STS3c, with UTP5 RJ-45 connector.

portAnim31p2 OBJECT IDENTIFIER ::= { portAnim 4 }
-- OBJECT-IDENTITY
--  Status
--    mandatory
--  Descr
--    2 port I/O module, 622 Mbps, OC12c, with multimode fiber SC connector.

portAnim39p2 OBJECT IDENTIFIER ::= { portAnim 5 }
-- OBJECT-IDENTITY
--  Status
--    mandatory
--  Descr
--    2 port I/O module, 622 Mbps, OC12c, with singlemode fiber SC connector.

portAnim29p4LR OBJECT IDENTIFIER ::= { portAnim 6 }
-- OBJECT-IDENTITY
--  Status
--    mandatory
--  Descr
--    4 port I/O module, 155 Mbps, OC3, with long range singlemode fiber SC
--    connectors.

portAnim29p3LR OBJECT IDENTIFIER ::= { portAnim 7 }
-- OBJECT-IDENTITY
--  Status
--    mandatory
--  Descr
--    3 port I/O module, 155 Mbps, OC3, with long range singlemode fiber
--    SC connector.

portAnim39p2LR OBJECT IDENTIFIER ::= { portAnim 8 }
-- OBJECT-IDENTITY
--  Status
--    mandatory
--  Descr
--    2 port I/O module, 622 Mbps, OC12, with long range singlemode fiber
--    SC connector.

portAnim59p1LR OBJECT IDENTIFIER ::= { portAnim 9 }
-- OBJECT-IDENTITY
--  Status
--    mandatory
--  Descr
--    1 port I/O module, 2.5 Gbps, OC48, with long range singlemode fiber
--    SC connector.

portAnim21p4 OBJECT IDENTIFIER ::= { portAnim 10 }
-- OBJECT-IDENTITY
--  Status
--    mandatory
--  Descr
--    4 port I/O module, 155 Mbps, OC3, with multimode fiber SC connector.

portAnim29p4 OBJECT IDENTIFIER ::= { portAnim 11 }
-- OBJECT-IDENTITY
--  Status
--    mandatory
--  Descr
--    4 port I/O module, 155 Mbps, OC3, with singlemode fiber SC connector.

portAnim67p2 OBJECT IDENTIFIER ::= { portAnim 12 }
-- OBJECT-IDENTITY
--  Status
--    mandatory
--  Descr
--    2 port I/O module, 45 Mbps, DS3, with coaxial BNC connectors.

portAnim77p2 OBJECT IDENTIFIER ::= { portAnim 13 }
-- OBJECT-IDENTITY
--  Status
--    mandatory
--  Descr
--    2 port I/O module, 33 Mbps, E3, with coaxial BNC connectors.

portAnim51p1 OBJECT IDENTIFIER ::= { portAnim 14 }
-- OBJECT-IDENTITY
--  Status
--    mandatory
--  Descr
--    1 port I/O module, 2.5 Gbps, OC48, with multimode fiber SC connector.

portAnim59p1 OBJECT IDENTIFIER ::= { portAnim 15 }
-- OBJECT-IDENTITY
--  Status
--    mandatory
--  Descr
--    1 port I/O module, 2.5 Gbps, OC48, with singlemode fiber SC connector.

chipType OBJECT IDENTIFIER ::= { hardwareType 1 }
-- OBJECT-IDENTITY
--  Status
--    mandatory

fddiMACDP83261 OBJECT IDENTIFIER ::= { chipType 1 }
-- OBJECT-IDENTITY
--  Status
--    mandatory

fddiPortDP83251 OBJECT IDENTIFIER ::= { chipType 2 }
-- OBJECT-IDENTITY
--  Status
--    mandatory

i960sa OBJECT IDENTIFIER ::= { chipType 3 }
-- OBJECT-IDENTITY
--  Status
--    mandatory
--  Descr
--    The intel 960 sa CPU.

i960ca OBJECT IDENTIFIER ::= { chipType 4 }
-- OBJECT-IDENTITY
--  Status
--    mandatory
--  Descr
--    The intel 960 CA CPU.

i960cf OBJECT IDENTIFIER ::= { chipType 5 }
-- OBJECT-IDENTITY
--  Status
--    mandatory
--  Descr
--    The intel 960 CF CPU.

i960ha OBJECT IDENTIFIER ::= { chipType 6 }
-- OBJECT-IDENTITY
--  Status
--    mandatory
--  Descr
--    The intel 960 HA CPU

i960hd OBJECT IDENTIFIER ::= { chipType 7 }
-- OBJECT-IDENTITY
--  Status
--    mandatory
--  Descr
--    The intel 960 HD CPU.

i960ht OBJECT IDENTIFIER ::= { chipType 8 }
-- OBJECT-IDENTITY
--  Status
--    mandatory
--  Descr
--    The intel 960 HT CPU.

powerPC603 OBJECT IDENTIFIER ::= { chipType 9 }
-- OBJECT-IDENTITY
--  Status
--    mandatory
--  Descr
--    The Power PC 603 processor.

powerPC603e OBJECT IDENTIFIER ::= { chipType 10 }
-- OBJECT-IDENTITY
--  Status
--    mandatory
--  Descr
--    The Power PC 603e processor.

powerPC604 OBJECT IDENTIFIER ::= { chipType 11 }
-- OBJECT-IDENTITY
--  Status
--    mandatory
--  Descr
--    The Power PC 604 processor.

powerPC740 OBJECT IDENTIFIER ::= { chipType 12 }
-- OBJECT-IDENTITY
--  Status
--    mandatory
--  Descr
--    The Power PC 740 processor.

powerMIPS5000 OBJECT IDENTIFIER ::= { chipType 13 }
-- OBJECT-IDENTITY
--  Status
--    mandatory
--  Descr
--    The CPU for the Omelette.

powerPC8241 OBJECT IDENTIFIER ::= { chipType 14 }
-- OBJECT-IDENTITY
--  Status
--    mandatory
--  Descr
--    The Power PC 8241 processor.

powerPC8245 OBJECT IDENTIFIER ::= { chipType 15 }
-- OBJECT-IDENTITY
--  Status
--    mandatory
--  Descr
--    The Power PC 8245 processor.

psMonitorTypes OBJECT IDENTIFIER ::= { physicalType 3 }
-- OBJECT-IDENTITY
--  Status
--    mandatory
--  Descr
--    This defines a naming tree for physical power supply
--    monitoring points.

powerSupplyMonitors OBJECT IDENTIFIER ::= { psMonitorTypes 1 }
-- OBJECT-IDENTITY
--  Status
--    mandatory
--  Descr
--    Defines a tree for all power supply monitoring types
--    ie those internal to the power supplies.

powerSupplyInputMonitor OBJECT IDENTIFIER ::= { powerSupplyMonitors 1 }
-- OBJECT-IDENTITY
--  Status
--    mandatory
--  Descr
--    Describes those power supply monitors that are on the
--    input to modules, convertors etc.

powerSupplyTermConvInput OBJECT IDENTIFIER ::= { powerSupplyMonitors 2 }
-- OBJECT-IDENTITY
--  Status
--    mandatory
--  Descr
--    This is at the input to the termination converter input.

powerSupplyLogicConvInput OBJECT IDENTIFIER ::= { powerSupplyMonitors 3 }
-- OBJECT-IDENTITY
--  Status
--    mandatory
--  Descr
--    This is at the input to the DC-DC convertor for logic
--    voltage.

powerSupplyTermOutput OBJECT IDENTIFIER ::= { powerSupplyMonitors 4 }
-- OBJECT-IDENTITY
--  Status
--    mandatory
--  Descr
--    This is the sensor at output from the termination voltage.

powerSupplyLogicOutput OBJECT IDENTIFIER ::= { powerSupplyMonitors 5 }
-- OBJECT-IDENTITY
--  Status
--    mandatory
--  Descr
--    This is the sensor at output from the power supply for
--    logic voltage rail.

powerSupplyHighVoltageOutput OBJECT IDENTIFIER ::= { powerSupplyMonitors 6 }
-- OBJECT-IDENTITY
--  Status
--    mandatory
--  Descr
--    This is the sensor at the output from the power supply
--    for high voltage rail.

chassisPowerMonitors OBJECT IDENTIFIER ::= { psMonitorTypes 2 }
-- OBJECT-IDENTITY
--  Status
--    mandatory
--  Descr
--    Defines a tree for all chassis based power supply
--    monitoring types.

chassisHighVoltageRail OBJECT IDENTIFIER ::= { chassisPowerMonitors 1 }
-- OBJECT-IDENTITY
--  Status
--    mandatory
--  Descr
--    This is the sensor on the chassis high voltage rail.

chassisLogicRail OBJECT IDENTIFIER ::= { chassisPowerMonitors 2 }
-- OBJECT-IDENTITY
--  Status
--    mandatory
--  Descr
--    This is the sensor at the chasis logic voltage rail.

chassisTermRail OBJECT IDENTIFIER ::= { chassisPowerMonitors 3 }
-- OBJECT-IDENTITY
--  Status
--    mandatory
--  Descr
--    This is the sensor at the termination voltage rail as
--    found on the chassis.

modulePowerMonitors OBJECT IDENTIFIER ::= { psMonitorTypes 3 }
-- OBJECT-IDENTITY
--  Status
--    mandatory
--  Descr
--    Defines a tree for all module based power supply
--    monitoring types.

moduleHighVoltageInput OBJECT IDENTIFIER ::= { modulePowerMonitors 1 }
-- OBJECT-IDENTITY
--  Status
--    mandatory
--  Descr
--    This is the sensor at the input to the module for the
--    high voltage rail.

moduleLogicVoltageOutput OBJECT IDENTIFIER ::= { modulePowerMonitors 2 }
-- OBJECT-IDENTITY
--  Status
--    mandatory
--  Descr
--    This is the sensor at the output from the modules convertors
--    for logic voltage.

moduleAux1Output OBJECT IDENTIFIER ::= { modulePowerMonitors 3 }
-- OBJECT-IDENTITY
--  Status
--    mandatory
--  Descr
--    This is the aux 1 output voltage level on the module.

moduleAux2Output OBJECT IDENTIFIER ::= { modulePowerMonitors 4 }
-- OBJECT-IDENTITY
--  Status
--    mandatory
--  Descr
--    This is the aux 2 output voltage level on the module.

mtExpanded OBJECT IDENTIFIER ::= { namingTree 9 }
-- OBJECT-IDENTITY
--  Status
--    mandatory

mtThrdParty OBJECT IDENTIFIER ::= { mtExpanded 1 }
-- OBJECT-IDENTITY
--  Status
--    mandatory
--  Descr
--    Defines the top of the third party module type naming
--    tree.

tpAEnet OBJECT IDENTIFIER ::= { mtThrdParty 2 }
-- OBJECT-IDENTITY
--  Status
--    mandatory
--  Descr
--    Third PartyMIMs with A channel Ethernet connections

mtPassaggioMim OBJECT IDENTIFIER ::= { tpAEnet 1 }
-- OBJECT-IDENTITY
--  Status
--    mandatory
--  Descr
--    Third party SONIX MIM providing a hardware switch for
--    either A channel backplane or front panel EPIM connection.

tpABorC OBJECT IDENTIFIER ::= { mtThrdParty 3 }
-- OBJECT-IDENTITY
--  Status
--    mandatory
--  Descr
--    Third Party Media Interface Modules with A, B, or C channel
--    connections

mtCiscoCRM3E OBJECT IDENTIFIER ::= { tpABorC 1 }
-- OBJECT-IDENTITY
--  Status
--    mandatory
--  Descr
--    Cisco router with Ethernet BIB

mtCrm2RE OBJECT IDENTIFIER ::= { tpABorC 2 }
-- OBJECT-IDENTITY
--  Status
--    mandatory
--  Descr
--    Cisco Ethernet BRIM on a mother MIM.

mtSnacMimRS232 OBJECT IDENTIFIER ::= { tpABorC 10 }
-- OBJECT-IDENTITY
--  Status
--    mandatory
--  Descr
--    RS232 without DB

mtSnacMimRS232wRS232DB OBJECT IDENTIFIER ::= { tpABorC 11 }
-- OBJECT-IDENTITY
--  Status
--    mandatory
--  Descr
--    RS232 with RS232 DB

mtSnacMimRS232wV35DB OBJECT IDENTIFIER ::= { tpABorC 12 }
-- OBJECT-IDENTITY
--  Status
--    mandatory
--  Descr
--    RS232 with V.35 DB

mtSnacMimRS232wRS422DB OBJECT IDENTIFIER ::= { tpABorC 13 }
-- OBJECT-IDENTITY
--  Status
--    mandatory
--  Descr
--    RS232 with RS422DB

mtSnacMimv35 OBJECT IDENTIFIER ::= { tpABorC 14 }
-- OBJECT-IDENTITY
--  Status
--    mandatory
--  Descr
--    V.35 without DB

mtSnacMimv35wRS232DB OBJECT IDENTIFIER ::= { tpABorC 15 }
-- OBJECT-IDENTITY
--  Status
--    mandatory
--  Descr
--    V.35 with RS232 DB

mtSnacMimV35wV35DB OBJECT IDENTIFIER ::= { tpABorC 16 }
-- OBJECT-IDENTITY
--  Status
--    mandatory
--  Descr
--    V.35 with V.35 DB

mtSnacMimV35wRS422DB OBJECT IDENTIFIER ::= { tpABorC 17 }
-- OBJECT-IDENTITY
--  Status
--    mandatory
--  Descr
--    V.35 with RS422 DB

mtSnacMimRS422DB OBJECT IDENTIFIER ::= { tpABorC 18 }
-- OBJECT-IDENTITY
--  Status
--    mandatory
--  Descr
--    RS422 without DB

mtSnacMimRS422wRS232DB OBJECT IDENTIFIER ::= { tpABorC 19 }
-- OBJECT-IDENTITY
--  Status
--    mandatory
--  Descr
--    RS422 with RS232 DB

mtSnacMimRS422wV35DB OBJECT IDENTIFIER ::= { tpABorC 20 }
-- OBJECT-IDENTITY
--  Status
--    mandatory
--  Descr
--    RS422 with V.35 DB

mtSnacMimRS422wRS422DB OBJECT IDENTIFIER ::= { tpABorC 21 }
-- OBJECT-IDENTITY
--  Status
--    mandatory
--  Descr
--    RS422 with RS422 DB

mtSnacMimSXRS232 OBJECT IDENTIFIER ::= { tpABorC 22 }
-- OBJECT-IDENTITY
--  Status
--    mandatory
--  Descr
--    486 based SNAC MIM withRS232 without DB

mtSnacMimSXRS232wRS232DB OBJECT IDENTIFIER ::= { tpABorC 23 }
-- OBJECT-IDENTITY
--  Status
--    mandatory
--  Descr
--    486 based SNAC MIM withRS232 with RS232 DB

mtSnacMimSXRS232wV35DB OBJECT IDENTIFIER ::= { tpABorC 24 }
-- OBJECT-IDENTITY
--  Status
--    mandatory
--  Descr
--    486 based SNAC MIM withRS232 with V.35 DB

mtSnacMimSXRS232wRS422DB OBJECT IDENTIFIER ::= { tpABorC 25 }
-- OBJECT-IDENTITY
--  Status
--    mandatory
--  Descr
--    486 based SNAC MIM withRS232 with RS422DB

mtSnacMimSXv35 OBJECT IDENTIFIER ::= { tpABorC 26 }
-- OBJECT-IDENTITY
--  Status
--    mandatory
--  Descr
--    486 based SNAC MIM withV.35 without DB

mtSnacMimSXv35wRS232DB OBJECT IDENTIFIER ::= { tpABorC 27 }
-- OBJECT-IDENTITY
--  Status
--    mandatory
--  Descr
--    486 based SNAC MIM withV.35 with RS232 DB

mtSnacMimSXV35wV35DB OBJECT IDENTIFIER ::= { tpABorC 28 }
-- OBJECT-IDENTITY
--  Status
--    mandatory
--  Descr
--    486 based SNAC MIM withV.35 with V.35 DB

mtSnacMimSXV35wRS422DB OBJECT IDENTIFIER ::= { tpABorC 29 }
-- OBJECT-IDENTITY
--  Status
--    mandatory
--  Descr
--    486 based SNAC MIM withV.35 with RS422 DB

mtSnacMimSXRS422DB OBJECT IDENTIFIER ::= { tpABorC 30 }
-- OBJECT-IDENTITY
--  Status
--    mandatory
--  Descr
--    486 based SNAC MIM withRS422 without DB

mtSnacMimSXRS422wRS232DB OBJECT IDENTIFIER ::= { tpABorC 31 }
-- OBJECT-IDENTITY
--  Status
--    mandatory
--  Descr
--    486 based SNAC MIM withRS422 with RS232 DB

mtSnacMimSXRS422wV35DB OBJECT IDENTIFIER ::= { tpABorC 32 }
-- OBJECT-IDENTITY
--  Status
--    mandatory
--  Descr
--    486 based SNAC MIM withRS422 with V.35 DB

mtSnacMimSXRS422wRS422DB OBJECT IDENTIFIER ::= { tpABorC 33 }
-- OBJECT-IDENTITY
--  Status
--    mandatory
--  Descr
--    486 based SNAC MIM withRS422 with RS422 DB

tpABandC OBJECT IDENTIFIER ::= { mtThrdParty 4 }
-- OBJECT-IDENTITY
--  Status
--    mandatory
--  Descr
--    Third Party Media Interface Modules with A, B, and C channel
--    connections

tpTrFNB OBJECT IDENTIFIER ::= { mtThrdParty 5 }
-- OBJECT-IDENTITY
--  Status
--    mandatory
--  Descr
--    Token Ring with FNB connection

mtCiscoCRM3T OBJECT IDENTIFIER ::= { tpTrFNB 1 }
-- OBJECT-IDENTITY
--  Status
--    mandatory
--  Descr
--    Cisco router with Token Ring BIB

mtTRMMIM62A OBJECT IDENTIFIER ::= { tpTrFNB 2 }
-- OBJECT-IDENTITY
--  Status
--    mandatory
--  Descr
--    Coaxial module for Token Ring

mt3174MIM OBJECT IDENTIFIER ::= { tpTrFNB 3 }
-- OBJECT-IDENTITY
--  Status
--    mandatory
--  Descr
--    Cluster controller from IBM

mtSNACmimRS232 OBJECT IDENTIFIER ::= { tpTrFNB 16 }
-- OBJECT-IDENTITY
--  Status
--    mandatory
--  Descr
--    RS232 w/RS232 486 CPU

mtSNACmimRS232v35db OBJECT IDENTIFIER ::= { tpTrFNB 17 }
-- OBJECT-IDENTITY
--  Status
--    mandatory
--  Descr
--    RS232 with V.35 DB 486 CPU

mtSNACmimRS232wRS422db OBJECT IDENTIFIER ::= { tpTrFNB 18 }
-- OBJECT-IDENTITY
--  Status
--    mandatory
--  Descr
--    RS232 with RS422DB 486 CPU

mtSNACmimRS232wodb486 OBJECT IDENTIFIER ::= { tpTrFNB 19 }
-- OBJECT-IDENTITY
--  Status
--    mandatory
--  Descr
--    RS232 without DB 486 CPU

mtSNACmimv35wRS232db OBJECT IDENTIFIER ::= { tpTrFNB 20 }
-- OBJECT-IDENTITY
--  Status
--    mandatory
--  Descr
--    V.35 with RS232 DB 486 CPU

mtSNACmimv35wv35db OBJECT IDENTIFIER ::= { tpTrFNB 21 }
-- OBJECT-IDENTITY
--  Status
--    mandatory
--  Descr
--    V.35 with V.35 DB 486 CPU

mtSNACmimv35RS422db OBJECT IDENTIFIER ::= { tpTrFNB 22 }
-- OBJECT-IDENTITY
--  Status
--    mandatory
--  Descr
--    V.35 with RSA422 DB 486 CPU

mtSNACmimv35wodb OBJECT IDENTIFIER ::= { tpTrFNB 23 }
-- OBJECT-IDENTITY
--  Status
--    mandatory
--  Descr
--    V.35 without DB 486 CPU

mtSNACmimRS422 OBJECT IDENTIFIER ::= { tpTrFNB 24 }
-- OBJECT-IDENTITY
--  Status
--    mandatory
--  Descr
--    RS422 with RS232 DB 486 CPU

mtSNACmimRS422wv35db OBJECT IDENTIFIER ::= { tpTrFNB 25 }
-- OBJECT-IDENTITY
--  Status
--    mandatory
--  Descr
--    RS422 with v.35 DB 486 CPU

mtSNACmimRS422wRS422db OBJECT IDENTIFIER ::= { tpTrFNB 26 }
-- OBJECT-IDENTITY
--  Status
--    mandatory
--  Descr
--    RS422 with RS422 DB 486 CPU

mtSNACmimrs433 OBJECT IDENTIFIER ::= { tpTrFNB 27 }
-- OBJECT-IDENTITY
--  Status
--    mandatory
--  Descr
--    RS433 without DB 486 CPU

tpTrFDDIFNB OBJECT IDENTIFIER ::= { mtThrdParty 6 }
-- OBJECT-IDENTITY
--  Status
--    mandatory
--  Descr
--    Token Ring with FDDI FNB connection

tpTrAEnet OBJECT IDENTIFIER ::= { mtThrdParty 7 }
-- OBJECT-IDENTITY
--  Status
--    mandatory
--  Descr
--    Token Ring with TR and A channel Enet

tpTrFDDIAEnet OBJECT IDENTIFIER ::= { mtThrdParty 8 }
-- OBJECT-IDENTITY
--  Status
--    mandatory
--  Descr
--    Token Ring with FDDI and A channel Enet

tpATM OBJECT IDENTIFIER ::= { mtThrdParty 9 }
-- OBJECT-IDENTITY
--  Status
--    mandatory
--  Descr
--    Third part MMAC ATM modules.

tpATMMIM OBJECT IDENTIFIER ::= { tpATM 1 }
-- OBJECT-IDENTITY
--  Status
--    mandatory
--  Descr
--    AT&T developed ATM switch module with 4 ports.

tpATMMIMx8 OBJECT IDENTIFIER ::= { tpATM 2 }
-- OBJECT-IDENTITY
--  Status
--    mandatory
--  Descr
--    An 8 port extension to the ATMMIM.

tpSS1500Modular OBJECT IDENTIFIER ::= { tpATM 3 }
-- OBJECT-IDENTITY
--  Status
--      mandatory
--  Descr
--      ATM OEM from Sonoma

tpSS1500Compact OBJECT IDENTIFIER ::= { tpATM 4 }
-- OBJECT-IDENTITY
--  Status
--      mandatory
--  Descr
--      ATM OEM from Sonoma

tpStandAlone OBJECT IDENTIFIER ::= { mtThrdParty 10 }
-- OBJECT-IDENTITY
--  Status
--    mandatory
--  Descr
--    Third party standalone modules.

tpELS10024TX  OBJECT IDENTIFIER ::= { tpStandAlone 1 }
-- OBJECT-IDENTITY
--  Status
--    mandatory
--  Descr
--     24 port 10/100 TX Third party ethernet switch.

tpELS10024TXM OBJECT IDENTIFIER ::= { tpStandAlone 2 }
-- OBJECT-IDENTITY
--  Status
--    mandatory
--  Descr
--     24 port 10/100 TX SmartStack switch with Fiber uplink.

tpELS10024TXG  OBJECT IDENTIFIER ::= { tpStandAlone 3 }
-- OBJECT-IDENTITY
--  Status
--    mandatory
--  Descr
--     24 port 10/100 TX SmartStack switch with Gigabit uplink.

tpELH10012  OBJECT IDENTIFIER ::= { tpStandAlone 4 }
-- OBJECT-IDENTITY
--  Status
--    mandatory
--  Descr
--     12 port 10/100 TX SmartStack repeater.

tpELH10024  OBJECT IDENTIFIER ::= { tpStandAlone 5 }
-- OBJECT-IDENTITY
--  Status
--    mandatory
--  Descr
--     24 port 10/100 TX SmartStack repeater.

tpELS10024FXG  OBJECT IDENTIFIER ::= { tpStandAlone 6 }
-- OBJECT-IDENTITY
--  Status
--    mandatory
--  Descr
--     24 port MTRJ Multimode fiber SmartStack switch 2 Modular Gigabit uplinks.

tpELS100S24TX2M  OBJECT IDENTIFIER ::= { tpStandAlone 7 }
-- OBJECT-IDENTITY
--  Status
--    mandatory
--  Descr
--    SmartStack with 24 RJ45 10/100 Fast Ethernet ports with 2 expansion slots.

xylogicsMIMs OBJECT IDENTIFIER ::= { mtThrdParty 12 }
-- OBJECT-IDENTITY
--  Status
--    mandatory
--  Descr
--    Xylogics Media Interface Modules

xylogicsCSMIM16 OBJECT IDENTIFIER ::= { xylogicsMIMs 1 }
-- OBJECT-IDENTITY
--  Status
--    mandatory
--  Descr
--    Xylogics 16 port communications server

xylogicsCSMIM32 OBJECT IDENTIFIER ::= { xylogicsMIMs 2 }
-- OBJECT-IDENTITY
--  Status
--    mandatory
--  Descr
--    Xylogics 32 port communications server

mtCSMIM16m2 OBJECT IDENTIFIER ::= { xylogicsMIMs 3 }
-- OBJECT-IDENTITY
--  Status
--    mandatory
--  Descr
--    Xylogics terminal server with 16 ports and A/B/C connectivity.

mtMODMIM4 OBJECT IDENTIFIER ::= { xylogicsMIMs 5 }
-- OBJECT-IDENTITY
--  Status
--    mandatory
--  Descr
--    Xylogics terminal server with 4 modem ports and A/B/C
--    connectivity.

mtMODMIM4x4 OBJECT IDENTIFIER ::= { xylogicsMIMs 7 }
-- OBJECT-IDENTITY
--  Status
--    mandatory
--  Descr
--    Xylogics terminal server with 8 modem ports and A/B/C
--    connectivity.

mtMODMIM4x8 OBJECT IDENTIFIER ::= { xylogicsMIMs 9 }
-- OBJECT-IDENTITY
--  Status
--    mandatory
--  Descr
--    Xylogics terminal server with 12 modem ports and A/B/C
--    connectivity.

mtCSMIM32m2 OBJECT IDENTIFIER ::= { xylogicsMIMs 10 }
-- OBJECT-IDENTITY
--  Status
--    mandatory
--  Descr
--    Xylogics CSMIM2-32 a CSMIM32 with A/B/C connectivity.

mtCSMIMm8T1 OBJECT IDENTIFIER ::= { xylogicsMIMs 11 }
-- OBJECT-IDENTITY
--  Status
--    mandatory
--  Descr
--    Xylogics T1 communication server with 8 integrated modems and A/B/C
--    connectivity

mtCSMIMm16T1 OBJECT IDENTIFIER ::= { xylogicsMIMs 12 }
-- OBJECT-IDENTITY
--  Status
--    mandatory
--  Descr
--    Xylogics T1 communication server with 16 integrated modems and A/B/C
--    connectivity

mtCSMIMm24T1 OBJECT IDENTIFIER ::= { xylogicsMIMs 13 }
-- OBJECT-IDENTITY
--  Status
--    mandatory
--  Descr
--    Xylogics T1 communication server with 24 integrated modems and A/B/C
--    connectivity

mtCSmimBri3 OBJECT IDENTIFIER ::= { xylogicsMIMs 14 }
-- OBJECT-IDENTITY
--  Status
--    mandatory
--  Descr
--    Xylogics MIM with 3 ISDN terminal adapters and A/B/C
--    connectivity.

mtCSmimBri6 OBJECT IDENTIFIER ::= { xylogicsMIMs 15 }
-- OBJECT-IDENTITY
--  Status
--    mandatory
--  Descr
--    Xylogics MIM with 6 ISDN terminal adapters and A/B/C
--    connectivity.

mtOlicom OBJECT IDENTIFIER ::= { mtThrdParty 13 }
-- OBJECT-IDENTITY
--  Status
--    mandatory
--  Description
--   Olicom Stackable Token Ring OEM branch.

mtSTS16-20 OBJECT IDENTIFIER ::= { mtOlicom 1 }
-- OBJECT-IDENTITY
--  Status
--    mandatory
--  Descr
--    SmartStack Token Ring Switch from Olicom
--    with 20 RJ-45 UTP/STP ports 4/16 Mb/s.
--    This typecode actually represents a system
--    (STS16-20RM,STS16-20R,STS16-20FRM,STS16-20D).

mtHSTS100-16RM  OBJECT IDENTIFIER ::= { mtOlicom 2 }
-- OBJECT-IDENTITY
--  Status
--    mandatory
--  Descr
--   SmartStack High Speed Token Ring Switch from
--   Olicom with 16 RJ-45 UTP5 ports at 100 Mb/s
--   with optional redundant power supplies and 2
--   modular uplink ports.

mtTPSoftware OBJECT IDENTIFIER ::= { mtThrdParty 14 }
-- OBJECT-IDENTITY
--  Status
--    mandatory
--  Description
--   Third party software packages which actually have
--   mib II interfaces and process packets.

mtBIGIP OBJECT IDENTIFIER ::= { mtTPSoftware 1 }
-- OBJECT-IDENTITY
--  Status
--    mandatory
--  Description
--   F5 Labs OEM Software BIG/IP. This OEM is
--   being handled by Ed Chang (Santa Clara).

mt3DNS OBJECT IDENTIFIER ::= { mtTPSoftware 2 }
-- OBJECT-IDENTITY
--  Status
--    mandatory
--  Description
--   F5 Labs OEM Software 3DNS. This OEM is
--   being handled by Ed Chang (Santa Clara).


mtChassis OBJECT IDENTIFIER ::= { mtExpanded 2 }
-- OBJECT-IDENTITY
--  Status
--    mandatory
--  Descr
--    MID Chassis Cabletron Media Interface Modules

cA OBJECT IDENTIFIER ::= { mtChassis 1 }
-- OBJECT-IDENTITY
--  Status
--    mandatory
--  Descr
--    MID Chassis Cabletron MIMs with A Channel Enet connection

cABorC OBJECT IDENTIFIER ::= { mtChassis 2 }
-- OBJECT-IDENTITY
--  Status
--    mandatory
--  Descr
--    MID Chassis Cabletron MIMs with A, B, or C Enet connection

cABandC OBJECT IDENTIFIER ::= { mtChassis 3 }
-- OBJECT-IDENTITY
--  Status
--    mandatory
--  Descr
--    MID Chassis Cabletron MIMs with A, B, and C Enet connection

cTrFNB OBJECT IDENTIFIER ::= { mtChassis 4 }
-- OBJECT-IDENTITY
--  Status
--    mandatory
--  Descr
--    MID Chassis Cabletron MIMs with Token Ring FNB connection

mtTbrmim OBJECT IDENTIFIER ::= { cTrFNB 1 }
-- OBJECT-IDENTITY
--  Status
--    mandatory
--  Descr
--    Mid chassis Token Ring bridge/router intelligent MIM with
--    4 ports/1 BRIM.

cFDDIFNB OBJECT IDENTIFIER ::= { mtChassis 5 }
-- OBJECT-IDENTITY
--  Status
--    mandatory
--  Descr
--    MID Chassis Cabletron MIMs with FDDI FNB connection

cTrA OBJECT IDENTIFIER ::= { mtChassis 6 }
-- OBJECT-IDENTITY
--  Status
--    mandatory
--  Descr
--    MID Chassis Cabletron MIMs with TR and A channel Ethernet

mtPCMIM OBJECT IDENTIFIER ::= { cTrA 1 }
-- OBJECT-IDENTITY
--  Status
--    mandatory
--  Descr
--    PC 486 on Media Interface Module

cFDDIA OBJECT IDENTIFIER ::= { mtChassis 7 }
-- OBJECT-IDENTITY
--  Status
--    mandatory
--  Descr
--    MID Chassis Cabletron MIMs with FDDI and A Channel Enet connection

cNoABorC OBJECT IDENTIFIER ::= { mtChassis 8 }
-- OBJECT-IDENTITY
--  Status
--    mandatory
--  Descr
--    MID Chassis Cabletron MIMs with no A, B, or C

sonixMIM OBJECT IDENTIFIER ::= { cNoABorC 1 }
-- OBJECT-IDENTITY
--  Status
--    mandatory
--  Descr
--    No Backplane with ISDN and Ethernet on front

mmacFPS OBJECT IDENTIFIER ::= { cNoABorC 2 }
-- OBJECT-IDENTITY
--  Status
--    mandatory
--  Descr
--    MMAC connection for FPS chassis.  This is a 2 MMAC slot
--    module that pulls power and ground from the MMAC chassis.

thirdPartyBrims OBJECT IDENTIFIER ::= { mtChassis 9 }
-- OBJECT-IDENTITY
--  Status
--    mandatory
--  Descr
--    Tree for third party BRIM modules.

mtCiscoBrimE OBJECT IDENTIFIER ::= { thirdPartyBrims 1 }
-- OBJECT-IDENTITY
--  Status
--    mandatory
--  Descr
--    Cisco WAN(2) to Ethernet(1) bridge/router BRIM (CRBRIM-W/E)
--    connecting to Third Party EPIM port taking power only from
--    BRIM connector.

mtCiscoBrimTR OBJECT IDENTIFIER ::= { thirdPartyBrims 11 }
-- OBJECT-IDENTITY
--  Status
--    mandatory
--  Descr
--    Cisco WAN(2) to Token Ring(1) bridge/router BRIM (CRBRIM-W/T)
--    connecting to Third Party TPIM port taking power only from
--    BRIM connector.

mtXylogicsUCS OBJECT IDENTIFIER ::= { thirdPartyBrims 22 }
-- OBJECT-IDENTITY
--  Status
--    mandatory
--  Descr
--    Xylogics Micro CS WAN BRIM with remote access DB for
--    MicroMMAC-E with 12 asynch ports.

mtXylogicsUSnac OBJECT IDENTIFIER ::= { thirdPartyBrims 23 }
-- OBJECT-IDENTITY
--  Status
--    mandatory
--  Descr
--    Xylogics Micro SNAC BRIM with remote access DB for
--    MicroMMAC-E.

mtXylogicsUSnacT OBJECT IDENTIFIER ::= { thirdPartyBrims 24 }
-- OBJECT-IDENTITY
--  Status
--    mandatory
--  Descr
--    Xylogics Micro SNAC BRIM with remote access DB for
--    MicroMMAC-T.

mtXylogicsUBrics OBJECT IDENTIFIER ::= { thirdPartyBrims 25 }
-- OBJECT-IDENTITY
--  Status
--    mandatory
--  Descr
--    Xylogics 3 ISDN terminal adapter module for the MicroMMAC-E.

mtEthernet OBJECT IDENTIFIER ::= { mtExpanded 3 }
-- OBJECT-IDENTITY
--  Status
--    mandatory
--  Descr
--    Ethernet Products using 3 registers

mtEtherA OBJECT IDENTIFIER ::= { mtEthernet 1 }
-- OBJECT-IDENTITY
--  Status
--    mandatory
--  Descr
--    Ethernet A Channel

mtEtherRic OBJECT IDENTIFIER ::= { mtEthernet 2 }
-- OBJECT-IDENTITY
--  Status
--    mandatory
--  Descr
--    Ethernet Ric Based MIMs

mtEtherEPIM OBJECT IDENTIFIER ::= { mtEthernet 3 }
-- OBJECT-IDENTITY
--  Status
--    mandatory
--  Descr
--    Ethernet EPIMs

mtEtherStandAlone OBJECT IDENTIFIER ::= { mtEthernet 4 }
-- OBJECT-IDENTITY
--  Status
--    mandatory
--  Descr
--    Ethernet Standalone Devices

mtUMMAC22E OBJECT IDENTIFIER ::= { mtEtherStandAlone 1 }
-- OBJECT-IDENTITY
--  Status
--    mandatory
--  Descr
--    12 Port 10BT RF45 with 1 EPIM & 1 BRIM

mtUMMAC32E OBJECT IDENTIFIER ::= { mtEtherStandAlone 2 }
-- OBJECT-IDENTITY
--  Status
--    mandatory
--  Descr
--    12 Port 10BT 1 50 Pin with 2 EPIMs and 1 BRIM

mtUMMAC24E OBJECT IDENTIFIER ::= { mtEtherStandAlone 3 }
-- OBJECT-IDENTITY
--  Status
--    mandatory
--  Descr
--    24 Port 10BT 24 RJ45 with 1 EPIM & BRIM

mtUMMAC34E OBJECT IDENTIFIER ::= { mtEtherStandAlone 4 }
-- OBJECT-IDENTITY
--  Status
--    mandatory
--  Descr
--    24 Port 10BT 2x50 Pin with 2 EPIMs and BRIMs

mtSEH22 OBJECT IDENTIFIER ::= { mtEtherStandAlone 5 }
-- OBJECT-IDENTITY
--  Status
--    mandatory
--  Descr
--    12 Port 10BT RJ45 with 1 EPIM Non-Intel

mtSEH32 OBJECT IDENTIFIER ::= { mtEtherStandAlone 6 }
-- OBJECT-IDENTITY
--  Status
--    mandatory
--  Descr
--    12 Port 10BT 1x50 Pin with 1 EPIM Non-Intel

mtSEH24 OBJECT IDENTIFIER ::= { mtEtherStandAlone 7 }
-- OBJECT-IDENTITY
--  Status
--    mandatory
--  Descr
--    24 Port 10BT RJ45 with 2 EPIM Non-Intel

mtSEH34 OBJECT IDENTIFIER ::= { mtEtherStandAlone 8 }
-- OBJECT-IDENTITY
--  Status
--    mandatory
--  Descr
--    24 Port 10BT 2x50 Pin with 2 EPIMs Non-Intel

mtNBR620 OBJECT IDENTIFIER ::= { mtEtherStandAlone 9 }
-- OBJECT-IDENTITY
--  Status
--    mandatory
--  Descr
--    Standalone EMM-E6

mtSEHi22 OBJECT IDENTIFIER ::= { mtEtherStandAlone 10 }
-- OBJECT-IDENTITY
--  Status
--    mandatory
--  Descr
--    Stackable Ethernet HUB Intelligent with 12 RJ45s and 1 EPIM

mtSEHi24 OBJECT IDENTIFIER ::= { mtEtherStandAlone 11 }
-- OBJECT-IDENTITY
--  Status
--    mandatory
--  Descr
--    Stackable Ethernet HUB Intelligent with 24 RJ45s and 2 EPIMs

mtSEHi26FB OBJECT IDENTIFIER ::= { mtEtherStandAlone 12 }
-- OBJECT-IDENTITY
--  Status
--    mandatory
--  Descr
--    6 port 10Base-FB

mtSEHi22FB OBJECT IDENTIFIER ::= { mtEtherStandAlone 13 }
-- OBJECT-IDENTITY
--  Status
--    mandatory
--  Descr
--    12 port 10Base-FB

mtSEHi32 OBJECT IDENTIFIER ::= { mtEtherStandAlone 14 }
-- OBJECT-IDENTITY
--  Status
--    mandatory
--  Descr
--    Stackable Ethernet HUB Intelligent with 1 50 Pin Telco and 1 EPIM

mtSEHi34 OBJECT IDENTIFIER ::= { mtEtherStandAlone 15 }
-- OBJECT-IDENTITY
--  Status
--    mandatory
--  Descr
--    Stackable Ethernet HUB Intelligent with 22 50 Pin Telcos and 2 EPIMs

mtSEH26C OBJECT IDENTIFIER ::= { mtEtherStandAlone 16 }
-- OBJECT-IDENTITY
--  Status
--    mandatory
--  Descr
--    6 Port 10Base-2 with 1 EPIM

mtSEH22C OBJECT IDENTIFIER ::= { mtEtherStandAlone 17 }
-- OBJECT-IDENTITY
--  Status
--    mandatory
--  Descr
--    12 Port 10Base-2 with 1 EPIM

mtSEH26FL OBJECT IDENTIFIER ::= { mtEtherStandAlone 18 }
-- OBJECT-IDENTITY
--  Status
--    mandatory
--  Descr
--    6 Port 10Base-FL with 1 EPIM

mtSEH22FL OBJECT IDENTIFIER ::= { mtEtherStandAlone 19 }
-- OBJECT-IDENTITY
--  Status
--    mandatory
--  Descr
--    12 Port 10Base-FL with 1 EPIM

mtUMMAC26FL OBJECT IDENTIFIER ::= { mtEtherStandAlone 20 }
-- OBJECT-IDENTITY
--  Status
--    mandatory
--  Descr
--    6 Port 10Base-FL with 1 EPIM

mtUMMAC22FL OBJECT IDENTIFIER ::= { mtEtherStandAlone 21 }
-- OBJECT-IDENTITY
--  Status
--    mandatory
--  Descr
--    12 Port 10Base-FL with 1 EPIM

mtNBR220 OBJECT IDENTIFIER ::= { mtEtherStandAlone 22 }
-- OBJECT-IDENTITY
--  Status
--    mandatory
--  Descr
--    2 Port Bridge with EPIMs

mtNBR420 OBJECT IDENTIFIER ::= { mtEtherStandAlone 23 }
-- OBJECT-IDENTITY
--  Status
--    mandatory
--  Descr
--    2 Port Bridge with EPIMs and 2 BRIMs

mtSEH22S OBJECT IDENTIFIER ::= { mtEtherStandAlone 24 }
-- OBJECT-IDENTITY
--  Status
--    mandatory
--  Descr
--    Secure 12 Port 10BT RJ45 with 1 EPIM Non-Intel

mtSEH32S OBJECT IDENTIFIER ::= { mtEtherStandAlone 25 }
-- OBJECT-IDENTITY
--  Status
--    mandatory
--  Descr
--    Secure 12 Port 10BT 1x50 Pin with 1 EPIM Non-Intel

mtSEH24S OBJECT IDENTIFIER ::= { mtEtherStandAlone 26 }
-- OBJECT-IDENTITY
--  Status
--    mandatory
--  Descr
--    Secure 24 Port 10BT RJ45 with 2 EPIM Non-Intel

mtSEH34S OBJECT IDENTIFIER ::= { mtEtherStandAlone 27 }
-- OBJECT-IDENTITY
--  Status
--    mandatory
--  Descr
--    Secure 24 Port 10BT 2x50 Pin with 2 EPIMs Non-Intel

mtSEH26FBS OBJECT IDENTIFIER ::= { mtEtherStandAlone 28 }
-- OBJECT-IDENTITY
--  Status
--    mandatory
--  Descr
--    Secure 6 port 10Base-FB

mtSEH22FBS OBJECT IDENTIFIER ::= { mtEtherStandAlone 29 }
-- OBJECT-IDENTITY
--  Status
--    mandatory
--  Descr
--    Secure 12 port 10Base-FB

mtSEH26CS OBJECT IDENTIFIER ::= { mtEtherStandAlone 30 }
-- OBJECT-IDENTITY
--  Status
--    mandatory
--  Descr
--    Secure 6 Port 10Base-2 with 1 EPIM

mtSEH22CS OBJECT IDENTIFIER ::= { mtEtherStandAlone 31 }
-- OBJECT-IDENTITY
--  Status
--    mandatory
--  Descr
--    Secure 12 Port 10Base-2 with 1 EPIM

mtSEH26FLS OBJECT IDENTIFIER ::= { mtEtherStandAlone 32 }
-- OBJECT-IDENTITY
--  Status
--    mandatory
--  Descr
--    Secure 6 Port 10Base-FL with 1 EPIM

mtSEH22FLS OBJECT IDENTIFIER ::= { mtEtherStandAlone 33 }
-- OBJECT-IDENTITY
--  Status
--    mandatory
--  Descr
--    Secure 12 Port 10Base-FL with 1 EPIM

mtSEHi22S OBJECT IDENTIFIER ::= { mtEtherStandAlone 34 }
-- OBJECT-IDENTITY
--  Status
--    mandatory
--  Descr
--    Stackable Secure Ethernet HUB Intelligent with 12 RJ45s and 1 EPIM

mtSEHi24S OBJECT IDENTIFIER ::= { mtEtherStandAlone 35 }
-- OBJECT-IDENTITY
--  Status
--    mandatory
--  Descr
--    Stackable secure Ethernet HUB Intelligent with 24 RJ45s and 2 EPIMs

mtSEHi32S OBJECT IDENTIFIER ::= { mtEtherStandAlone 36 }
-- OBJECT-IDENTITY
--  Status
--    mandatory
--  Descr
--    Stackable Secure Ethernet HUB Intelligent with 1 50 Pin Telco
--    and 1 EPIM

mtSEHi34S OBJECT IDENTIFIER ::= { mtEtherStandAlone 37 }
-- OBJECT-IDENTITY
--  Status
--    mandatory
--  Descr
--    Stackable Secure Ethernet HUB Intelligent with 22 50 Pin Telcos
--    and 2 EPIMs

mtUMMAC22ES OBJECT IDENTIFIER ::= { mtEtherStandAlone 38 }
-- OBJECT-IDENTITY
--  Status
--    mandatory
--  Descr
--    Secure 12 Port 10BT RF45 with 1 EPIM & 1 BRIM

mtUMMAC32ES OBJECT IDENTIFIER ::= { mtEtherStandAlone 39 }
-- OBJECT-IDENTITY
--  Status
--    mandatory
--  Descr
--    Secure 12 Port 10BT 1 50 Pin with 2 EPIMs and 1 BRIM

mtUMMAC24ES OBJECT IDENTIFIER ::= { mtEtherStandAlone 40 }
-- OBJECT-IDENTITY
--  Status
--    mandatory
--  Descr
--    Secure 24 Port 10BT 24 RJ45 with 1 EPIM & BRIM

mtUMMAC34ES OBJECT IDENTIFIER ::= { mtEtherStandAlone 41 }
-- OBJECT-IDENTITY
--  Status
--    mandatory
--  Descr
--    Secure 24 Port 10BT 2x50 Pin with 2 EPIMs and BRIMs

mtUMMAC22UCSs OBJECT IDENTIFIER ::= { mtEtherStandAlone 42 }
-- OBJECT-IDENTITY
--  Status
--    mandatory
--  Descr
--    MicroMMAC-22E Secure with Micro-CS.

mtUMMAC22EUCS OBJECT IDENTIFIER ::= { mtEtherStandAlone 43 }
-- OBJECT-IDENTITY
--  Status
--    mandatory
--  Descr
--    MicroMMAC-22E with Micro-CS.

mtUMMAC22UCSsSnac OBJECT IDENTIFIER ::= { mtEtherStandAlone 44 }
-- OBJECT-IDENTITY
--  Status
--    mandatory
--  Descr
--    MicroMMAC-22E secure with Micro-SNAC.

mtUMMAC22EUCSSnac OBJECT IDENTIFIER ::= { mtEtherStandAlone 45 }
-- OBJECT-IDENTITY
--  Status
--    mandatory
--  Descr
--    MicroMMAC-22E with Micro-SNAC.

mtUMMAC22EBrics OBJECT IDENTIFIER ::= { mtEtherStandAlone 46 }
-- OBJECT-IDENTITY
--  Status
--    mandatory
--  Descr
--    MicroMMAC-22E with Xylogics Brics adapter which has 3 ISDN
--    terminal adapters.

mtUMMAC22ESBrics OBJECT IDENTIFIER ::= { mtEtherStandAlone 47 }
-- OBJECT-IDENTITY
--  Status
--    mandatory
--  Descr
--    MicroMMAC-22E secure with Xylogics Brics adapter which has
--    3 ISDN terminal adapters.

mtESX1320 OBJECT IDENTIFIER ::= { mtEtherStandAlone 48 }
-- OBJECT-IDENTITY
--  Status
--    mandatory
--  Descr
--    Standalone ethernet switch with 12 RJ45 ports and 1 Brim
--    connector.

mtESX1380 OBJECT IDENTIFIER ::= { mtEtherStandAlone 49 }
-- OBJECT-IDENTITY
--  Status
--    mandatory
--  Descr
--    Standalone ethernet switch with 12 ST fiber optic ports
--    and 1 Brim connector.

mtSEHi22FLS OBJECT IDENTIFIER ::= { mtEtherStandAlone 50 }
-- OBJECT-IDENTITY
--  Status
--    mandatory
--  Descr
--    Stackable Secure Ethernet HUB Intelligent with 6 10Base-FL ports
--    and 1 EPIM

mtSEHi26FLS OBJECT IDENTIFIER ::= { mtEtherStandAlone 51 }
-- OBJECT-IDENTITY
--  Status
--    mandatory
--  Descr
--    Stackable Secure Ethernet HUB Intelligent with 12 10Base-FL ports
--    and 1 EPIM

mtSEHi22FL OBJECT IDENTIFIER ::= { mtEtherStandAlone 52 }
-- OBJECT-IDENTITY
--  Status
--    mandatory
--  Descr
--    Stackable Ethernet HUB Intelligent with 6 10Base-FL ports
--    and 1 EPIM

mtSEHi26FL OBJECT IDENTIFIER ::= { mtEtherStandAlone 53 }
-- OBJECT-IDENTITY
--  Status
--    mandatory
--  Descr
--    Stackable Ethernet HUB Intelligent with 12 10Base-FL ports
--    and 1 EPIM

mtSEH100Tx22 OBJECT IDENTIFIER ::= { mtEtherStandAlone 54 }
-- OBJECT-IDENTITY
--  Status
--    mandatory
--  Descr
--    Stackable Fast Ethernet class I non-intelligent repeater.
--    With 22 100BaseTX (RJ45) ports with one EPIM slot.

mtSEHi100Tx22 OBJECT IDENTIFIER ::= { mtEtherStandAlone 55 }
-- OBJECT-IDENTITY
--  Status
--    mandatory
--  Descr
--    Stackable Fast Ethernet class I Intelligent repeater.
--    With 22 100BaseTX (RJ45) ports with one EPIM slot.

mt8H02p16 OBJECT IDENTIFIER ::= { mtEtherStandAlone 56 }
-- OBJECT-IDENTITY
--  Status
--    mandatory
--  Descr
--    Standalone ethernet switch module supporting 14 front
--    panel RJ45 connectors, and two optional FE-100XX
--    modules.

mt2E42p27 OBJECT IDENTIFIER ::= { mtEtherStandAlone 57 }
-- OBJECT-IDENTITY
--  Status
--    mandatory
--  Descr
--    Standalone ethernet SmartSwitch with 24 front panel
--    RJ45 ports, 2 FE-100XX slots and one HSIM (High
--    Speed Interface Module) slot.

mt2E42p27R OBJECT IDENTIFIER ::= { mtEtherStandAlone 58 }
-- OBJECT-IDENTITY
--  Status
--    mandatory
--  Descr
--    Standalone ethernet SmartSwitch with 24 front panel
--    RJ45 ports, 2 FE-100XX slots and one HSIM (High
--    Speed Interface Module) slot. With redundant power supplies.

mt2E43p27 OBJECT IDENTIFIER ::= { mtEtherStandAlone 59 }
-- OBJECT-IDENTITY
--  Status
--    mandatory
--  Descr
--    Standalone ethernet SmartSwitch with 24 front panel
--    RJ21 ports, 2 FE-100XX slots and one HSIM (High Speed
--    Interface Module) slot.

mt2E43p27R OBJECT IDENTIFIER ::= { mtEtherStandAlone 60 }
-- OBJECT-IDENTITY
--  Status
--    mandatory
--  Descr
--    Standalone ethernet SmartSwitch with 24 front panel
--    RJ21 ports, 2 FE-100XX slots and one HSIM (High Speed
--    Interface Module) slot. This will have redunant power
--    supplies.

mt2E43p51 OBJECT IDENTIFIER ::= { mtEtherStandAlone 61 }
-- OBJECT-IDENTITY
--  Status
--    mandatory
--  Descr
--    Standalone chassis with 4 12-port repeated segments,
--    2 fast ethernet FEPIM ports and 1 HSIM port.

mt2E43p51R OBJECT IDENTIFIER ::= { mtEtherStandAlone 62 }
-- OBJECT-IDENTITY
--  Status
--    mandatory
--  Descr
--    Standalone chassis with 4 12-port repeated segments,
--    2 fast ethernet FEPIM ports and 1 HSIM port. This
--    will have redundant power supplies.

mt2H43p51 OBJECT IDENTIFIER ::= { mtEtherStandAlone 63 }
-- OBJECT-IDENTITY
-- Status
--    deprecated
-- Descr
--     Standalone chassis with 4 10Mbs segments of up to 12 repeated ports,
--     4 100Mbs segments of up to 12 repeated ports, two FE-PIM slots and
--     an HSIM slot. Each repeated port is autosensing, as to the
--     connection speed, so within each 12 port group there can be a mixture
--     of 10Mbs and 100Mbs.

mt2H43p51R OBJECT IDENTIFIER ::= { mtEtherStandAlone 64 }
-- OBJECT-IDENTITY
-- Status
--    deprecated
-- Descr
--     Standalone chassis with 4 10Mbs segments of up to 12 repeated ports,
--     4 100Mbs segments of up to 12 repeated ports, two FE-PIM slots and
--     an HSIM slot. Each repeated port is autosensing, as to the
--     connection speed, so within each 12 port group there can be a mixture
--     of 10Mbs and 100Mbs. This will have redundant power supplies.

mt2E42p27RDC OBJECT IDENTIFIER ::= { mtEtherStandAlone 65 }
-- OBJECT-IDENTITY
--  Status
--    mandatory
--  Descr
--    Standalone ethernet SmartSwitch with 24 front panel
--    RJ45 ports, 2 FE-100XX slots and one HSIM (High Speed
--    Interface Module) slot.  Redundant DC power supplies.

mt2E42p27DC OBJECT IDENTIFIER ::= { mtEtherStandAlone 66 }
-- OBJECT-IDENTITY
--  Status
--    mandatory
--  Descr
--    Standalone ethernet SmartSwitch with 24 front panel
--    RJ45 ports, 2 FE-100XX slots and one HSIM (High Speed
--    Interface Module) slot. Distributed Chassis version.

mt2M46p04 OBJECT IDENTIFIER ::= { mtEtherStandAlone 67 }
-- OBJECT-IDENTITY
--  Status
--    mandatory
--  Descr
--    SmartSwitch 2200 with 2 HSIM slots and 2 Fast Ethernet
--    ports (uses FEPIMs)

mt2E48p27R OBJECT IDENTIFIER ::= { mtEtherStandAlone 68 }
-- OBJECT-IDENTITY
-- Status
--    mandatory
-- Descr
--    Redundant powered Standalone SmartSwitch with 24 Multimode fiber
--    10Base-FL switch ports (via ST connectors) with one optional HSIM
--    port and two optional FE-PIM ports.

mt2E48p27 OBJECT IDENTIFIER ::= { mtEtherStandAlone 69 }
-- OBJECT-IDENTITY
-- Status
--    mandatory
-- Descr
--    Standalone SmartSwitch with 24 Multimode fiber 10Base-FL
--    switch ports (via ST connectors) with one optional HSIM port and
--    two optional FE-PIM ports.

mt2E49p27 OBJECT IDENTIFIER ::= { mtEtherStandAlone 70 }
-- OBJECT-IDENTITY
-- Status
--    mandatory
-- Descr
--    Standalone SmartSwitch with 24 fixed single-mode fiber 10Mb
--    switched ports (via ST connectors) with one optional HSIM port and
--    two optional 100BaseX FE-PIM ports.

mt2E49p27R OBJECT IDENTIFIER ::= { mtEtherStandAlone 71 }
-- OBJECT-IDENTITY
-- Status
--    mandatory
-- Descr
--    Redundant powered Standalone SmartSwitch with 24 fixed single-mode
--    fiber 10Mb switched ports (via ST connectors) with one optional
--    HSIM port and two optional 100BaseX FE-PIM ports.

mt2E49p27RDC OBJECT IDENTIFIER ::= { mtEtherStandAlone 72 }
-- OBJECT-IDENTITY
-- Status
--    mandatory
-- Descr
--    Redundant powered Standalone SmartSwitch with 24 fixed single-mode
--    fiber 10Mb switched ports (via ST connectors) with one optional
--    HSIM port and two optional 100BaseX FE-PIM ports. Distributed
--    Chassis version.

mt2M46p04R OBJECT IDENTIFIER ::= { mtEtherStandAlone 73 }
-- OBJECT-IDENTITY
--  Status
--    mandatory
--  Descr
--    SmartSwitch 2200 with 2 HSIM slots and 2 Fast Ethernet
--    ports (uses FEPIMs), and redundant power.

mt2M46p04RDC OBJECT IDENTIFIER ::= { mtEtherStandAlone 74 }
-- OBJECT-IDENTITY
--  Status
--    mandatory
--  Descr
--    SmartSwitch 2200 with 2 HSIM slots and 2 Fast Ethernet
--    ports (uses FEPIMs), and DC redundant power.

mt2H28p08R OBJECT IDENTIFIER ::= { mtEtherStandAlone 75 }
-- OBJECT-IDENTITY
--  Status
--    mandatory
--  Descr
--    Redundant powered standalone SmartSwitch with 6 fixed
--    multi-mode fiber 100BaseF switched ports (via SC onnectors) and
--    2 optional FE100-XX ports.

mt2H22p08R OBJECT IDENTIFIER ::= { mtEtherStandAlone 76 }
-- OBJECT-IDENTITY
--  Status
--    mandatory
--  Descr
--    Redundant powered standalone SmartSwitch with 6 fixed
--    RJ45 10BaseT/100BaseTX switched ports (via SC connectors) and
--    2 optional FE100-XX ports.

mt2H23p50R OBJECT IDENTIFIER ::= { mtEtherStandAlone 77 }
-- OBJECT-IDENTITY
--  Status
--    mandatory
--  Descr
--    48 port MicroLAN Standalone (4 RJ21 connectors) with two
--    optional FE-PIM slots.  Redundant power supplies.

mt2H33p37R OBJECT IDENTIFIER ::= { mtEtherStandAlone 78 }
-- OBJECT-IDENTITY
--  Status
--    mandatory
--  Descr
--    36 port MicroLAN Standalone (3 RJ21 connectors) with one
--    optional HSIM slot.  Redundant power supplies.

mt2H252p25 OBJECT IDENTIFIER ::= { mtEtherStandAlone 79 }
-- OBJECT-IDENTITY
--  Status
--    mandatory
--  Descr
--    24 port Standalone workgroup Smartswitch with 24 10/100 Switch
--    ports and one optional VHSIM slot.

mt2H252p25R OBJECT IDENTIFIER ::= { mtEtherStandAlone 80 }
-- OBJECT-IDENTITY
--  Status
--    mandatory
--  Descr
--    24 port Standalone workgroup Smartswitch with 24 10/100 Switch
--    ports and one optional VHSIM slot.  Redundant power supplies.

mt2M256p04R OBJECT IDENTIFIER ::= { mtEtherStandAlone 81 }
-- OBJECT-IDENTITY
--  Status
--    mandatory
--  Descr
--    SmartSwitch 2200 with 2 VHSIM/HSIM slots and 2 Fast Ethernet
--    ports (uses FEPIMs).  Redundant power supplies.

mt2E253p49R OBJECT IDENTIFIER ::= { mtEtherStandAlone 82 }
-- OBJECT-IDENTITY
--  Status
--    mandatory
--  Descr
--    SmartSwitch 2200 with 48 10 Meg ports with 1 optional VHSIM
--    slot.  Redundant power supplies.

mt2H258p17R OBJECT IDENTIFIER ::= { mtEtherStandAlone 83 }
-- OBJECT-IDENTITY
--  Status
--    mandatory
--  Descr
--    SmartSwitch 2200 with 16 Multimode fiber 100BaseFX switched
--    ports (MT RJ connectors) with 1 optional VHSIM
--    slot.  Redundant power supplies.

mt2H253p25R OBJECT IDENTIFIER ::= { mtEtherStandAlone 84 }
-- OBJECT-IDENTITY
--  Status
--    mandatory
--  Descr
--    SmartSwitch 2200 with 24 10/100 BaseTX switched ports
--    (Telco RJ21 connector) with 1 optional VHSIM
--    slot.  Redundant power supplies.

mt2H252p25RDC OBJECT IDENTIFIER ::= { mtEtherStandAlone 85 }
-- OBJECT-IDENTITY
--  Status
--    mandatory
--  Descr
--    24 port Standalone workgroup Smartswitch with 24 10/100 Switch
--    ports and one optional VHSIM slot.  Redundant DC power supplies.

mt2H259p17R OBJECT IDENTIFIER ::= { mtEtherStandAlone 86 }
-- OBJECT-IDENTITY
--  Status
--    mandatory
--  Descr
--    SmartSwitch 2200 with 16 Singlemode fiber 100BaseFX switched
--    ports (MT RJ connectors) with 1 optional VHSIM
--    slot.  Redundant power supplies.

mtELS10082F2 OBJECT IDENTIFIER ::= { mtEtherStandAlone 87 }
-- OBJECT-IDENTITY
--  Status
--    mandatory
--  Descr
--    SmartStack with 8 RJ45 10/100 ports with 2 MultiMode
--    MTRJ Fiber ports.

-- mtELS1008TX OBJECT IDENTIFIER ::= { mtEtherStandAlone 88 }
-- OBJECT-IDENTITY
--  Status
--    mandatory
--  Descr
--    SmartStack with 8 RJ45 10/100 ports with no uplink.

-- mtELS10081F2 OBJECT IDENTIFIER ::= { mtEtherStandAlone 89 }
-- OBJECT-IDENTITY
--  Status
--    mandatory
--  Descr
--    SmartStack with 8 RJ45 10/100 ports with 1 MultiMode
--    MTRJ Fiber ports.

-- mtELS10081F3 OBJECT IDENTIFIER ::= { mtEtherStandAlone 90 }
-- OBJECT-IDENTITY
--  Status
--    mandatory
--  Descr
--    SmartStack with 8 RJ45 10/100 ports with 1 SingleMode
--    MTRJ Fiber ports.

-- mtELS10082F3 OBJECT IDENTIFIER ::= { mtEtherStandAlone 91 }
-- OBJECT-IDENTITY
--  Status
--    mandatory
--  Descr
--    SmartStack with 8 RJ45 10/100 ports with two SingleMode
--    MTRJ Fiber ports.

mtELS10024TX2M OBJECT IDENTIFIER ::= { mtEtherStandAlone 92 }
-- OBJECT-IDENTITY
--  Status
--    mandatory
--  Descr
--    SmartStack with 24 RJ45 10/100 ports with two expansion
--    slots.

mtELS10024FX2M OBJECT IDENTIFIER ::= { mtEtherStandAlone 93 }
-- OBJECT-IDENTITY
--  Status
--    mandatory
--  Descr
--    SmartStack with 24 MTRJ Multimode ports with two expansion
--    slots.

mtELS10048TX2M OBJECT IDENTIFIER ::= { mtEtherStandAlone 94 }
-- OBJECT-IDENTITY
--  Status
--    mandatory
--  Descr
--    SmartStack with 48 RJ45 10/100 ports with two expansion
--    slots.

mtELS10008SX1M OBJECT IDENTIFIER ::= { mtEtherStandAlone 95 }
-- OBJECT-IDENTITY
--  Status
--    mandatory
--  Descr
--    SmartStack with 8 1000 Base SX  ports with one expansion
--    slot.

mtELS100012SX2M OBJECT IDENTIFIER ::= { mtEtherStandAlone 96 }
-- OBJECT-IDENTITY
--  Status
--    mandatory
--  Descr
--    SmartStack with 12 1000 Base SX ports with two expansion
--    slots.

mtELS10016FXG  OBJECT IDENTIFIER ::= { mtEtherStandAlone 97 }
-- OBJECT-IDENTITY
--  Status
--    mandatory
--  Descr
--     SmartStack with 16 port MTRJ Multimode fiber and 2 Modular
--     Gigabit uplinks.

mtELS100024TX2MA OBJECT IDENTIFIER ::= { mtEtherStandAlone 98 }
-- OBJECT-IDENTITY
--  Status
--    mandatory
--  Descr
--    SmartStack with 24 RJ45 10/100 Fast Ethernet ports with two expansion
--    modules.

mtELS10024TX1M OBJECT IDENTIFIER ::= { mtEtherStandAlone 99 }
-- OBJECT-IDENTITY
--  Status
--    mandatory
--  Descr
--    SmartStack with 24 RJ45 10/100 Ethernet ports with 1 modular slot that
--    can accept 2 or 4 port 100BaseFX module or 2 GBIC port module.

etherSlot1 OBJECT IDENTIFIER ::= { mtEthernet 5 }
-- OBJECT-IDENTITY
--  Status
--    mandatory
--  Descr
--    Ethernet First Slot Devices

mtEMME6 OBJECT IDENTIFIER ::= { etherSlot1 1 }
-- OBJECT-IDENTITY
--  Status
--    mandatory
--  Descr
--    EMME with 2 BRIM Ports

mtEnetBrim OBJECT IDENTIFIER ::= { mtEthernet 6 }
-- OBJECT-IDENTITY
--  Status
--    mandatory
--  Descr
--    Ethernet BRIMs

mtBrimUnk OBJECT IDENTIFIER ::= { mtEnetBrim 1 }
-- OBJECT-IDENTITY
--  Status
--    mandatory
--  Descr
--    Unknown ethernet BRIM type.

mtBrimE6 OBJECT IDENTIFIER ::= { mtEnetBrim 2 }
-- OBJECT-IDENTITY
--  Status
--    mandatory
--  Descr
--    Ethernet BRIM with 1 EPIM port

mt100MBEnet OBJECT IDENTIFIER ::= { mtEthernet 7 }
-- OBJECT-IDENTITY
--  Status
--    mandatory
--  Descr
--    100 Mega Bit Ethernet products.

mtBrimE100 OBJECT IDENTIFIER ::= { mt100MBEnet 1 }
-- OBJECT-IDENTITY
--  Status
--    mandatory
--  Descr
--    A 100 MB Ethernet BRIM with single EPIM, accepting
--    FE100xx modules.

mtmmacEthernetSmartSwitch OBJECT IDENTIFIER ::= { mtEthernet 8 }
-- OBJECT-IDENTITY
--  Status
--    mandatory
--  Descr
--    MMAC Ethernet SmartSwitch products branch

mtSmartMIM216 OBJECT IDENTIFIER ::= { mtmmacEthernetSmartSwitch 1 }
-- OBJECT-IDENTITY
--  Status
--    mandatory
--  Descr
--    A SmartSwitch MIM with 14 10Base-T ports and two FE-100
--    PIM slots.

mtEnetHSIM OBJECT IDENTIFIER ::= { mtEthernet 9 }
-- OBJECT-IDENTITY
--  Status
--    mandatory
--  Descr
--    MMAC Ethernet HSIMs

mtHSIMpG01 OBJECT IDENTIFIER ::= { mtEnetHSIM 1 }
-- OBJECT-IDENTITY
--  Status
--    mandatory
--  Descr
--    1 port Gigabit Ethernet High Speed Interface Module (SmartSwitch
--    product). The 1000Base-SX interface on the front panel uses an SC
--    connector supporting multimode fiber. The laser is an 850 nanometer
--    optical laser.

mtHSIMpG09 OBJECT IDENTIFIER ::= { mtEnetHSIM 2 }
-- OBJECT-IDENTITY
--  Status
--    mandatory
--  Descr
--    1 port Gigabit Ethernet High Speed Interface Module (SmartSwitch
--    product). The 1000Base-LX interface on the front panel uses an SC
--    connector supporting Single or multi-mode fiber. The laser is a
--    1300 nanometer optical laser.

mtHSIMFE6 OBJECT IDENTIFIER ::= { mtEnetHSIM 3 }
-- OBJECT-IDENTITY
--  Status
--    mandatory
--  Descr
--   2 port Fast Ethernet High Speed Interface Module (SmartSwitch
--   product  with 2 FEPIM connectors.

mtVHSIMG6 OBJECT IDENTIFIER ::= { mtEnetHSIM 4 }
-- OBJECT-IDENTITY
--  Status
--    mandatory
--  Descr
--    2 port Gigabit Ethernet Very High Speed Interface Module (SmartSwitch
--    product) with 2 GPIM (hot-swappable) connectors.

mtEnetRepeater OBJECT IDENTIFIER ::= { mtExpanded 4 }
-- OBJECT-IDENTITY
--  Status
--    mandatory
--  Descr
--    Ethernet repeater MIMs.

mtEnetABC OBJECT IDENTIFIER ::= { mtEnetRepeater 1 }
-- OBJECT-IDENTITY
--  Status
--    mandatory
--  Descr
--    Ethernet MIMs resident on A or B or C.

mtTPXMIM20 OBJECT IDENTIFIER ::= { mtEnetABC 1 }
-- OBJECT-IDENTITY
--  Status
--    mandatory
--  Descr
--    9 RJ45s 10Base-T with one EPIM

mtTPXMIM22 OBJECT IDENTIFIER ::= { mtEnetABC 2 }
-- OBJECT-IDENTITY
--  Status
--    mandatory
--  Descr
--    21 RJ45s 10Base-T with one EPIM

mtTPXMIM33 OBJECT IDENTIFIER ::= { mtEnetABC 3 }
-- OBJECT-IDENTITY
--  Status
--    mandatory
--  Descr
--    One 50 pin telco 10Base-T with one EPIM

mtTPXMIM34 OBJECT IDENTIFIER ::= { mtEnetABC 4 }
-- OBJECT-IDENTITY
--  Status
--    mandatory
--  Descr
--    Two 50 pin telcos 10Base-T with one EPIM

mtTpxmim20S OBJECT IDENTIFIER ::= { mtEnetABC 5 }
-- OBJECT-IDENTITY
--  Status
--    mandatory
--  Descr
--    9 RJ45s 10Base-T with one EPIM all ports support
--    LANVIEW/SECURE.

mtTpxmim22S OBJECT IDENTIFIER ::= { mtEnetABC 6 }
-- OBJECT-IDENTITY
--  Status
--    mandatory
--  Descr
--    21 RJ45s 10Base-T with one EPIM all ports
--    support LANVIEW/SECURE.

mtTpxmim33S OBJECT IDENTIFIER ::= { mtEnetABC 7 }
-- OBJECT-IDENTITY
--  Status
--    mandatory
--  Descr
--    1 50 PIN Telcos 10Base-T with EPIM all ports
--    support LANVIEW/SECURE.

mtTpxmim34S OBJECT IDENTIFIER ::= { mtEnetABC 8 }
-- OBJECT-IDENTITY
--  Status
--    mandatory
--  Descr
--    2 50 PIN Telcos 10Base-T with EPIM all ports
--    support LANVIEW/SECURE.

mtTokenRing OBJECT IDENTIFIER ::= { mtExpanded 5 }
-- OBJECT-IDENTITY
--  Status
--    mandatory
--  Descr
--    The Token Ring Product branch

mtTRActive OBJECT IDENTIFIER ::= { mtTokenRing 1 }
-- OBJECT-IDENTITY
--  Status
--    mandatory
--  Descr
--    Fiber based active token ring MIMs

mtTRMIM22A OBJECT IDENTIFIER ::= { mtTRActive 1 }
-- OBJECT-IDENTITY
--  Status
--    mandatory
--  Descr
--    Active MIM with 12 UTP ports with ring out.

mtTRMIM24A OBJECT IDENTIFIER ::= { mtTRActive 2 }
-- OBJECT-IDENTITY
--  Status
--    mandatory
--  Descr
--    Active MIM with 24 UTP ports with ring out.

mtTRMIM42A OBJECT IDENTIFIER ::= { mtTRActive 3 }
-- OBJECT-IDENTITY
--  Status
--    mandatory
--  Descr
--    Active MIM with 12 STP ports with ring out.

mtTRMIM44A OBJECT IDENTIFIER ::= { mtTRActive 4 }
-- OBJECT-IDENTITY
--  Status
--    mandatory
--  Descr
--    Active MIM with 24 STP ports with ring out.

mtTRFMIM32 OBJECT IDENTIFIER ::= { mtTRActive 5 }
-- OBJECT-IDENTITY
--  Status
--    mandatory
--  Descr
--    12 port with ST single mode fiber.

mtTRFMIM36 OBJECT IDENTIFIER ::= { mtTRActive 6 }
-- OBJECT-IDENTITY
--  Status
--    mandatory
--  Descr
--    6 port with ST single mode fiber.

mtTRFMIM38 OBJECT IDENTIFIER ::= { mtTRActive 7 }
-- OBJECT-IDENTITY
--  Status
--    mandatory
--  Descr
--    18 port with ST single mode fiber.

mtTRRepeater OBJECT IDENTIFIER ::= { mtTokenRing 2 }
-- OBJECT-IDENTITY
--  Status
--    mandatory

mtTRRMIMf2t OBJECT IDENTIFIER ::= { mtTRRepeater 1 }
-- OBJECT-IDENTITY
--  Status
--    mandatory
--  Descr
--    repeater with 6 multimode stations and TPIMs for Ring-In/Ring-Out

mtTRRMIMf3t OBJECT IDENTIFIER ::= { mtTRRepeater 2 }
-- OBJECT-IDENTITY
--  Status
--    mandatory
--  Descr
--    repeater with 6 singlemode stations and TPIMs for Ring-In/Ring-Out

mtTRRMIMat OBJECT IDENTIFIER ::= { mtTRRepeater 3 }
-- OBJECT-IDENTITY
--  Status
--    mandatory
--  Descr
--    repeater with no stations and TPIM Ring-In/Ring-Out

mtTRRMIM2at OBJECT IDENTIFIER ::= { mtTRRepeater 4 }
-- OBJECT-IDENTITY
--  Status
--    mandatory
--  Descr
--    repeater with 12 active UTP stations and TPIM Ring-In/Ring-Out

mtTRRMIM4at OBJECT IDENTIFIER ::= { mtTRRepeater 5 }
-- OBJECT-IDENTITY
--  Status
--    mandatory
--  Descr
--    Token Ring repeater with 12 active STP stations and TPIM
--    Ring-in/Ring-out.

mtTPIM OBJECT IDENTIFIER ::= { mtTokenRing 4 }
-- OBJECT-IDENTITY
--  Status
--    mandatory
--  Descr
--    Token Ring TPIMs

mtTPIMUnk OBJECT IDENTIFIER ::= { mtTPIM 1 }
-- OBJECT-IDENTITY
--  Status
--    mandatory
--  Descr
--    Unknown TPIM

mtTPIMT1 OBJECT IDENTIFIER ::= { mtTPIM 2 }
-- OBJECT-IDENTITY
--  Status
--    mandatory
--  Descr
--    TPIM STP with DB9 connection

mtTPIMF2 OBJECT IDENTIFIER ::= { mtTPIM 3 }
-- OBJECT-IDENTITY
--  Status
--    mandatory
--  Descr
--    TPIM with ST multimode connectors

mtTPIMT4 OBJECT IDENTIFIER ::= { mtTPIM 4 }
-- OBJECT-IDENTITY
--  Status
--    mandatory
--  Descr
--    TPIM with STP RJ45 connector

mtTPIMT2 OBJECT IDENTIFIER ::= { mtTPIM 5 }
-- OBJECT-IDENTITY
--  Status
--    mandatory
--  Descr
--    TPIM with UTP RJ45

mtTPIMF3 OBJECT IDENTIFIER ::= { mtTPIM 6 }
-- OBJECT-IDENTITY
--  Status
--    mandatory
--  Descr
--    TPIM with single mode fiber, ST connectors

mtTRBrim OBJECT IDENTIFIER ::= { mtTokenRing 5 }
-- OBJECT-IDENTITY
--  Status
--    mandatory
--  Descr
--    Token Ring BRIMs

mtBrimT6 OBJECT IDENTIFIER ::= { mtTRBrim 1 }
-- OBJECT-IDENTITY
--  Status
--    mandatory
--  Descr
--    Token Ring BRIM supports TPIM

mtTRStandAlone OBJECT IDENTIFIER ::= { mtTokenRing 6 }
-- OBJECT-IDENTITY
--  Status
--    mandatory
--  Descr
--    Token Ring Standalone Devices

mtTSX1620 OBJECT IDENTIFIER ::= { mtTRStandAlone 1 }
-- OBJECT-IDENTITY
--  Status
--    mandatory
--  Descr
--    Token Ring Standalone switch with 8 base ports and optional
--    extension module.

mtTrxi24 OBJECT IDENTIFIER ::= { mtTRStandAlone 48 }
-- OBJECT-IDENTITY
--  Status
--    mandatory
--  Descr
--    24 passive UTP ports.

mtTrxi22 OBJECT IDENTIFIER ::= { mtTRStandAlone 49 }
-- OBJECT-IDENTITY
--  Status
--    mandatory
--  Descr
--    12 Passive UTP Ports

mtTrxi24A OBJECT IDENTIFIER ::= { mtTRStandAlone 50 }
-- OBJECT-IDENTITY
--  Status
--    mandatory
--  Descr
--    24 active UTP ports.

mtTrxi22A OBJECT IDENTIFIER ::= { mtTRStandAlone 51 }
-- OBJECT-IDENTITY
--  Status
--    mandatory
--  Descr
--    12 Active UTP Ports

mtTrxi44 OBJECT IDENTIFIER ::= { mtTRStandAlone 56 }
-- OBJECT-IDENTITY
--  Status
--    mandatory
--  Descr
--    24 passive STP ports.

mtTrxi42 OBJECT IDENTIFIER ::= { mtTRStandAlone 57 }
-- OBJECT-IDENTITY
--  Status
--    mandatory
--  Descr
--    12 Passive STP Ports

mtTrxi44A OBJECT IDENTIFIER ::= { mtTRStandAlone 58 }
-- OBJECT-IDENTITY
--  Status
--    mandatory
--  Descr
--    24 active STP ports.

mtTrxi42A OBJECT IDENTIFIER ::= { mtTRStandAlone 59 }
-- OBJECT-IDENTITY
--  Status
--    mandatory
--  Descr
--    12 Active STP Ports

mtTRManagement OBJECT IDENTIFIER ::= { mtTokenRing 7 }
-- OBJECT-IDENTITY
--  Status
--    mandatory

mtTRMMIM4at OBJECT IDENTIFIER ::= { mtTRManagement 1 }
-- OBJECT-IDENTITY
--  Status
--    mandatory
--  Descr
--    Token Ring with 12 STP active stations with TPIMs
--    for ring in and ring out.

mtTRMMIM2at OBJECT IDENTIFIER ::= { mtTRManagement 2 }
-- OBJECT-IDENTITY
--  Status
--    mandatory
--  Descr
--    Token Ring with 12 UTP active stations with TPIMs
--    for ring in and ring out.

mtTRMMIMF2t OBJECT IDENTIFIER ::= { mtTRManagement 3 }
-- OBJECT-IDENTITY
--  Status
--    mandatory
--  Descr
--    Token Ring with 6 MMF  station ports with TPIMs
--    for ring in and ring out.

mtTRMMIMF3t OBJECT IDENTIFIER ::= { mtTRManagement 4 }
-- OBJECT-IDENTITY
--  Status
--    mandatory
--  Descr
--    Token Ring with 5 SMF  station ports with TPIMs
--    for ring in and ring out.

mtTBRMIM OBJECT IDENTIFIER ::= { mtTRManagement 5 }
-- OBJECT-IDENTITY
--  Status
--    mandatory
--  Descr
--    4 port Token Ring Bridge/Routing MIM with 1 BRIM port.

mtSTH OBJECT IDENTIFIER ::= { mtTokenRing 8 }
-- OBJECT-IDENTITY
--  Status
--    mandatory
--  Descr
--    Reserved for Steve Zinch and STH products

mtSTH22A OBJECT IDENTIFIER ::= { mtSTH 248 }
-- OBJECT-IDENTITY
--  Status
--    mandatory
--  Descr
--    12 port UTP Active

mtSTH24A OBJECT IDENTIFIER ::= { mtSTH 136 }
-- OBJECT-IDENTITY
--  Status
--    mandatory
--  Descr
--    24 port UTP Active

mtSTH42A OBJECT IDENTIFIER ::= { mtSTH 244 }
-- OBJECT-IDENTITY
--  Status
--    mandatory
--  Descr
--    12 port STP Active

mtSTH44A OBJECT IDENTIFIER ::= { mtSTH 68 }
-- OBJECT-IDENTITY
--  Status
--    mandatory
--  Descr
--    24 port UTP Active

mtSTHI OBJECT IDENTIFIER ::= { mtTokenRing 9 }
-- OBJECT-IDENTITY
--  Status
--    mandatory
--  Descr
--    Reserved for Steve Zinch and STH products

mtSTHI22A OBJECT IDENTIFIER ::= { mtSTHI 248 }
-- OBJECT-IDENTITY
--  Status
--    mandatory
--  Descr
--    12 port UTP Active with intelligence

mtSTHI24A OBJECT IDENTIFIER ::= { mtSTHI 136 }
-- OBJECT-IDENTITY
--  Status
--    mandatory
--  Descr
--    24 port UTP Active with intelligence

mtSTHI42A OBJECT IDENTIFIER ::= { mtSTHI 244 }
-- OBJECT-IDENTITY
--  Status
--    mandatory
--  Descr
--    12 port STP Active with intelligence

mtSTHI44A OBJECT IDENTIFIER ::= { mtSTHI 68 }
-- OBJECT-IDENTITY
--  Status
--    mandatory
--  Descr
--    24 port STP Active with intellgence

mtUMMAC OBJECT IDENTIFIER ::= { mtTokenRing 10 }
-- OBJECT-IDENTITY
--  Status
--    mandatory
--  Descr
--    MicroMMAC

mtUMMAC22T OBJECT IDENTIFIER ::= { mtUMMAC 248 }
-- OBJECT-IDENTITY
--  Status
--    mandatory
--  Descr
--    12 port UTP Active with intelligence

mtUMMAC24T OBJECT IDENTIFIER ::= { mtUMMAC 136 }
-- OBJECT-IDENTITY
--  Status
--    mandatory
--  Descr
--    24 port UTP Active with intelligence

mtUMMAC42T OBJECT IDENTIFIER ::= { mtUMMAC 244 }
-- OBJECT-IDENTITY
--  Status
--    mandatory
--  Descr
--    12 port STP Active with intellgence

mtUMMAC44T OBJECT IDENTIFIER ::= { mtUMMAC 68 }
-- OBJECT-IDENTITY
--  Status
--    mandatory
--  Descr
--    24 port STP Active with intellgence

mtTRPortSwitch OBJECT IDENTIFIER ::= { mtTokenRing 11 }
-- OBJECT-IDENTITY
--  Status
--    mandatory
--  Descr
--    The DIABLO ASIC based Token Ring Port Switch modules.

mtTRXMIM22A OBJECT IDENTIFIER ::= { mtTRPortSwitch 1 }
-- OBJECT-IDENTITY
--  Status
--    mandatory
--  Descr
--    Port assignment with 12 RJ45 UTP station ports.

mtTRXMIM24A OBJECT IDENTIFIER ::= { mtTRPortSwitch 2 }
-- OBJECT-IDENTITY
--  Status
--    mandatory
--  Descr
--    Port assignment with 24 RJ45 UTP station ports.

mtTRXMIM42A OBJECT IDENTIFIER ::= { mtTRPortSwitch 3 }
-- OBJECT-IDENTITY
--  Status
--    mandatory
--  Descr
--    Port assignment with 12 RJ45 STP station ports.

mtTRXMIM44A OBJECT IDENTIFIER ::= { mtTRPortSwitch 4 }
-- OBJECT-IDENTITY
--  Status
--    mandatory
--  Descr
--    Port assignment with 24 RJ45 STP station ports.

mtTRXMIM54A OBJECT IDENTIFIER ::= { mtTRPortSwitch 5 }
-- OBJECT-IDENTITY
--  Status
--    mandatory
--  Descr
--    Port assignment with 24 RJ45 UTP/STP station ports.

mtTDRMIM22A OBJECT IDENTIFIER ::= { mtTRPortSwitch 7 }
-- OBJECT-IDENTITY
--  Status
--    mandatory
--  Descr
--    Dual port ring in/ring out with 12 active UTP lobe
--    ports on daughter board.

mtTDRMIM42A OBJECT IDENTIFIER ::= { mtTRPortSwitch 8 }
-- OBJECT-IDENTITY
--  Status
--    mandatory
--  Descr
--    Dual port ring in/ring out with 12 active STP lobe
--    ports on daughter board.

mtCrm2RT OBJECT IDENTIFIER ::= { mtTRPortSwitch 9 }
-- OBJECT-IDENTITY
--  Status
--    mandatory
--  Descr
--    Cisco Token Ring BRIM on a mother MIM.

mtTDRMIMAT OBJECT IDENTIFIER ::= { mtTRPortSwitch 10 }
-- OBJECT-IDENTITY
--  Status
--    mandatory
--  Descr
--    Dual port ring in/ring out with 12 active UTP/STP lobe
--    ports on daughter board.

mtFDDI OBJECT IDENTIFIER ::= { mtExpanded 7 }
-- OBJECT-IDENTITY
--  Status
--    mandatory
--  Descr
--    The FDDI product branch

mtFDDIconcFIBER OBJECT IDENTIFIER ::= { mtFDDI 1 }
-- OBJECT-IDENTITY
--  Status
--    mandatory
--  Descr
--    FDDI concentrators fiber.

mtFDDIconcTWISTED OBJECT IDENTIFIER ::= { mtFDDI 2 }
-- OBJECT-IDENTITY
--  Status
--    mandatory
--  Descr
--    FDDI concentrators twisted pair.

mtFDCMIM12 OBJECT IDENTIFIER ::= { mtFDDIconcTWISTED 16 }
-- OBJECT-IDENTITY
--  Status
--    mandatory
--  Descr
--    FDDI concentrator with 12 STP DB9 M ports.

mtFDCMIM22 OBJECT IDENTIFIER ::= { mtFDDIconcTWISTED 22 }
-- OBJECT-IDENTITY
--  Status
--    mandatory
--  Descr
--    FDDI concentrator with 12 UTP M ports.

mtFDCMIM42 OBJECT IDENTIFIER ::= { mtFDDIconcTWISTED 18 }
-- OBJECT-IDENTITY
--  Status
--    mandatory
--  Descr
--    FDDI concentrator with 12 STP RJ45 M ports.

mtFDCMIM16 OBJECT IDENTIFIER ::= { mtFDDIconcTWISTED 19 }
-- OBJECT-IDENTITY
--  Status
--    mandatory
--  Descr
--    FDDI concentrator with 6 STP DB9 M ports.

mtFDCMIM26 OBJECT IDENTIFIER ::= { mtFDDIconcTWISTED 20 }
-- OBJECT-IDENTITY
--  Status
--    mandatory
--  Descr
--    FDDI concentrator with 12 STP DB9 M ports.

mtFDCMIM46 OBJECT IDENTIFIER ::= { mtFDDIconcTWISTED 21 }
-- OBJECT-IDENTITY
--  Status
--    mandatory
--  Descr
--    FDDI concentrator with 6 STP RJ45 M ports.

mtFDCMIM44 OBJECT IDENTIFIER ::= { mtFDDIconcTWISTED 24 }
-- OBJECT-IDENTITY
--  Status
--    mandatory
--  Descr
--    FDDI concentrator with 4 STP M ports.

mtFDCMIM48 OBJECT IDENTIFIER ::= { mtFDDIconcTWISTED 25 }
-- OBJECT-IDENTITY
--  Status
--    mandatory
--  Descr
--    FDDI concentrator with 8 UTP M ports.

mtFDDImanagement OBJECT IDENTIFIER ::= { mtFDDI 3 }
-- OBJECT-IDENTITY
--  Status
--    mandatory

mtFDMMIM24mmf OBJECT IDENTIFIER ::= { mtFDDImanagement 1 }
-- OBJECT-IDENTITY
--  Status
--    mandatory
--  Descr
--    FDDI to Ethernet Bridge/Management MIM MMF A/B and 4 UTP M
--    ports

mtFddiBrim OBJECT IDENTIFIER ::= { mtFDDI 4 }
-- OBJECT-IDENTITY
--  Status
--    mandatory
--  Descr
--    FDDI BRIMs

mtBrimFD0 OBJECT IDENTIFIER ::= { mtFddiBrim 1 }
-- OBJECT-IDENTITY
--  Status
--    mandatory
--  Descr
--    A/B ports, Multimode MIC connectors.

mtBrimFD6 OBJECT IDENTIFIER ::= { mtFddiBrim 2 }
-- OBJECT-IDENTITY
--  Status
--    mandatory
--  Descr
--    A/B ports, FPIM slots.

mtBrimFD5 OBJECT IDENTIFIER ::= { mtFddiBrim 3 }
-- OBJECT-IDENTITY
--  Status
--    mandatory
--  Descr
--    A/B ports, Singlemode MIC connectors.

mtFddiHsim OBJECT IDENTIFIER ::= { mtFDDI 5 }
-- OBJECT-IDENTITY
--  Status
--    mandatory
--  Descr
--    FDDI HSIMs

mtFddiHsimF6 OBJECT IDENTIFIER ::= { mtFddiHsim 1 }
-- OBJECT-IDENTITY
--  Status
--    mandatory
--  Descr
--    FDDI High Speed Interface Module which supports
--    two FPIMs.

mtWan OBJECT IDENTIFIER ::= { mtExpanded 9 }
-- OBJECT-IDENTITY
--  Status
--    mandatory
--  Descr
--    WAN Products using 3 registers

mtWanBrim OBJECT IDENTIFIER ::= { mtWan 1 }
-- OBJECT-IDENTITY
--  Status
--    mandatory
--  Descr
--    WAN BRIMs

mtBrimWT1 OBJECT IDENTIFIER ::= { mtWanBrim 1 }
-- OBJECT-IDENTITY
--  Status
--    mandatory
--  Descr
--    WAN BRIM for MicroMMAC

mtBrimW6 OBJECT IDENTIFIER ::= { mtWanBrim 2 }
-- OBJECT-IDENTITY
--  Status
--    mandatory
--  Descr
--    WAN BRIM for Generic BRIMs

mtBrimWB4 OBJECT IDENTIFIER ::= { mtWanBrim 3 }
-- OBJECT-IDENTITY
--  Status
--    mandatory
--  Descr
--    LAN/WAN Virtual Router for MMAC with four ISDN BRI ports.
--    Supports TCP/IP and optionally IPX, Frame Relay and X.25.
--    A Serial port is used for local managagement.  Supports
--    ML-PPP and compression.

mtWanCyberSwitch OBJECT IDENTIFIER ::= { mtWan 2 }
-- OBJECT-IDENTITY
--  Status
--    mandatory
--  Descr
--    branch for CyberSwitches

mtWanCyberSwitch200 OBJECT IDENTIFIER ::= { mtWanCyberSwitch 1 }
-- OBJECT-IDENTITY
--  Status
--    mandatory
--  Descr
--    LAN/WAN switch which supports VLAN and SFS, with 12
--    repeated Ethernet RJ-45 ports, a single WPIM, and an
--    optional compression/encryption internal daughter card.

mtWanCyberSwitch300 OBJECT IDENTIFIER ::= { mtWanCyberSwitch 2 }
-- OBJECT-IDENTITY
--  Status
--    mandatory
--  Descr
--    LAN/WAN switch which supports VLAN and SFS, with 24
--    repeated Ethernet RJ-45 ports, a stackable connector,
--    a single WPIM, an asynchronous interface, an ISDN
--    BRI S/T interface and an optional compression/encryption
--    internal daughter card.

mtWanCyberSwitch400 OBJECT IDENTIFIER ::= { mtWanCyberSwitch 3 }
-- OBJECT-IDENTITY
--  Status
--    mandatory
--  Descr
--    LAN/WAN switch which supports VLAN and SFS, with 2 switched
--    Ethernet WPIM ports, 2 WPIMs and 2 optional compression/encryption
--    internal daughter cards.

mtWanCyberSwitch150 OBJECT IDENTIFIER ::= { mtWanCyberSwitch 4 }
-- OBJECT-IDENTITY
--  Status
--    mandatory
--  Descr
--    LAN/WAN Bridge/Router with dual POTS ports and a single ISDN BRI port.
--    Supports TCP/IP and optionally IPX.  A Serial port is used for local
--    managagement as well as an Asynch-PPP interface.  Supports ML-PPP and
--    compression.

mtWanCyberSwitch1200 OBJECT IDENTIFIER ::= { mtWanCyberSwitch 5 }
-- OBJECT-IDENTITY
--  Status
--    mandatory
--  Descr
--    LAN/WAN Bridge/Router with four ISDN BRI ports or a single PRI port.
--    Supports TCP/IP and optionally IPX, Frame Relay and X.25.  A Serial port
--    is used for local managagement.  Supports ML-PPP and compression.

mtWanCyberSwitch6000 OBJECT IDENTIFIER ::= { mtWanCyberSwitch 6 }
-- OBJECT-IDENTITY
--  Status
--    mandatory
--  Descr
--    LAN/WAN Bridge/Router with 8 slots to accomodate multiple WAN
--    technologies.  Up to 24 ISDN BRI ports or 6 PRI ports, Digital
--    Modem, V.35 and Dedicated Lines. Supports TCP/IP and optionally
--    IPX, Frame Relay and X.25.  Supports ML-PPP and compression. Single
--    or dual port Ethernet capability.

mtWanCyberSwitch7000 OBJECT IDENTIFIER ::= { mtWanCyberSwitch 7 }
-- OBJECT-IDENTITY
--  Status
--    mandatory
--  Descr
--    LAN/WAN Bridge/Router with 16 slots to accomodate multiple WAN
--    technologies.  Up to 48 ISDN BRI ports or 12 PRI ports, Digital
--    Modem, V.35 and Dedicated Lines. Supports TCP/IP and optionally
--    IPX, Frame Relay and X.25.  Supports ML-PPP and compression.  Single
--    or dual port Ethernet capability.

mtWanCyberSwitch5500 OBJECT IDENTIFIER ::= { mtWanCyberSwitch 8 }
-- OBJECT-IDENTITY
--  Status
--    mandatory
--  Descr
--    LAN/WAN Bridge/Router with 6 slots to accomodate multiple WAN
--    technologies.  Up to 16 ISDN BRI ports or 4 PRI ports, Digital
--    Modem, V.35 and Dedicated Lines. Supports TCP/IP and optionally
--    IPX, Frame Relay and X.25.  Supports ML-PPP and compression.  Single
--    or dual port Ethernet capability.

mtWanCyberSwitch9W000p00 OBJECT IDENTIFIER ::= { mtWanCyberSwitch 9 }
-- OBJECT-IDENTITY
--  Status
--    mandatory
--  Descr
--    LAN/WAN Bridge/Router module for the MMAC-Plus product with 2 slots
--    to accommodate up to 4 WAN cards for ISDN and Digital Modem access.
--    TCP/IP, IPX, and AppleTalk protocols supported, and optionally
--    FrameRelay and X.25. Supports ML-PPP and compression. Dual port
--    Ethernet capability.

mtWanCyberSwitch9W426p420 OBJECT IDENTIFIER ::= { mtWanCyberSwitch 10 }
-- OBJECT-IDENTITY
--  Status
--    mandatory
--  Descr
--    Dual slot MMAC-Plus module with INB-2 connectivity. The front panel
--    has 2 slots for HSIMs-W65's.

mtWanCyberSwitch9W427p420 OBJECT IDENTIFIER ::= { mtWanCyberSwitch 11 }
-- OBJECT-IDENTITY
--  Status
--    mandatory
--  Descr
--    Dual slot MMAC-Plus module with INB-2 connectivity. The front panel
--    has 2 slots for HSIMs-W75's.

mtWanCyberSwitchNE1000 OBJECT IDENTIFIER ::= { mtWanCyberSwitch 12 }
-- OBJECT-IDENTITY
--  Status
--    mandatory
--  Descr
--    LAN/WAN Bridge/Router with up to four ISDN BRI ports.
--    Supports TCP/IP and optionally IPX, Frame Relay and X.25.  A Serial
--    port is used for local managagement.  Supports ML-PPP and
--    compression.

mtWanCyberSwitchPOTS OBJECT IDENTIFIER ::= { mtWanCyberSwitch 13 }
-- OBJECT-IDENTITY
--  Status
--    mandatory
--  Descr
--    CyberSwitch Plain Old Telephone adapter for CSX150.
--    Provides 2 RJ-11 connections.

mtWanCyberSwitchNTp1 OBJECT IDENTIFIER ::= { mtWanCyberSwitch 14 }
-- OBJECT-IDENTITY
--  Status
--    mandatory
--  Descr
--    CyberSwitch Network Terminator adapter for CSX150.
--    Converts the RJ-45 connector to ISDN U Basic Rate connectivity.

mtWanCyberSwitchBRI1 OBJECT IDENTIFIER ::= { mtWanCyberSwitch 15 }
-- OBJECT-IDENTITY
--  Status
--    mandatory
--  Descr
--    CyberSwitch WAN module with 1 RJ45 port and ISDN S/T Basic Rate
--    connectivity.

mtWanCyberSwitchBRI4 OBJECT IDENTIFIER ::= { mtWanCyberSwitch 16 }
-- OBJECT-IDENTITY
--  Status
--    mandatory
--  Descr
--    CyberSwitch WAN module with 4 RJ45 ports and ISDN S/T Basic Rate
--    connectivity.

mtWanCyberSwitchPRI8  OBJECT IDENTIFIER ::= { mtWanCyberSwitch 17 }
-- OBJECT-IDENTITY
--  Status
--    mandatory
--  Descr
--    CyberSwitch WAN module with 1 RJ45 port and ISDN S/T Primary Rate
--    connectivity. Provides 8 Kbps "B" channels.

mtWanCyberSwitchPRI23  OBJECT IDENTIFIER ::= { mtWanCyberSwitch 18 }
-- OBJECT-IDENTITY
--  Status
--    mandatory
--  Descr
--    CyberSwitch WAN module with 1 RJ45 port and ISDN S/T Primary Rate
--    connectivity. Provides 23 to 30 Kbps "B" channels.

mtWanCyberSwitchEXP  OBJECT IDENTIFIER ::= { mtWanCyberSwitch 19 }
-- OBJECT-IDENTITY
--  Status
--    mandatory
--  Descr
--    CyberSwitch WAN expansion module with no ports and provides
--    only PRI8 channel expansion up to 23 or 30 Kbps "B" channels.

mtWanCyberSwitchRS232 OBJECT IDENTIFIER ::= { mtWanCyberSwitch 20 }
-- OBJECT-IDENTITY
--  Status
--    mandatory
--  Descr
--    CyberSwitch Serial module with 4 DB56 ports and dedicated line
--    connectivity.

mtWanCyberSwitchV35 OBJECT IDENTIFIER ::= { mtWanCyberSwitch 21 }
-- OBJECT-IDENTITY
--  Status
--    mandatory
--  Descr
--    CyberSwitch Serial module with 2 DB26 ports and dedicated line
--    connectivity.

mtWanCyberSwitchDIG OBJECT IDENTIFIER ::= { mtWanCyberSwitch 22 }
-- OBJECT-IDENTITY
--  Status
--    mandatory
--  Descr
--    CyberSwitch Digital Modem module with 8 V.34+ 33.6 Kbps modems
--    Supports Async-PPP.

mtWanCyberSwitchDIG24 OBJECT IDENTIFIER ::= { mtWanCyberSwitch 23 }
-- OBJECT-IDENTITY
--  Status
--    mandatory
--  Descr
--    CyberSwitch Digital Modem module with 24 V.34+ 33.6 Kbps modems
--    Supports Async-PPP.

mtWanCyberSwitchDIG24Plus OBJECT IDENTIFIER ::= { mtWanCyberSwitch 24 }
-- OBJECT-IDENTITY
--  Status
--    mandatory
--  Descr
--    CyberSwitch Digital Modem module with 24 V.34+ 56 Kbps modems
--     Supports Async-PPP.

mtWanCyberSwitchDIG30Plus OBJECT IDENTIFIER ::= { mtWanCyberSwitch 25 }
-- OBJECT-IDENTITY
--  Status
--    mandatory
--  Descr
--    CyberSwitch Digital Modem module with 30 V.34+ 56 Kbps modems
--    Supports Async-PPP.

mtWanCyberSwitchAUI1 OBJECT IDENTIFIER ::= { mtWanCyberSwitch 26 }
-- OBJECT-IDENTITY
--  Status
--    mandatory
--  Descr
--    CyberSwitch AUI/Ethernet Port Interface Module Supporting a
--    single Ethernet segment.

mtWanCyberSwitchAUI2 OBJECT IDENTIFIER ::= { mtWanCyberSwitch 27 }
-- OBJECT-IDENTITY
--  Status
--    mandatory
--  Descr
--    CyberSwitch AUI/Ethernet Port Interface Module Supporting two
--    Ethernet segments.

mtWanThirdParty OBJECT IDENTIFIER ::= { mtWan 3 }
-- OBJECT-IDENTITY
--  Status
--    mandatory
--  Descr
--    branch for WAN third party products

tpWanCyberSwitch100 OBJECT IDENTIFIER ::= { mtWanThirdParty 1 }
-- OBJECT-IDENTITY
--  Status
--    mandatory
--  Descr
--    an Ethernet to ISDN device which supports Transparent
--    Bridging and IP/IPX routing.

mtWanHsim OBJECT IDENTIFIER ::= { mtWan 4 }
-- OBJECT-IDENTITY
--  Status
--    mandatory
--  Descr
--    branch for WAN HSIMs

mtWanHsimW6 OBJECT IDENTIFIER ::= { mtWanHsim 1 }
-- OBJECT-IDENTITY
--  Status
--    mandatory

mtWanHsimW84 OBJECT IDENTIFIER ::= { mtWanHsim 2 }
-- OBJECT-IDENTITY
--  Status
--    mandatory

mtWanHsimW87 OBJECT IDENTIFIER ::= { mtWanHsim 3 }
-- OBJECT-IDENTITY
-- Status
--    mandatory
--  Descr
--    A wan hsim with a physical T3 interface
--    providing 28 logical T1 connections.


mtWanHsimWB4 OBJECT IDENTIFIER ::= { mtWanHsim 4 }
-- OBJECT-IDENTITY
--  Status
--    mandatory

mtWanHsimSSA710 OBJECT IDENTIFIER ::= { mtWanHsim 5 }
-- OBJECT-IDENTITY
--  Status
--    mandatory
--  Descr
--      A WAN dial access HSIM with a single fixed RJ-48C
--      ISDN PRI (T1) interface and a second wpim interface.
--      Supports 24 ports V.90 digital modems.

mtWanHsimSSA720 OBJECT IDENTIFIER ::= { mtWanHsim 6 }
-- OBJECT-IDENTITY
--  Status
--    mandatory
--  Descr
--      A WAN dial access HSIM with a single fixed RJ-48C ISDN
--      PRI (E1) interface and a wpim interface.  Supports 24
--      ports V.90 digital modems.

mtWanHsimWD1 OBJECT IDENTIFIER ::= { mtWanHsim 7 }
-- OBJECT-IDENTITY
--  Status
--    mandatory
--  Descr
--    A wan hsim which supports Voice over IP and
--    comes configured with a T1 WPIM with an
--    additional wpim slot.

mtWanHsimW85 OBJECT IDENTIFIER ::= { mtWanHsim 8 }
-- OBJECT-IDENTITY
--  Status
--    mandatory
--  Descr
--       A wan hsim with 8 physical T1 interfaces

mtWanHsimSSA710p48 OBJECT IDENTIFIER ::= { mtWanHsim 9 }
-- OBJECT-IDENTITY
--  Status
--    mandatory
--  Descr
--      A WAN dial access HSIM with a single fixed RJ-48C
--      ISDN PRI (T1) interface and a second PRI interface.
--      Supports 48 ports V.90 digital modems.

mtWanHsimSSA720p60 OBJECT IDENTIFIER ::= { mtWanHsim 10 }
-- OBJECT-IDENTITY
--  Status
--    mandatory
--  Descr
--      A WAN dial access HSIM with a single fixed RJ-48C ISDN
--      PRI (E1) interface and a second PRI interface.  Supports 60
--      ports V.90 digital modems.

mtWanCMM OBJECT IDENTIFIER ::= { mtWan 5 }
-- OBJECT-IDENTITY
--  Status
--    mandatory
--  Descr
--    Branch for Multi-Modem Modules

mtWanCMM824 OBJECT IDENTIFIER ::= { mtWanCMM 1 }
-- OBJECT-IDENTITY
--  Status
--    mandatory
--  Descr
--    Multimode modem with 3 modules of 8 modems for
--    a total of 24 modems

mtWanCMM3248 OBJECT IDENTIFIER ::= { mtWanCMM 2 }
-- OBJECT-IDENTITY
--  Status
--   mandatory
--  Descr
--   Multimode modem with 2 modules of 24 modems for a total of 48 modems.

mtWanCMM3264 OBJECT IDENTIFIER ::= { mtWanCMM 3 }
-- OBJECT-IDENTITY
--  Status
--   mandatory
--  Descr
--   Multimode modem with 2 modules of 32 modems for a total of 64 modems.

mtWanCMM3224 OBJECT IDENTIFIER ::= { mtWanCMM 4 }
-- OBJECT-IDENTITY
--  Status
--   mandatory
--  Descr
--   Multimode modem with 1 module of 24 modems.

mtWanCMM3232 OBJECT IDENTIFIER ::= { mtWanCMM 5 }
-- OBJECT-IDENTITY
--  Status
--   mandatory
--  Descr
--   Multimode modem with 1 module of 32 modems.

mtWanAccess     OBJECT IDENTIFIER ::= { mtWan 6 }
-- OBJECT-IDENTITY
--  Status
--    mandatory
--  Descr
--    Branch for Access Servers

mtAS316 OBJECT IDENTIFIER ::= { mtWanAccess 1 }
-- OBJECT-IDENTITY
--  Status
--    mandatory
--  Descr
--    StandAlone Access Server with 16 async ports and one
--    Ethernet port.

mtSSA710p48 OBJECT IDENTIFIER ::= { mtWanAccess 2 }
-- OBJECT-IDENTITY
--  Status
--    mandatory
--  Descr
--    Wan dial access stackable with a fixed RJ-48C ISDN PRI
--    (T1) inteface, a wpim-RT1 PRI interface and a 10Base-T
--    interface with an RJ-45 connector.  This supports 48
--    ports of V.90 digital modems.

mtSSA720p60 OBJECT IDENTIFIER ::= { mtWanAccess 3 }
-- OBJECT-IDENTITY
--  Status
--    mandatory
--  Descr
--    Wan dial access stackable with a fixed RJ-48C ISDN PRI
--    (E1) inteface, a wpim-RE1 PRI interface and a 10Base-T
--    interface with an RJ-45 connector.  This supports 60
--    ports of V.90 digital modems.

mtATM OBJECT IDENTIFIER ::= { mtExpanded 11 }
-- OBJECT-IDENTITY
--  Status
--    mandatory
--  Descr
--    Reserved for ATM products

mtAtmBrim OBJECT IDENTIFIER ::= { mtATM 1 }
-- OBJECT-IDENTITY
--  Status
--    mandatory
--  Descr
--    ATM BRIMs

mtBrimA100 OBJECT IDENTIFIER ::= { mtAtmBrim 1 }
-- OBJECT-IDENTITY
--  Status
--    mandatory
--  Descr
--    100 Meg with MIC connector

mtBrimA6 OBJECT IDENTIFIER ::= { mtAtmBrim 2 }
-- OBJECT-IDENTITY
--  Status
--    mandatory
--  Descr
--    ATM Bridge Router Interface Module with one ATM Port
--    Interface Module (APIM).

mtBrimA6DP OBJECT IDENTIFIER ::= { mtAtmBrim 3 }
-- OBJECT-IDENTITY
--  Status
--    mandatory
--  Descr
--    ATM Bridge Router Interface module with 2 APIM connectors,
--    one of which is redundent.

mtAtmHsim OBJECT IDENTIFIER ::= { mtATM 2 }
-- OBJECT-IDENTITY
--  Status
--    mandatory
--  Descr
--    ATM HSIMs

mtAtmHsimA6DP OBJECT IDENTIFIER ::= { mtAtmHsim 1 }
-- OBJECT-IDENTITY
--  Status
--    mandatory
--  Descr
--    ATM High Speed Interface Module which supports
--    two (redundant) APIMs.

mtAtmVHsimA6DP OBJECT IDENTIFIER ::= { mtAtmHsim 2 }
-- OBJECT-IDENTITY
--  Status
--    mandatory
--  Descr
--    ATM Very High Speed Interface Module which supports
--    two (redundant) APIMs

mtAtmStandAlone OBJECT IDENTIFIER ::= { mtATM 3 }
-- OBJECT-IDENTITY
--  Status
--    mandatory
--  Descr
--    ATM Standalone devices (switches)

mt2A000  OBJECT IDENTIFIER ::= { mtAtmStandAlone 1 }
-- OBJECT-IDENTITY
--  Status
--    mandatory
--  Descr
--    SS2500 ATM Switch w/ 2.5Gbps switch fabric and
--    four network module slots.

mt2A000R  OBJECT IDENTIFIER ::= { mtAtmStandAlone 2 }
-- OBJECT-IDENTITY
--  Status
--    mandatory
--  Descr
--    SS2500 ATM Switch w/ 2.5Gbps switch fabric and
--    four network module slots. Redundant power supplies.

mtAtmNetworkModule  OBJECT IDENTIFIER ::= { mtATM 4 }
-- OBJECT-IDENTITY
--  Status
--    mandatory
--  Descr
--    This branch defines Network Modules cards that are
--    specific to the 2500/6500 architecture

mtIOM21p04      OBJECT IDENTIFIER ::= { mtAtmNetworkModule 1 }
-- OBJECT-IDENTITY
--  Status
--    mandatory
--  Descr
--    A network module with 4 MMF SC connectors at 155 Mbps

mtIOM22p04      OBJECT IDENTIFIER ::= { mtAtmNetworkModule 2 }
-- OBJECT-IDENTITY
--  Status
--    mandatory
--  Descr
--    A network module with 4 Cat 5 UTP with RJ45
--    connectors at 155 Mbps

mtIOM29p04IR      OBJECT IDENTIFIER ::= { mtAtmNetworkModule 3 }
-- OBJECT-IDENTITY
--  Status
--    mandatory
--  Descr
--    A network module with 4 ports 1 SMF IR (intermediate reach)
--    SC port at 155 Mbps and 3 MMF SC connectors at 155 Mbps

mtIOM29p04LR      OBJECT IDENTIFIER ::= { mtAtmNetworkModule 4 }
-- OBJECT-IDENTITY
--  Status
--    mandatory
--  Descr
--    A network module with 4 ports 1 SMF LR (long reach)
--    SC port at 155 Mbps and 3 MMF SC connectors at 155 Mbps

mtIOM31p01      OBJECT IDENTIFIER ::= { mtAtmNetworkModule 5 }
-- OBJECT-IDENTITY
--  Status
--    mandatory
--  Descr
--    A network module with a single port OC12 (622 Mbps) MMF
--    with an SC connector

mtIOM39p01      OBJECT IDENTIFIER ::= { mtAtmNetworkModule 6 }
-- OBJECT-IDENTITY
--  Status
--    mandatory
--  Descr
--    A network module with a single port OC12 (622 Mbps) SMF
--    with an SC connector

mtIOM39p01LR      OBJECT IDENTIFIER ::= { mtAtmNetworkModule 7 }
-- OBJECT-IDENTITY
--  Status
--    mandatory
--  Descr
--    A network module with a single port OC12 (622 Mbps) SMF
--    long reach with an SC connector

mtIOM67p04      OBJECT IDENTIFIER ::= { mtAtmNetworkModule 8 }
-- OBJECT-IDENTITY
--  Status
--    mandatory
--  Descr
--    A T3 (45 Mbps) network module with four BNC connectors.

mtIOM77p04      OBJECT IDENTIFIER ::= { mtAtmNetworkModule 9 }
-- OBJECT-IDENTITY
--  Status
--    mandatory
--  Descr
--    An E3 (34 Mbps) network module with 4 BNC connectors.


mtFPS OBJECT IDENTIFIER ::= { mtExpanded 12 }
-- OBJECT-IDENTITY
--  Status
--    mandatory
--  Descr
--    This branch is reserved for FPS modules that are
--    not directly related to either MMAC or MMAC plus products.
--    These may exist in an MMAC or MMAC plus chassis but be
--    unknown to that chassis.  They may also exist in their
--    own standalone chassis.

mtFPSModules OBJECT IDENTIFIER ::= { mtFPS 1 }
-- OBJECT-IDENTITY
--  Status
--    mandatory
--  Descr
--    This branch is used to identify all FPS modules.
--    In this instance a module may be a module which resides
--    in another chassis but allows other stand alone modules to
--    be plugged into it.  It may also be a true stand alone
--    chassis.  It may also be a management module.

mt7C03 OBJECT IDENTIFIER ::= { mtFPSModules 1 }
-- OBJECT-IDENTITY
--  Status
--    mandatory
--  Descr
--    Two Slot MMAC module providing enclosure providing
--    three slots for NIB modules.  This module is visible
--    within an MMAC chassis but not managable.

mt7C04 OBJECT IDENTIFIER ::= { mtFPSModules 2 }
-- OBJECT-IDENTITY
--  Status
--    mandatory
--  Descr
--    Standalone NIB enclosures having 4 slots.

mt7X00 OBJECT IDENTIFIER ::= { mtFPSModules 3 }
-- OBJECT-IDENTITY
--  Status
--    mandatory
--  Descr
--    FPS and Management Module for FPSMIM and MMACFPS.
--    Provides two user configurable COM Ports.

mt7C04r OBJECT IDENTIFIER ::= { mtFPSModules 4 }
-- OBJECT-IDENTITY
--  Status
--    mandatory
--  Descr
--    Standalone NIB enclosures having 4 slots, and redundent
--    power capability.

mtFpsEthernet OBJECT IDENTIFIER ::= { mtFPS 2 }
-- OBJECT-IDENTITY
--  Status
--    mandatory
--  Descr
--    This branch is reserved for FPS ethernet products.

mt7E03p24 OBJECT IDENTIFIER ::= { mtFpsEthernet 1 }
-- OBJECT-IDENTITY
--  Status
--    mandatory
--  Descr
--    24 port Ethernet Module for FPSMIM and MMAC FPS using
--    telco connectors.

mt7E02p12 OBJECT IDENTIFIER ::= { mtFpsEthernet 2 }
-- OBJECT-IDENTITY
--  Status
--    mandatory
--  Descr
--    12 Port ethernet module for FPSMIM and MMAC FPS using
--    RJ45 connectors.

mt7E02p24 OBJECT IDENTIFIER ::= { mtFpsEthernet 3 }
-- OBJECT-IDENTITY
--  Status
--    mandatory
--  Descr
--    24 Port ethernet wide slot module for FPSMIM and MMAC FPS using
--    RJ45 connectors.

mt7E08p12 OBJECT IDENTIFIER ::= { mtFpsEthernet 4 }
-- OBJECT-IDENTITY
--  Status
--    mandatory
--  Descr
--    12 Port ethernet wide slot module for FPSMIM and MMAC FPS using
--    fiber connectors.

mtFpsFDDI OBJECT IDENTIFIER ::= { mtFPS 3 }
-- OBJECT-IDENTITY
--  Status
--    mandatory
--  Descr
--    This branch is reserved for FPS FDDI products.

mt7F06p02 OBJECT IDENTIFIER ::= { mtFpsFDDI 1 }
-- OBJECT-IDENTITY
--  Status
--    mandatory
--  Descr
--    2 Port FDDI module for FPSMIM and MMAC FPS using 4
--    (2 per FDDI port) FPIMs.

mtFpsTR OBJECT IDENTIFIER ::= { mtFPS 4 }
-- OBJECT-IDENTITY
--  Status
--    mandatory
--  Descr
--    This branch is reserved for FPS Token Ring products.

mt7T05p04 OBJECT IDENTIFIER ::= { mtFpsTR 1 }
-- OBJECT-IDENTITY
--  Status
--    mandatory
--  Descr
--    4 Port Token Ring module for FPSMIM and MMAC FPS using
--    RJ45 connectors and supporting UTP/STP.


mtFpsATM OBJECT IDENTIFIER ::= { mtFPS 5 }
-- OBJECT-IDENTITY
--  Status
--    mandatory
--  Descr
--    This branch identifies ATM FPS products.

mt7A06p01 OBJECT IDENTIFIER ::= { mtFpsATM 1 }
-- OBJECT-IDENTITY
--  Status
--    mandatory
--  Descr
--    Single port ATM access module for FPSMIM and MMACFPS
--    with two redundant APIMs.

mtFpsFastEthernet OBJECT IDENTIFIER ::= { mtFPS 6 }
-- OBJECT-IDENTITY
--  Status
--    mandatory
--  Descr
--    This branch identifies FPS Fast Ethernet products.

mt7H02p06 OBJECT IDENTIFIER ::= { mtFpsFastEthernet 1 }
-- OBJECT-IDENTITY
--  Status
--    mandatory
--  Descr
--    6 port fast ethernet module for FPSMIM and MMACFPS
--    with 5 RJ45 connectors and 1 FEPIM slot.

mt7H02p12 OBJECT IDENTIFIER ::= { mtFpsFastEthernet 2 }
-- OBJECT-IDENTITY
--  Status
--    mandatory
--  Descr
--    12 port fast ethernet wide slot module for FPSMIM
--    in 7C04-R with 11 RJ45 connectors and 1 FEPIM slot.

mt7H06p2 OBJECT IDENTIFIER ::= { mtFpsFastEthernet 3 }
-- OBJECT-IDENTITY
--  Status
--    mandatory
--  Descr
--    2 port fast ethernet single slot module for FPSMIM
--    with 2 FEPIM slots.

mtCableModem OBJECT IDENTIFIER ::= { mtExpanded 14 }
-- OBJECT-IDENTITY
--  Status
--    mandatory
--  Descr
--    A line of products which bridge between the network media
--    technologies and CATV.

mtEthernetCableModem OBJECT IDENTIFIER ::= { mtCableModem 1 }
-- OBJECT-IDENTITY
--  Status
--    mandatory
--  Descr
--    CableModems which bridge between ethernet and CATV.

mtMC23001pXE21 OBJECT IDENTIFIER ::= { mtEthernetCableModem 1 }
-- OBJECT-IDENTITY
--  Status
--    mandatory
--  Descr
--    CableModem for Head End with 2 ports and an EPIM.

mtMC21001pE01 OBJECT IDENTIFIER ::= { mtEthernetCableModem 2 }
-- OBJECT-IDENTITY
--  Status
--    mandatory
--  Descr
--    CableModem for Customer Premise with 2 ports and an EPIM.

mtWorkGroup OBJECT IDENTIFIER ::= { mtExpanded 20 }
-- OBJECT-IDENTITY
--  Status
--    mandatory
--  Descr
--    Work Group product line

mtWorkGroupChassis OBJECT IDENTIFIER ::= { mtWorkGroup 1 }
-- OBJECT-IDENTITY
--  Status
--    mandatory
--  Descr
--     Work Group product line chassis.

mt6C105 OBJECT IDENTIFIER ::= { mtWorkGroupChassis 1 }
-- OBJECT-IDENTITY
--  Status
--    mandatory
--  Descr
--     5 Slot Work Group chassis

mt6C110 OBJECT IDENTIFIER ::= { mtWorkGroupChassis 2}
-- OBJECT-IDENTITY
--  Status
--   mandatory
--  Desc
--   10 Slot Work Group Chassis with ATM backplane


mtSmartSwitchRouter8 OBJECT IDENTIFIER ::= { mtWorkGroupChassis 3}
-- OBJECT-IDENTITY
--  Status
--   mandatory
--  Desc
--   8 Slot Work Group Chassis (SSR8000)

mtSmartSwitchRouter16 OBJECT IDENTIFIER ::= { mtWorkGroupChassis 4}
-- OBJECT-IDENTITY
--  Status
--   mandatory
--  Desc
--   16 Slot Work Group Chassis (SSR16000)

mtSmartSwitchRouter32 OBJECT IDENTIFIER ::= { mtWorkGroupChassis 5 }
-- OBJECT-IDENTITY
--  Status
--   mandatory
--  Desc
--   32 Slot Work Group Chassis (SSR32000)

mt6C107 OBJECT IDENTIFIER ::= { mtWorkGroupChassis 6 }
-- OBJECT-IDENTITY
--  Status
--   mandatory
--  Descr
--   7 Slot SmartSwitch 6700 Chassis.

mtWorkGroupEthernet OBJECT IDENTIFIER ::= { mtWorkGroup 2 }
-- OBJECT-IDENTITY
--  Status
--    mandatory
--  Descr
--     Work Group Ethernet Module.

mt6E102p24 OBJECT IDENTIFIER ::= { mtWorkGroupEthernet 1 }
-- OBJECT-IDENTITY
--  Status
--    mandatory
--  Descr
--     24 port SmartSwitch for the 6C105 chassis. Supports 24
--     10Base-T switch ports.

mt6E122p26 OBJECT IDENTIFIER ::= { mtWorkGroupEthernet 2 }
-- OBJECT-IDENTITY
--  Status
--    mandatory
--  Descr
--     Port SmartSwitch module for the 6C105 chassis. Supports
--     24 10Base-T switch ports and two FE-100XX PIMs.

mt6E132p25 OBJECT IDENTIFIER ::= { mtWorkGroupEthernet 3 }
-- OBJECT-IDENTITY
--  Status
--    mandatory
--  Descr
--     Port SmartSwitch module for the 6C105 chassis. Supports
--     24 10Base-T switch ports and one HSIM port

mt6H122p08 OBJECT IDENTIFIER ::= { mtWorkGroupEthernet 4 }
-- OBJECT-IDENTITY
-- Status
--   mandatory
-- Descr
--    A SmartSwitch module for the 6C105 chassis. Supports 8 Fast
--    Ethernet switch ports, 6 being dedicated RJ45s, and two optional
--    FE-PIM ports.

mt6E123p50 OBJECT IDENTIFIER ::= { mtWorkGroupEthernet 5 }
-- OBJECT-IDENTITY
-- Status
--    mandatory
-- Descr
--    A microlan module with 4 12-port repeated segments and 2 Fast
--    Ethernet FEPIM ports for the 6C105 chassis.

mt6E133p49 OBJECT IDENTIFIER ::= { mtWorkGroupEthernet 6 }
-- OBJECT-IDENTITY
-- Status
--    mandatory
-- Descr
--    A microlan module with 4 12-port repeated segments and 1 HSIM
--    port for the 6C105 chassis.

mt6E123p26 OBJECT IDENTIFIER ::= { mtWorkGroupEthernet 7 }
-- OBJECT-IDENTITY
-- Status
--    mandatory
-- Descr
--     Port SmartSwitch module for the 6C105 chassis. Supports
--     24 telco connector ports and two FE-100XX PIMs.

mt6E133p25 OBJECT IDENTIFIER ::= { mtWorkGroupEthernet 8 }
-- OBJECT-IDENTITY
-- Status
--    mandatory
-- Descr
--     Port SmartSwitch module for the 6C105 chassis. Supports
--     24 telco connector ports and one HSIM port.

mt6H133p49 OBJECT IDENTIFIER ::= { mtWorkGroupEthernet 9 }
-- OBJECT-IDENTITY
-- Status
--    deprecated
-- Descr
--     MicroLAN module with 4 10Mbs segments of up to 12 repeated ports,
--     4 100Mbs segments of up to 12 repeated ports, and an HSIM slot.
--     Each repeated port is autosensing, as to the connection speed, so
--     within each 12 port group there can be a mixture of 10Mbs and 100Mbs.

mt6H123p50 OBJECT IDENTIFIER ::= { mtWorkGroupEthernet 10 }
-- OBJECT-IDENTITY
-- Status
--    mandatory
-- Descr
--     MicroLAN module with 4 10Mbs segments of up to 12 repeated ports,
--     4 100Mbs segments of up to 12 repeated ports, and two FE-PIM slots.
--     Each repeated port is autosensing, as to the connection speed, so
--     within each 12 port group there can be a mixture of 10Mbs and 100Mbs.

mt6M146p04 OBJECT IDENTIFIER ::= { mtWorkGroupEthernet 11 }
-- OBJECT-IDENTITY
--  Status
--    mandatory
--  Descr
--    SmartSwitch 6000 module with 2 HSIM slots and 2 Fast Ethernet
--    ports (uses FEPIMs)

mt6E128p26 OBJECT IDENTIFIER ::= { mtWorkGroupEthernet 12 }
-- OBJECT-IDENTITY
--  Status
--    mandatory
--  Descr
--    SmartSwitch 6000 module with 24 Multimode fiber 10Base-FL Switch
--    ports (via ST connectors) with two optional FE-PIM ports.

mt6E138p25 OBJECT IDENTIFIER ::= { mtWorkGroupEthernet 13 }
-- OBJECT-IDENTITY
--  Status
--    mandatory
--  Descr
--    SmartSwitch 6000 module with 24 Multimode fiber 10Base-FL Switch
--    ports (via ST connectors) with one optional HSIM slot.

mt6E129p26 OBJECT IDENTIFIER ::= { mtWorkGroupEthernet 14 }
-- OBJECT-IDENTITY
--  Status
--    mandatory
--  Descr
--    SmartSwitch 6000 module with 24 single-mode fiber 10Mb switched
--    ports (via ST connectors) with two optional FE-PIM ports.

mt6E139p25 OBJECT IDENTIFIER ::= { mtWorkGroupEthernet 15 }
-- OBJECT-IDENTITY
--  Status
--    mandatory
--  Descr
--    SmartSwitch 6000 module with 24 single-mode fiber 10Mb switched
--    ports (via ST connectors) with one optional HSIM slot.

mt6H128p08 OBJECT IDENTIFIER ::= { mtWorkGroupEthernet 16 }
-- OBJECT-IDENTITY
--  Status
--    mandatory
--  Descr
--    SmartSwitch 6000 module with 6 fixed Multi-mode fiber
--    100BaseFX Switched ports (via SC connectors) and two optional
--    FE-PIM ports.

mt6H129p08 OBJECT IDENTIFIER ::= { mtWorkGroupEthernet 17 }
-- OBJECT-IDENTITY
--  Status
--    mandatory
--  Descr
--    SmartSwitch 6000 module with 6 fixed Single-mode fiber
--    100BaseFX Switched ports (via SC connectors) and two optional
--    FE-PIM ports.

mt6H122p16 OBJECT IDENTIFIER ::= { mtWorkGroupEthernet 18 }
-- OBJECT-IDENTITY
-- Status
--   mandatory
-- Descr
--    SmartSwitch 6000 module with 16 RJ45 ports.

mt6H133p37 OBJECT IDENTIFIER ::= { mtWorkGroupEthernet 19 }
-- OBJECT-IDENTITY
-- Status
--   mandatory
-- Descr
--    36 port MicroLAN module (3 RJ21 connectors) with an
--    optional HSIM slot.

mt6H202p24 OBJECT IDENTIFIER ::= { mtWorkGroupEthernet 20 }
-- OBJECT-IDENTITY
-- Status
--   mandatory
-- Descr
--    SmartSwitch 6000 module with 24 10/100 Switch ports.

mt6H252p17 OBJECT IDENTIFIER ::= { mtWorkGroupEthernet 21 }
-- OBJECT-IDENTITY
-- Status
--   mandatory
-- Descr
--    SmartSwitch 6000 module with 16 10/100 Switch ports
--    and one optional VHSIM slot.

mt6M256p04  OBJECT IDENTIFIER ::= { mtWorkGroupEthernet 22 }
-- OBJECT-IDENTITY
--  Status
--    mandatory
--  Descr
--    SmartSwitch 6000 module with 2 VHSIM/HSIM slots and 2 Fast
--    Ethernet ports (uses FEPIMs)

mt6E233p49  OBJECT IDENTIFIER ::= { mtWorkGroupEthernet 23 }
-- OBJECT-IDENTITY
--  Status
--    mandatory
--  Descr
--    SmartSwitch 6000 module with 48 10 Meg ports and an optional
--    HSIM slot.

mt6H258p17  OBJECT IDENTIFIER ::= { mtWorkGroupEthernet 24 }
-- OBJECT-IDENTITY
--  Status
--    mandatory
--  Descr
--    SmartSwitch 6000 module with 16 Multimode fiber 100BaseFX
--    switched ports (MT RJ connectors) with one optional
--    VHSIM slot.

mt6H203p24  OBJECT IDENTIFIER ::= { mtWorkGroupEthernet 25 }
-- OBJECT-IDENTITY
--  Status
--    mandatory
--  Descr
--    SmartSwitch 6000 module with 24 10/100 BaseTX  ports
--    (telco RJ21 connector).

mt6H253p13  OBJECT IDENTIFIER ::= { mtWorkGroupEthernet 26 }
-- OBJECT-IDENTITY
--  Status
--    mandatory
--  Descr
--    SmartSwitch 6000 module with 12 10/100 BaseTX  ports
--    (telco RJ21 connector) with one optional VHSIM slot.

mt6H259p17  OBJECT IDENTIFIER ::= { mtWorkGroupEthernet 27 }
-- OBJECT-IDENTITY
--  Status
--    mandatory
--  Descr
--    SmartSwitch 6000 module with 16 single mode 100 BaseFX
--    ports with one optional VHSIM slot.

mt6H262p18  OBJECT IDENTIFIER ::= { mtWorkGroupEthernet 28 }
-- OBJECT-IDENTITY
--  Status
--    mandatory
--  Descr
--    SmartSwitch 6000 module with 16 10/100 BaseTx ports (RJ45
--    connectors)  with two optional GPIM slots.

mt6H202p48  OBJECT IDENTIFIER ::= { mtWorkGroupEthernet 29 }
-- OBJECT-IDENTITY
--  Status
--    mandatory
--  Descr
--    SmartSwitch 6000 module with 48 100 BaseTx ports (RJ45
--    connectors).

mt6E253p49  OBJECT IDENTIFIER ::= { mtWorkGroupEthernet 30 }
-- OBJECT-IDENTITY
--  Status
--    mandatory
--  Descr
--    SmartSwitch 6000 module with 48 10 BaseTx ports (telco RJ21
--    connector) with one optional VHSIM/HSIM slot.

mt6H203p48  OBJECT IDENTIFIER ::= { mtWorkGroupEthernet 31 }
-- OBJECT-IDENTITY
--  Status
--    mandatory
--  Descr
--    SmartSwitch 6000 module with 46 10/100 BaseTx ports (telco RJ21
--    connector) with two optional VHSIM/HSIM slots.

mt6H303p48 OBJECT IDENTIFIER ::= { mtWorkGroupEthernet 32 }
-- OBJECT-IDENTITY
--  Status
--    mandatory
--  Descr
--    SmartSwitch 6000 module with 48 ports (telco RJ21 connector).

mt6H302p48 OBJECT IDENTIFIER ::= { mtWorkGroupEthernet 33 }
-- OBJECT-IDENTITY
--  Status
--    mandatory
--  Descr
--    SmartSwitch 6000 module with 48 ports (telco RJ45 connector).

mt6H352p25 OBJECT IDENTIFIER ::= { mtWorkGroupEthernet 34 }
-- OBJECT-IDENTITY
--  Status
--    mandatory
--  Descr
--    SmartSwitch 6000 module with 24 ports (RJ45 connector) and one optional
--    VHSIM slot.

mt6G306p06 OBJECT IDENTIFIER ::= { mtWorkGroupEthernet 35 }
-- OBJECT-IDENTITY
--  Status
--    mandatory
--  Descr
--    A second generation Giga bit module with 6 GBIC ports.

mtWorkGroupATM OBJECT IDENTIFIER ::= { mtWorkGroup 3 }
-- OBJECT-IDENTITY
--  Status
--    mandatory
--  Descr
--     Work Group ATM Module.

mt6A000 OBJECT IDENTIFIER ::= { mtWorkGroupATM 1 }
--  OBJECT-IDENTITY
--  Status
--    mandatory
--  Descr
--     SmartSwitch 6000 module with 4 IOM slots and
--     2.5 Gbps switching capabilities (6500 chassis).

mt6A000F OBJECT IDENTIFIER ::= { mtWorkGroupATM 2 }
--  OBJECT-IDENTITY
--  Status
--    mandatory
--  Descr
--     SmartSwitch 6000 module with 4 IOM slots and
--     2.5 Gbps switching capabilities (6500 chassis).

mtMMACPlus OBJECT IDENTIFIER ::= { mtExpanded 32 }
-- OBJECT-IDENTITY
--  Status
--    mandatory
--  Descr
--    The MMAC Plus  module type naming tree.

mtMMACPlusEnclose OBJECT IDENTIFIER ::= { mtMMACPlus 1 }
-- OBJECT-IDENTITY
--  Status
--    mandatory
--  Descr
--    MMAC Plus style enclosures.

mt9C114 OBJECT IDENTIFIER ::= { mtMMACPlusEnclose 1 }
-- OBJECT-IDENTITY
--  Status
--    mandatory
--  Descr
--    The 14 slot MMAC plus enclosure.

mt9C106 OBJECT IDENTIFIER ::= { mtMMACPlusEnclose 2 }
-- OBJECT-IDENTITY
--  Status
--    mandatory
--  Descr
--    The 6 slot MMAC plus enclosure.

mtMMACEM OBJECT IDENTIFIER ::= { mtMMACPlus 3 }
-- OBJECT-IDENTITY
--  Status
--    mandatory
--  Descr
--    Environmental modules for the MMAC plus.

mt9C300p01 OBJECT IDENTIFIER ::= { mtMMACEM 1 }
-- OBJECT-IDENTITY
--  Status
--    mandatory
--  Descr
--    EM with 4X40 LCD display, EPIM and 2 com ports for the
--    14 slot chassis.

mt9C306p01 OBJECT IDENTIFIER ::= { mtMMACEM 2 }
-- OBJECT-IDENTITY
--  Status
--    mandatory
--  Descr
--    System Manager with EPIM and 2 com ports for the
--    6 slot MMAC plus chassis.

mtMMACPU OBJECT IDENTIFIER ::= { mtMMACPlus 4 }
-- OBJECT-IDENTITY
--  Status
--    mandatory
--  Descr
--    MMAC Plus DC and AC power supplies and battery units.

mt9C214p1 OBJECT IDENTIFIER ::= { mtMMACPU 1 }
-- OBJECT-IDENTITY
--  Status
--    mandatory
--  Descr
--    AC Power supply with 100 - 240 volt input.

mt9C214p2 OBJECT IDENTIFIER ::= { mtMMACPU 2 }
-- OBJECT-IDENTITY
--  Status
--    mandatory
--  Descr
--    DC Power supply with -40 volt to 60 volt input.

mt9C206p1 OBJECT IDENTIFIER ::= { mtMMACPU 3 }
-- OBJECT-IDENTITY
--  Status
--    mandatory
--  Descr
--    1000 watt AC Power supply for the MMAC plus 6 slot chassis.

mt9C214p3 OBJECT IDENTIFIER ::= { mtMMACPU 4 }
-- OBJECT-IDENTITY
--  Status
--    mandatory
--  Descr
--    2000W AC  Power supply for MMAC-Plus.

mtMMACPlusFNBSingle OBJECT IDENTIFIER ::= { mtMMACPlus 5 }
-- OBJECT-IDENTITY
--  Status
--    mandatory
--  Descr
--    Modules with Flexible network bus connectivity.

mt9E133p36 OBJECT IDENTIFIER ::= { mtMMACPlusFNBSingle 1 }
-- OBJECT-IDENTITY
--  Status
--    mandatory
--  Descr
--    Ethernet with 36 ports on 3 50 pin Telcos.

mt9E122p24 OBJECT IDENTIFIER ::= { mtMMACPlusFNBSingle 2 }
-- OBJECT-IDENTITY
--  Status
--    mandatory
--  Descr
--    Ethernet with 24 RJ45 ports.

mt9E138p36 OBJECT IDENTIFIER ::= { mtMMACPlusFNBSingle 3 }
-- OBJECT-IDENTITY
--  Status
--    mandatory
--  Descr
--    Ethernet 2 slot module with 36 fiber optic ST ports.

mt9F116p01 OBJECT IDENTIFIER ::= { mtMMACPlusFNBSingle 4 }
-- OBJECT-IDENTITY
--  Status
--    mandatory
--  Descr
--    FDDI 2 port bridge with DAS front panel.

mt9F106p02 OBJECT IDENTIFIER ::= { mtMMACPlusFNBSingle 5 }
-- OBJECT-IDENTITY
--  Status
--    mandatory
--  Descr
--    FDDI repeater module with 2 sets aof A/B ports using
--    FPIMs.

mt9W116p04 OBJECT IDENTIFIER ::= { mtMMACPlusFNBSingle 6 }
-- OBJECT-IDENTITY
--  Status
--    mandatory
--  Descr
--    Wan module with 4 WPIMs with 2 i960 processors.

mt9T122p24 OBJECT IDENTIFIER ::= { mtMMACPlusFNBSingle 7 }
-- OBJECT-IDENTITY
--  Status
--    mandatory
--  Descr
--    Token Ring module with 24 port UTP bridge/router.

mt9E132p15 OBJECT IDENTIFIER ::= { mtMMACPlusFNBSingle 8 }
-- OBJECT-IDENTITY
--  Status
--    mandatory
--  Descr
--    Ethernet module with 3 networks each network having
--    1 EPIM and 4 RJ45 connectors.

mt9T122p08 OBJECT IDENTIFIER ::= { mtMMACPlusFNBSingle 9 }
-- OBJECT-IDENTITY
--  Status
--    mandatory
--  Descr
--    Token ring module with 2 segments, each segment having
--    2 TPIMs for Ring-in/Ring-out and 4 RJ45 lobes.

mt9A128p01 OBJECT IDENTIFIER ::= { mtMMACPlusFNBSingle 10 }
-- OBJECT-IDENTITY
--  Status
--    mandatory
--  Descr
--    ATM to FDDI bridge, with single ATM connection on
--    front panel and single FNB backplane connection.

mt9E106p06 OBJECT IDENTIFIER ::= { mtMMACPlusFNBSingle 11 }
-- OBJECT-IDENTITY
--  Status
--    mandatory
--  Descr
--    FDDI-FNB to 6 EPIM port bridge.

mt9E138p12 OBJECT IDENTIFIER ::= { mtMMACPlusFNBSingle 12 }
-- OBJECT-IDENTITY
--  Status
--    mandatory
--  Descr
--    Ethernet bridge with 12 fiber optic ports.

mt9F206p02 OBJECT IDENTIFIER ::= { mtMMACPlusFNBSingle 13 }
-- OBJECT-IDENTITY
--  Status
--    mandatory
--  Descr
--    FDDI repeater module with 4 FPIMs to extend FNB-1 and FNB-2
--    backplanes.

mt9A126p01 OBJECT IDENTIFIER ::= { mtMMACPlusFNBSingle 14 }
-- OBJECT-IDENTITY
--  Status
--    mandatory
--  Descr
--    ATM to FDDI bridge/router/switch module.  Having 2 APIM
--    connectors one of which is redundent.

mt9T112p24 OBJECT IDENTIFIER ::= { mtMMACPlusFNBSingle 15 }
-- OBJECT-IDENTITY
--  Status
--    mandatory
--  Descr
--    Single 24 port token ring attached to the FDDI-FNB.

mt9T162p06 OBJECT IDENTIFIER ::= { mtMMACPlusFNBSingle 16 }
-- OBJECT-IDENTITY
--  Status
--    mandatory
--  Descr
--    Token Ring switch module with 6 RJ45 ports and FDDI-FNB
--    connectivity.

mt9T125p08 OBJECT IDENTIFIER ::= { mtMMACPlusFNBSingle 17 }
-- OBJECT-IDENTITY
--  Status
--    mandatory
--  Descr
--    Token Ring MicroLAN Extension FNB module with 8 RJ-45 port
--    UTP/STP and 4 TPIMs RI/RO bridge/switch.

mt9T125p24 OBJECT IDENTIFIER ::= { mtMMACPlusFNBSingle 18 }
-- OBJECT-IDENTITY
--  Status
--    mandatory
--  Descr
--    Token Ring MicroLAN FNB module with 24 RJ-45 port UTP/STP
--    bridge/switch.

mt9E132p15s OBJECT IDENTIFIER ::= { mtMMACPlusFNBSingle 19 }
-- OBJECT-IDENTITY
--  Status
--    mandatory
--  Descr
--    Ethernet module, supporting LanviewSecure, with 3 networks each
--    network having 1 EPIM and 4 RJ45 connectors.

mt9E133p36s OBJECT IDENTIFIER ::= { mtMMACPlusFNBSingle 20 }
-- OBJECT-IDENTITY
--  Status
--    mandatory
--  Descr
--    Ethernet module, supporting LanviewSecure, with 36 ports
--    on 3 50 pin Telcos.

mt9E138p36s OBJECT IDENTIFIER ::= { mtMMACPlusFNBSingle 21 }
-- OBJECT-IDENTITY
--  Status
--    mandatory
--  Descr
--    Ethernet 2 slot module, supporting LanviewSecure,
--    with 36 fiber optic ST ports.

mt9E138p12s OBJECT IDENTIFIER ::= { mtMMACPlusFNBSingle 22 }
-- OBJECT-IDENTITY
--  Status
--    mandatory
--  Descr
--    Ethernet module, supporting LanviewSecure, with
--    12 fiber optic ports.

mtMMACPlusFNBDual OBJECT IDENTIFIER ::= { mtMMACPlus 6 }
-- OBJECT-IDENTITY
--  Status
--    mandatory
--  Descr
--    MMAC Plus modules with Dual FNB connections.

mt9F122p12 OBJECT IDENTIFIER ::= { mtMMACPlusFNBDual 1 }
-- OBJECT-IDENTITY
--  Status
--    mandatory
--  Descr
--    FDDI dual attached concentrator with 12 ports.

mt9F120p08 OBJECT IDENTIFIER ::= { mtMMACPlusFNBDual 2 }
-- OBJECT-IDENTITY
--  Status
--    mandatory
--  Descr
--    FDDI dual attached Concentrator with 8 master ports
--    with mm MIC connectors.

mt9F125p08 OBJECT IDENTIFIER ::= { mtMMACPlusFNBDual 3 }
-- OBJECT-IDENTITY
--  Status
--    mandatory
--  Descr
--    FDDI dual attached Concentrator with 8 master ports
--    with single mode fiber MIC connectors.

mt9F241P12 OBJECT IDENTIFIER ::= { mtMMACPlusFNBDual 4 }
-- OBJECT-IDENTITY
--  Status
--    mandatory
--  Descr
--    FDDI dual attached concentrator with 12 multi mode
--    fiber SC connectors.

mt9F240p08 OBJECT IDENTIFIER ::= { mtMMACPlusFNBDual 5 }
-- OBJECT IDENTITY
-- Status
--   mandatory
-- Descr
-- FDDI dual attached concentrator with 8 master ports with mm
-- MIC connectors, multi-mode, 2 FDDI Macs and 2 FDDI bandwidth
-- utilization chips.

mtMMACPlusINBSingle OBJECT IDENTIFIER ::= { mtMMACPlus 9 }
-- OBJECT-IDENTITY
--  Status
--    mandatory
--  Descr
--    MMAC plus modules with a single INB connection.

mt9E312p12 OBJECT IDENTIFIER ::= { mtMMACPlusINBSingle 1 }
-- OBJECT-IDENTITY
--  Status
--    mandatory
--  Descr
--    Ethernet 12 port bridge/switch modules with RJ45
--    connectors.

mt9E313p12 OBJECT IDENTIFIER ::= { mtMMACPlusINBSingle 2 }
-- OBJECT-IDENTITY
--  Status
--    mandatory
--  Descr
--    Ethernet 12 port bridge/switch with one 50 pin
--    connector.

mt9E318p12 OBJECT IDENTIFIER ::= { mtMMACPlusINBSingle 3 }
-- OBJECT-IDENTITY
--  Status
--    mandatory
--  Descr
--    Ethernet bridge/switch with 12 ST multi-mode
--    fiber optic ports.

mt9F310p02 OBJECT IDENTIFIER ::= { mtMMACPlusINBSingle 4 }
-- OBJECT-IDENTITY
--  Status
--    mandatory
--  Descr
--    FDDI 2 port switching module with FNB connectivity
--    and 2 sets of front panel Multi-mode fiber ports.

mt9A426p02 OBJECT IDENTIFIER ::= { mtMMACPlusINBSingle 5 }
-- OBJECT-IDENTITY
--  Status
--    mandatory
--  Descr
--    ATM Bridge/Switch module with FNB, INB2 backplane
--    connectivity and two front panel APIMs.

mt9F315p02 OBJECT IDENTIFIER ::= { mtMMACPlusINBSingle 6 }
-- OBJECT-IDENTITY
--  Status
--    mandatory
--  Descr
--    FDDI 2 port switching module with FNB connectivity
--    and 2 sets of front panel single mode fiber ports.

mt9F426p2 OBJECT IDENTIFIER ::= { mtMMACPlusINBSingle 7 }
-- OBJECT-IDENTITY
--  Status
--    mandatory
--  Descr
--    FDDI 2 port switching module with FNB and INB
--    connectivity and 4 FPIMs.

mt9E423p24 OBJECT IDENTIFIER ::= { mtMMACPlusINBSingle 8 }
-- OBJECT-IDENTITY
--  Status
--    mandatory
--  Descr
--    Ethernet 24 port bridge/switch module with INB
--    connectivity with 2 telco front panel connectors.

mt9H422p12 OBJECT IDENTIFIER ::= { mtMMACPlusINBSingle 9 }
-- OBJECT-IDENTITY
--  Status
--    mandatory
--  Descr
--    Fast Ethernet 12 port bridge/switch module with INB
--    connectivity. 11 RJ45 100BaseTX ports and one FEPIM.
--    slot.

mt9E428p12 OBJECT IDENTIFIER ::= { mtMMACPlusINBSingle 10 }
-- OBJECT-IDENTITY
--  Status
--    mandatory
--  Descr
--    Ethernet 12 port bridge/switch module with INB connectivity.
--    12 front panel MMF ST style connectors.

mt9E428p36 OBJECT IDENTIFIER ::= { mtMMACPlusINBSingle 11 }
-- OBJECT-IDENTITY
--  Status
--    mandatory
--  Descr
--    Ethernet 36 port bridge/switch dual module with INB connectivity.
--    36 front panel MMF ST style connectors.

mt9E429p12 OBJECT IDENTIFIER ::= { mtMMACPlusINBSingle 12 }
-- OBJECT-IDENTITY
--  Status
--    mandatory
--  Descr
--    Ethernet 12 port bridge/switch module with INB connectivity.
--    12 front panel SMF ST style connectors.

mt9E429p36 OBJECT IDENTIFIER ::= { mtMMACPlusINBSingle 13 }
-- OBJECT-IDENTITY
--  Status
--    mandatory
--  Descr
--    Ethernet 36 port bridge/switch dual module with INB connectivity.
--    36 front panel SMF ST style connectors.

mt9F426p03 OBJECT IDENTIFIER ::= { mtMMACPlusINBSingle 14 }
-- OBJECT-IDENTITY
--  Status
--    mandatory
--  Descr
--    FDDI 3 port bridge/switch module with INB connectivity.
--    The 3 front panel ports can support a total of 6 FPIMs.

mt9H421p12 OBJECT IDENTIFIER ::= { mtMMACPlusINBSingle 15 }
-- OBJECT-IDENTITY
--  Status
--    mandatory
--  Descr
--    Fast Ethernet 12 port switch module with INB-2 connectivity.
--    12 ports of 100FX SC connector multimode fiber.

mt9E423p36 OBJECT IDENTIFIER ::= { mtMMACPlusINBSingle 16 }
-- OBJECT-IDENTITY
--  Status
--    mandatory
--  Descr
--    Ethernet 36 port bridge/switch module with INB
--    connectivity with 3 telco front panel connectors.

mt9H429p12 OBJECT IDENTIFIER ::= { mtMMACPlusINBSingle 17 }
-- OBJECT-IDENTITY
--  Status
--    mandatory
--  Descr
--    Fast Ethernet 12 port switch module with INB-2 connectivity.
--    12 ports of 100FX SC connector single mode fiber.

mt9T425p16 OBJECT IDENTIFIER ::= { mtMMACPlusINBSingle 18 }
-- OBJECT-IDENTITY
--  Status
--    mandatory
--  Descr
--    Token Ring 16 RJ-45 port bridge/switch dual slot module with
--    INB2 connectivity.

mt9T425p24 OBJECT IDENTIFIER ::= { mtMMACPlusINBSingle 19 }
-- OBJECT-IDENTITY
--  Status
--    mandatory
--  Descr
--    Token Ring 24 RJ-45 port bridge/switch single slot module with
--    INB2 connectivity.

mt9A426p01 OBJECT IDENTIFIER ::= { mtMMACPlusINBSingle 20 }
-- OBJECT-IDENTITY
--  Status
--    mandatory
--  Descr
--    ATM Uplink module with INB2 and FNB connectivity and two
--    front panel APIMs utilizing APIM redundancy.

mt9G426p02 OBJECT IDENTIFIER ::= { mtMMACPlusINBSingle 21 }
-- OBJECT-IDENTITY
--  Status
--    mandatory
--  Descr
--    1 Gigabit single slot module with INB2 connectivity and
--    interfaces for two front panel GPIMs.

mt9H423p28 OBJECT IDENTIFIER ::= { mtMMACPlusINBSingle 22 }
-- OBJECT-IDENTITY
--  Status
--    mandatory
--  Descr
--    28 port ethernet bridge/switch module with INB connectivity.
--    Consisting of 24 10 MB ethernet ports, via 2 telco front panel
--    connectors, and 4 100 MB ethernet ports via 2 fixed RJ-45,
--    1 fixed MMF and 1 FEpim.

mt9H423p26 OBJECT IDENTIFIER ::= { mtMMACPlusINBSingle 23 }
-- OBJECT-IDENTITY
--  Status
--    mandatory
--  Descr
--    Fast Ethernet MMAC-Plus Module with INB-2 connectivity.
--    Consisting of 24 ports via 2 RJ21 Connectors, and 2 ports
--    via 2 MMF SC Connectors. This is a single slot module.

mt9G421p02 OBJECT IDENTIFIER ::= { mtMMACPlusINBSingle 24 }
-- OBJECT-IDENTITY
--  Status
--    mandatory
--  Descr
--    2 port Gigabit Ethernet INB-B MMAC-PLUS module (SmartSwitch Plus product)
--    It uses two interfaces on the front panel that connect via MultiMode
--    Fiber.

mt9M426p02 OBJECT IDENTIFIER ::= { mtMMACPlusINBSingle 25 }
-- OBJECT-IDENTITY
--  Status
--    mandatory
--  Descr
--    Dual slot module with INB-2 connectivity. The front panel consists
--    of two HSIMs.

mt9D422p16 OBJECT IDENTIFIER ::= { mtMMACPlusINBSingle 26 }
-- OBJECT-IDENTITY
--  Status
--    mandatory
--  Descr
--    Dual slot MMAC-PLUS INB module (ATU-C) with 16 ADSL ports (DMT).

mt9G429p02 OBJECT IDENTIFIER ::= { mtMMACPlusINBSingle 27 }
-- OBJECT-IDENTITY
--  Status
--    mandatory
--  Descr
--    2 port Gigabit Ethernet INB-B MMAC-PLUS module (SmartSwitch Plus
--    product).  It uses two interfaces on the front panel that connect via
--    Single mode or multimode Fiber.  The laser is a 1300 nanometer optical
--    laser.

mt9T428p16 OBJECT IDENTIFIER ::= { mtMMACPlusINBSingle 28 }
-- OBJECT-IDENTITY
--  Status
--    mandatory
--  Descr
--    Dual slot, 16-port multi-mode fiber with ST connectors.
--    TR Smartswitch module.

mt9T427p16 OBJECT IDENTIFIER ::= { mtMMACPlusINBSingle 29 }
-- OBJECT-IDENTITY
--  Status
--    mandatory
--  Descr
--    Single slot, 16-port multi-mode fiber with RJ-45 connectors.
--    TR Smartswitch module.  This connects to the INB-2 Backplane


mt3PartyFnbSingle OBJECT IDENTIFIER ::= { mtMMACPlus 10 }
-- OBJECT-IDENTITY
--  Status
--    mandatory
--  Descr
--    Third party MMAC+ modules with Single FDDI-FNB.

mt9W111p08 OBJECT IDENTIFIER ::= { mt3PartyFnbSingle 1 }
-- OBJECT-IDENTITY
--  Status
--    mandatory
--  Descr
--    Cisco 4T router with 8 synchronus serial wan ports.  With
--    single FDDI-FNB connection and SMB-1. In MMAC+ chassis.

mt9T101p04 OBJECT IDENTIFIER ::= { mt3PartyFnbSingle 2 }
-- OBJECT-IDENTITY
--  Status
--    mandatory
--  Descr
--    Cisco 4500 router with 4 DB9 Token Ring ports.  With single
--    FDDI-FNB connection in MMAC+ chassis.

mt9F106p01 OBJECT IDENTIFIER ::= { mt3PartyFnbSingle 3 }
-- OBJECT-IDENTITY
--  Status
--    mandatory
--  Descr
--    Cisco 4500 router with a FDDI DAS MIC connector on the front
--    pannel.  With single FDDI-FNB connection in MMAC+ chassis.

mt9F206p01 OBJECT IDENTIFIER ::= { mt3PartyFnbSingle 4 }
-- OBJECT-IDENTITY
--  Status
--    mandatory
--  Descr
--    Cisco 4700 router with a FDDI DAS MIC connector on the
--    front panel.  With single FDDI-FNB connection in MMAC+
--    chassis.

mt9T201p04 OBJECT IDENTIFIER ::= { mt3PartyFnbSingle 5 }
-- OBJECT-IDENTITY
--  Status
--    mandatory
--  Descr
--    Cisco 4700 router with 4 DB9 Token Ring ports.
--    With single FDDI-FNB connection in MMAC+ chassis.

mt9W211p08 OBJECT IDENTIFIER ::= { mt3PartyFnbSingle 6 }
-- OBJECT-IDENTITY
--  Status
--    mandatory
--  Descr
--    Cisco 4700 router with 8 synchronous serial WAN ports.
--    With single FDDI-FNB connection and SMB-1 in MMAC+ chassis.

mt9A221p01 OBJECT IDENTIFIER ::= { mt3PartyFnbSingle 7 }
-- OBJECT-IDENTITY
--  Status
--    mandatory
--  Descr
--    Cisco 4700 router with 1 SC MM fiber OC-3 ATM front panel
--    port.  With single FDDI-FNB connection in MMAC+ chassis.

--  mt3PartyFnbSingle 8-13 are currently reserved for future
--  modules

mt9A222p01 OBJECT IDENTIFIER ::= { mt3PartyFnbSingle 14 }
-- OBJECT-IDENTITY
--  Status
--    mandatory
--  Descr
--    Cisco 4700 router with 1 UTP OC-3 ATM front panel
--    port.  With single FDDI-FNB connection in MMAC+ chassis.

mt9A229p01 OBJECT IDENTIFIER ::= { mt3PartyFnbSingle 15 }
-- OBJECT-IDENTITY
--  Status
--    mandatory
--  Descr
--    Cisco 4700 router with 1 SC SM fiber OC-3 ATM front panel
--    port.  With single FDDI-FNB connection in MMAC+ chassis.

mtMMACPOther OBJECT IDENTIFIER ::= { mtMMACPlus 11 }
-- OBJECT-IDENTITY
--  Status
--    mandatory
--  Descr
--    This branch defines other MMAC plus modules.  This includes
--    but is not limited to modules that draw power only and
--    personal computer modules.

mt9A000 OBJECT IDENTIFIER ::= { mtMMACPOther 1 }
-- OBJECT-IDENTITY
--  Status
--    mandatory
--  Descr
--    MMAC-Plus LAN ATM Switch manufactured by Fore Systems
--    w/ 2.5Gbps switch fabric and four network module slots.

mt9P120 OBJECT IDENTIFIER ::= { mtMMACPOther 2 }
-- OBJECT-IDENTITY
--  Status
--    mandatory
--  Descr
--    A personal computer module for the MMAC plus chassis
--    based off from a sparc 5 processor.

mt9P110 OBJECT IDENTIFIER ::= { mtMMACPOther 3 }
-- OBJECT-IDENTITY
--  Status
--    mandatory
--  Descr
--    A personal computer module for the MMAC plus chassis
--    based off from the Intel 486 DX/2 66 MHz processor.

mt9X000p16 OBJECT IDENTIFIER ::= { mtMMACPOther 4 }
-- OBJECT-IDENTITY
--  Status
--    mandatory
--  Descr
--    Xylogics T1 communication server with 16 integrated modems

mt9P110mhz90 OBJECT IDENTIFIER ::= { mtMMACPOther 5 }
-- OBJECT-IDENTITY
--  Status
--    mandatory
--  Descr
--    A personal computer module for the MMAC plus chassis
--    based off from the Intel 486 DX/2 90 MHz processor.

mt9A656p04 OBJECT IDENTIFIER ::= { mtMMACPOther 6 }
-- OBJECT-IDENTITY
--  Status
--    mandatory
--  Descr
--    MMAC-Plus single slot 5 Gbps ATM Switch with 4
--    ANIM slots and CTM connectivity.

mt9A600p04 OBJECT IDENTIFIER ::= { mtMMACPOther 7 }
-- OBJECT-IDENTITY
--  Status
--    mandatory
--  Descr
--    MMAC-Plus single slot 5.4 Gbps ATM Switch with 4
--    ANIM slots.

mt9A686p04 OBJECT IDENTIFIER ::= { mtMMACPOther 8 }
-- OBJECT-IDENTITY
--  Status
--    mandatory
--  Descr
--    MMAC-Plus single slot 5.4 Gbps ATM Switch with 4
--    ANIM slots and CTM connectivity.

mt9A100 OBJECT IDENTIFIER ::= { mtMMACPOther 9 }
-- OBJECT-IDENTITY
--  Status
--    mandatory
--  Descr
--    MMAC-Plus single slot 2.5 Gbps ATM Switch with 4
--    Input Network Module (IOM) slots.

mtMMACPlusNortel OBJECT IDENTIFIER ::= { mtMMACPlus 12 }
-- OBJECT-IDENTITY
--  Status
--    mandatory
--  Descr
--    This branch defines Cabletron/Nortel MMAC-Plus products.

mt9N050 OBJECT IDENTIFIER ::= { mtMMACPlusNortel 1 }
-- OBJECT-IDENTITY
--  Status
--    mandatory
--  Descr
--    An MMAC-PLUS option module, which consumes six contiguous
--    slots of an MMAC-PLUS chassis.  The device provides
--    MMAC-PLUS integration for a maximum of five, off-the-shelf,
--    Northern Telecom Passport Interface modules.

mtMMACPlusINBDual OBJECT IDENTIFIER ::= { mtMMACPlus 13 }
-- OBJECT-IDENTITY
--  Status
--    mandatory
--  Descr
--    This branch defines MMAC-Plus products with dual INB
--    connections.

mt9H532p18      OBJECT IDENTIFIER ::= { mtMMACPlusINBDual 1 }
-- OBJECT-IDENTITY
-- Status
--   mandatory
-- Descr
--   An MMAC-PLUS 100Base-TX module which supports 16 RJ45 10/100
--   ports and two gigabit port interfaces via GPIM's.

mt9H531p18      OBJECT IDENTIFIER ::= { mtMMACPlusINBDual 2 }
-- OBJECT-IDENTITY
-- Status
--   mandatory
-- Descr
--   An MMAC-PLUS 100Base-FX module which supports 16 100 Meg MMF
--   ports (mini MTRJ transcievers) and two gigabit port
--   interfaces via GPIM's.

mt9H539p18        OBJECT IDENTIFIER ::= { mtMMACPlusINBDual 3 }
-- OBJECT-IDENTITY
-- Status
--   mandatory
-- Descr
--   An MMAC-PLUS 100Base-FX module which supports 16 100 Meg SMF
--   ports (mini MTRJ transcievers) and two gigabit port
--   interfaces via GPIM's.

mt9H532p17        OBJECT IDENTIFIER ::= { mtMMACPlusINBDual 4 }
-- OBJECT-IDENTITY
-- Status
--   mandatory
-- Descr
--   An MMAC-PLUS 100Base-TX module which supports 16 10/100
--   ports and a VHSIM/HSIM slot.

mt9H531p17        OBJECT IDENTIFIER ::= { mtMMACPlusINBDual 5 }
-- OBJECT-IDENTITY
-- Status
--   mandatory
-- Descr
--   An MMAC-PLUS 100Base-FX module which supports 16 100 Meg MMF
--   ports (mini MTRJ transcievers) and a VHSIM/HSIM slot.

mt9H539p17        OBJECT IDENTIFIER ::= { mtMMACPlusINBDual 6 }
-- OBJECT-IDENTITY
-- Status
--   mandatory
-- Descr
--   An MMAC-PLUS 100Base-FX module which supports 16 100 Meg SMF
--   ports (mini MTRJ transcievers) and a VHSIM/HSIM slot.

mt9G536p04        OBJECT IDENTIFIER ::= { mtMMACPlusINBDual 7 }
-- OBJECT-IDENTITY
-- Status
--   mandatory
-- Descr
--   An MMAC-PLUS module which supports four gigabit port
--   interfaces via GPIM's.

mt9H532p24        OBJECT IDENTIFIER ::= { mtMMACPlusINBDual 8 }
-- OBJECT-IDENTITY
-- Status
--   mandatory
-- Descr
--   An MMAC-PLUS 100Base-TX module which supports 24 RJ-45
--   ports each supporting 10/100 BaseT.

mt9H531p24        OBJECT IDENTIFIER ::= { mtMMACPlusINBDual 9 }
-- OBJECT-IDENTITY
-- Status
--   mandatory
-- Descr
--   An MMAC-PLUS 100Base-FX module which supports 24 100 Meg MMF
--   ports (mini MTRJ transcievers).

mt9H539p24        OBJECT IDENTIFIER ::= { mtMMACPlusINBDual 10 }
-- OBJECT-IDENTITY
-- Status
--   mandatory
-- Descr
--   An MMAC-PLUS 100Base-FX module which supports 24 100 Meg SMF
--   ports (mini MTRJ transcievers).

mt9M546p04        OBJECT IDENTIFIER ::= { mtMMACPlusINBDual 11 }
-- OBJECT-IDENTITY
-- Status
--   mandatory
-- Descr
--   An MMAC-PLUS dual slot module which supports 2 VHSIM/HSIM
--   ports and 2 FEPIM slots.

mt9H533p24        OBJECT IDENTIFIER ::= { mtMMACPlusINBDual 12 }
-- OBJECT-IDENTITY
-- Status
--   mandatory
-- Descr
--   A 24 port MMAC-PLUS 10/100Base Ethernet Smartswitch module with
--   dual RJ-21 Telco connectors.

mt9H533p48        OBJECT IDENTIFIER ::= { mtMMACPlusINBDual 13 }
-- OBJECT-IDENTITY
-- Status
--   mandatory
-- Descr
--   A 48 port MMAC-PLUS 10/100Base Ethernet Smartswitch module with
--   quad RJ-21 Telco connectors.

mt9E531p24        OBJECT IDENTIFIER ::= { mtMMACPlusINBDual 14 }
-- OBJECT-IDENTITY
--  Status
--   mandatory
--  Descr
--   A 38-Special 24 port 10Base-FL Ethernet Smartswitch module with
--   MT-RJ connectors.

mtSSR OBJECT IDENTIFIER ::= { mtExpanded 33 }
-- OBJECT-IDENTITY
-- Status
--   mandatory
-- Descr
--   The Smart Switch Router naming Tree

mtSSRStandAlone OBJECT IDENTIFIER ::= { mtSSR 1 }
-- OBJECT-IDENTITY
-- Status
--   mandatory
-- Descr
--   The Smart Switch Router StandAlone module naming Tree

mtSSR2Expansion OBJECT IDENTIFIER ::= { mtSSR 2 }
-- OBJECT-IDENTITY
-- Status
--   mandatory
-- Descr
--   The Smart Switch Router Expansion module naming Tree
--   Modules under this branch are supported by the SSR 2000
--   series of products.

mtSSR8Expansion OBJECT IDENTIFIER ::= { mtSSR 3 }
-- OBJECT-IDENTITY
-- Status
--   mandatory
-- Descr
--   The Smart Switch Router Expansion module naming Tree
--   Modules under this branch are supported by the SSR
--   8000/8600 series of products.

mtSSR6Expansion OBJECT IDENTIFIER ::= { mtSSR 4 }
-- OBJECT-IDENTITY
-- Status
--   mandatory
-- Descr
--   The Smart Switch Router Expansion module naming Tree
--   Modules under this branch are supported by the SS6000
--   series of products.

mtHSIMSSR  OBJECT IDENTIFIER ::= { mtSSR 5 }
-- OBJECT-IDENTITY
-- Status
--   mandatory
-- Descr
--   The Smart Switch Router HSIM module naming Tree
--   Modules under this branch are supported by the SS6000
--   and SS2000 carrier modules.



mtSSR2SX OBJECT IDENTIFIER ::= { mtSSR2Expansion 1 }
-- OBJECT-IDENTITY
-- Status
--   mandatory
-- Descr
--  2 port 1000 Base-SX expansion module for SSR 2000

mtSSR2LX OBJECT IDENTIFIER ::= { mtSSR2Expansion 2 }
-- OBJECT-IDENTITY
-- Status
--   mandatory
-- Descr
--  2 port 1000 Base-LX expansion module for SSR 2000

mtSSR2TX OBJECT IDENTIFIER ::= { mtSSR2Expansion 3 }
-- OBJECT-IDENTITY
-- Status
--   mandatory
-- Descr
--  8 port 10/100 Base-TX expansion module for SSR 2000

mtSSR2FX OBJECT IDENTIFIER ::= { mtSSR2Expansion 4 }
-- OBJECT-IDENTITY
-- Status
--   mandatory
-- Descr
--  8 port 100 Base-FX expansion module for SSR 2000
--  with MT-RJ connectors.

mtSSR2SER OBJECT IDENTIFIER ::= { mtSSR2Expansion 5 }
-- OBJECT-IDENTITY
-- Status
--   mandatory
-- Descr
--  Dual port serial module for SSR 2000.

mtSSR2SERC OBJECT IDENTIFIER ::= { mtSSR2Expansion 6 }
-- OBJECT-IDENTITY
-- Status
--   mandatory
-- Descr
--  Dual port serial module with compression for SSR 2000.

mtSSR2SERCE OBJECT IDENTIFIER ::= { mtSSR2Expansion 7 }
-- OBJECT-IDENTITY
-- Status
--   mandatory
-- Descr
--  Dual port serial module with compression and encryption
--  for SSR 2000.


mtIA1100  OBJECT IDENTIFIER ::= { mtSSR2Expansion 8 }
mtIA1200 OBJECT IDENTIFIER ::= { mtSSR2Expansion 9 }

mtSSRHTX12p08 OBJECT IDENTIFIER ::= { mtSSR8Expansion 1 }
-- OBJECT-IDENTITY
-- Status
--   mandatory
-- Descr
--  8 port 10/100 Base-TX  module for SSR8000/8600
--  with Cat 5 RJ-45 ports (4 MB of memory).

mtSSRHTX22p08 OBJECT IDENTIFIER ::= { mtSSR8Expansion 2 }
-- OBJECT-IDENTITY
-- Status
--   mandatory
-- Descr
--  8 port 10/100 Base-TX  module for SSR8000/8600
--  with Cat 5 RJ-45 ports (16 MB of memory).

mtSSRHFX11p08 OBJECT IDENTIFIER ::= { mtSSR8Expansion 3 }
-- OBJECT-IDENTITY
-- Status
--   mandatory
-- Descr
--  8 port 100 Base-FX  module for SSR8000/8600
--  with MMF SC ports and 4 MB of memory.

mtSSRHFX21p08 OBJECT IDENTIFIER ::= { mtSSR8Expansion 4 }
-- OBJECT-IDENTITY
-- Status
--   mandatory
-- Descr
--  8 port 100 Base-FX  module for SSR8000/8600
--  with MMF SC ports and 16 MB of memory.

mtSSRGSX11p02 OBJECT IDENTIFIER ::= { mtSSR8Expansion 5 }
-- OBJECT-IDENTITY
-- Status
--   mandatory
-- Descr
--  2 port 1000Base-SX  module for SSR8000/8600
--  with SCSX ports (for MMF only) and 4 MB of memory.

mtSSRGSX21p02 OBJECT IDENTIFIER ::= { mtSSR8Expansion 6 }
-- OBJECT-IDENTITY
-- Status
--   mandatory
-- Descr
--  2 port 1000Base-SX  module for SSR8000/8600
--  with SCSX (for MMF only) and 16 MB of memory.

mtSSRGLX19p02 OBJECT IDENTIFIER ::= { mtSSR8Expansion 7 }
-- OBJECT-IDENTITY
-- Status
--   mandatory
-- Descr
--  2 port 1000Base-LX module for SSR8000/8600
--  with SCLX ports (for MMF or SMF) and 4 MB of memory.

mtSSRGLX29p02 OBJECT IDENTIFIER ::= { mtSSR8Expansion 8 }
-- OBJECT-IDENTITY
-- Status
--   mandatory
-- Descr
--  2 port 1000 Base-LX module for SSR8000/8600
--  with SCLX ports (for MMF or SMF) and 16 MB of memory.

mtSSRGLX70p01 OBJECT IDENTIFIER ::= { mtSSR8Expansion 9 }
-- OBJECT-IDENTITY
-- Status
--   mandatory
-- Descr
--  1 port 70km 1000 BaseLX Gigabit Ethernet module for SSR8000/8600
--  with 16MB memory.

mtSSRHFX29p08 OBJECT IDENTIFIER ::= { mtSSR8Expansion 10 }
-- OBJECT-IDENTITY
-- Status
--   mandatory
-- Descr
--  8 port 1000 Base-FX  module for SSR8000/8600
--  with 16 MB of memory.

mtSSRSERCp04 OBJECT IDENTIFIER ::= { mtSSR8Expansion 11 }
-- OBJECT-IDENTITY
-- Status
--   mandatory
-- Descr
--  Quad port serial module with compression for SSR8000/8600

mtSSRSERCEp04 OBJECT IDENTIFIER ::= { mtSSR8Expansion 12 }
-- OBJECT-IDENTITY
-- Status
--   mandatory
-- Descr
--  Quad port serial module with compression and encryption
--  for SSR8000/8600

mtSSRHSSIp02 OBJECT IDENTIFIER ::= { mtSSR8Expansion 13 }
-- OBJECT-IDENTITY
-- Status
--   mandatory
-- Descr
--  Dual port HSSI module for SSR8000/8600

mt6SSRM-02 OBJECT IDENTIFIER ::= { mtSSR6Expansion 1 }
-- OBJECT-IDENTITY
-- Status
--   mandatory
-- Descr
--  SmartSwitchRouter module for the 6000 chassis.
--  This module has two expansion slots for line cards.

mt6SSRLC-LX OBJECT IDENTIFIER ::= { mtSSR6Expansion 2 }
-- OBJECT-IDENTITY
-- Status
--   mandatory
-- Descr
--  2 port 1000 Base-LX expansion module for 6SSRM-02 module.

mt6SSRLC-TX OBJECT IDENTIFIER ::= { mtSSR6Expansion 3 }
-- OBJECT-IDENTITY
-- Status
--   mandatory
-- Descr
--  8 port 10/100 Base-TX expansion module for 6SSRM-02 module

mt6SSRLC-FX OBJECT IDENTIFIER ::= { mtSSR6Expansion 4 }
-- OBJECT-IDENTITY
-- Status
--   mandatory
-- Descr
--  8 port 100 Base-FX expansion module for 6SSRM-02 module
--  with MT-RJ connectors.

mt6SSRLC-SX OBJECT IDENTIFIER ::= { mtSSR6Expansion 5 }
-- OBJECT-IDENTITY
-- Status
--   mandatory
-- Descr
--  2 port 1000 Base-SX expansion module for 6SSRM-02 module

mt6SSRLC-SER OBJECT IDENTIFIER ::= { mtSSR6Expansion 6 }
-- OBJECT-IDENTITY
-- Status
--   mandatory
-- Descr
--  Dual port serial module for 6SSRM-02 module.

mt6SSRLC-SERC OBJECT IDENTIFIER ::= { mtSSR6Expansion 7 }
-- OBJECT-IDENTITY
-- Status
--   mandatory
-- Descr
--  4 port serial module with compression for 6SSRM-02 module.

mt6SSRLC-SERCE OBJECT IDENTIFIER ::= { mtSSR6Expansion 8 }
-- OBJECT-IDENTITY
-- Status
--   mandatory
-- Descr
--  4 port serial module with compression and encryption
--  for the 6SSRM-02 module.

mt6SSRLC-LX70  OBJECT IDENTIFIER ::= { mtSSR6Expansion 9 }
-- OBJECT-IDENTITY
-- Status
--   mandatory
-- Descr
--  Single port 1000Base-LX (70 km)Line Card for 6SSRM-02 module.

mtSSR2B OBJECT IDENTIFIER ::= { mtSSRStandAlone 1 }
-- OBJECT-IDENTITY
-- Status
--   mandatory
-- Descr
--  24 Port 10/100 Base-TX base unit with one expansion
--  slot.  Includes SSR Router Services software.

mtSSR2BPS OBJECT IDENTIFIER ::= { mtSSRStandAlone 2 }
-- OBJECT-IDENTITY
-- Status
--   mandatory
-- Descr
--  24 Port 10/100 Base-TX base unit with one expansion
--  slot.  Includes redundant power supply.

mtSSR2100 OBJECT IDENTIFIER ::= { mtSSRStandAlone 3 }
-- OBJECT IDENTITY
-- Status
--   mandatory
-- Descr
--  8 Port 1000 Base-SX standalone SmartSwitchRouter.

mtSSR510 OBJECT IDENTIFIER ::= { mtSSRStandAlone 4 }
-- OBJECT IDENTITY
-- Status
--   mandatory
-- Descr
--  3 port standalone SmartSwitchRouter supporting 1 RJ45 10 Base-TX
--  port, 1 T1/E1 synchronous WAN port and one Basic Rate
--  ISDN port.

mtSSR520 OBJECT IDENTIFIER ::= { mtSSRStandAlone 5 }
-- OBJECT IDENTITY
-- Status
--   mandatory
-- Descr
--  3 port standalone SmartSwitchRouter supporting 1 RJ45 10 Base-TX
--  port and 2 T1/E1 synchronous WAN port.

mtSSR600S OBJECT IDENTIFIER ::= { mtSSRStandAlone 6 }
-- OBJECT IDENTITY
-- Status
--   mandatory
-- Descr
--  A 4 port standalone SmartSwitchRouter supporting 2 RJ45 10/100 Base-TX
--  ports and 2 SWPIM slots.

mtSSR600D OBJECT IDENTIFIER ::= { mtSSRStandAlone 7 }
-- OBJECT IDENTITY
-- Status
--   mandatory
-- Descr
--  A 4 port standalone SmartSwitchRouter supporting 2 RJ45 10/100 Base-TX
--  ports and 2 SWPIM slots. This supports redundant power supplies.

mtSSR710T1 OBJECT IDENTIFIER ::= { mtSSRStandAlone 8 }
-- OBJECT IDENTITY
-- Status
--   mandatory
-- Descr
--  An 8 port standalone SmartSwitchRouter supporting 2 RJ45 10 Base-TX
--  ports, 2 RJ45 Primary Rate ISDN ports and 4 T1 synchronous WAN ports.


mtSSR710E1 OBJECT IDENTIFIER ::= { mtSSRStandAlone 9 }
-- OBJECT IDENTITY
-- Status
--   mandatory
-- Descr
--  An 8 port standalone SmartSwitchRouter supporting 2 RJ45 10 Base-TX
--  ports, 2 RJ45 Primary Rate ISDN ports and 4 E1 synchronous WAN ports.

mtSSR720 OBJECT IDENTIFIER ::= { mtSSRStandAlone 10 }
-- OBJECT IDENTITY
-- Status
--   mandatory
-- Descr
--  A 10 port standalone SmartSwitchRouter supporting 2 RJ45 10 Base-TX
--  ports and 8 T1/E1 synchronous WAN ports.



mtHSIMSSR600 OBJECT IDENTIFIER ::= { mtHSIMSSR 1 }
-- OBJECT IDENTITY
-- Status
--   mandatory
-- Descr
--  A 3 port HSIM SmartSwitchRouter module supporting 1 RJ45 10/100 Base-TX
--  ports and 2 SWPIM slots.

ctIfTypes OBJECT IDENTIFIER ::= { namingTree 10 }
-- OBJECT-IDENTITY
--  Status
--    mandatory

ctIfBackPlane OBJECT IDENTIFIER ::= { ctIfTypes 1 }
-- OBJECT-IDENTITY
--  Status
--    mandatory

ctIfNonFNB OBJECT IDENTIFIER ::= { ctIfBackPlane 1 }
-- OBJECT-IDENTITY
--  Status
--    mandatory

ctIfFNB OBJECT IDENTIFIER ::= { ctIfBackPlane 2 }
-- OBJECT-IDENTITY
--  Status
--    mandatory

ctIfFrontPanel OBJECT IDENTIFIER ::= { ctIfTypes 2 }
-- OBJECT-IDENTITY
--  Status
--    mandatory

ctHsimInterconnect OBJECT IDENTIFIER ::= { ctIfTypes 3 }
-- OBJECT-IDENTITY
--  Status
--    mandatory

ctResourceType OBJECT IDENTIFIER ::= { namingTree 11 }
-- OBJECT-IDENTITY
--  Status
--    mandatory
--  Descr
--    Identifies the different chassis resource types.  Notice
--    that these may also identify interface types since devices
--    have interfaces to many of the resources.

ctFDDIFnbBP OBJECT IDENTIFIER ::= { ctResourceType 1 }
-- OBJECT-IDENTITY
--  Status
--    mandatory
--  Descr
--    The MMAC plus FDDI FNB backplane.

ctFDDIFnbBP1 OBJECT IDENTIFIER ::= { ctFDDIFnbBP 1 }
-- OBJECT-IDENTITY
--  Status
--    mandatory
--  Descr
--    The MMAC plus FDDI FNB 1 backplane.

ctFDDIFnbBP2 OBJECT IDENTIFIER ::= { ctFDDIFnbBP 2 }
-- OBJECT-IDENTITY
--  Status
--    mandatory
--  Descr
--    The MMAC plus FDDI FNB 2 backplane.

ctSMB1 OBJECT IDENTIFIER ::= { ctResourceType 2 }
-- OBJECT-IDENTITY
--  Status
--    mandatory
--  Descr
--    The MMAC plus SMB1 bus.

ctSMB10 OBJECT IDENTIFIER ::= { ctResourceType 3 }
-- OBJECT-IDENTITY
--  Status
--    mandatory
--  Descr
--    The MMAC plus SMB10 bus.

-- ctINB OBJECT IDENTIFIER ::= { ctResourceType 4 }
-- OBJECT-IDENTITY
--  Status
--    deprecated
--  Descr
--    The MMAC plus INB bus.

ctFrontPanel OBJECT IDENTIFIER ::= { ctResourceType 5 }
-- OBJECT-IDENTITY
--  Status
--    mandatory
--  Descr
--    The MMAC plus front panel types.  This defines a branch
--    for all front panel types.  Note that these types also
--    apply to the MMAC SmartSwitch product line.

ctINB1 OBJECT IDENTIFIER ::= { ctResourceType 6 }
-- OBJECT-IDENTITY
--  Status
--    mandatory
--  Descr
--    The MMAC plus INB1 bus.

ctINB2 OBJECT IDENTIFIER ::= { ctResourceType 7 }
-- OBJECT-IDENTITY
--  Status
--    mandatory
--  Descr
--    The MMAC plus INB2 bus.

ctHostPort OBJECT IDENTIFIER ::= { ctResourceType 8 }
-- OBJECT-IDENTITY
--  Status
--    mandatory
--  Descr
--    Defines an MMAC plus host interface type.
--    Note that this type also applies to the MMAC
--    SmartSwitch product line.

ctCTM OBJECT IDENTIFIER ::= { ctResourceType 9 }
-- OBJECT-IDENTITY
--  Status
--    mandatory
--  Descr
--    The MMAC plus Cell Transfer Matrix.

ctWorkGroupBPport OBJECT IDENTIFIER ::= { ctResourceType 10 }
-- OBJECT-IDENTITY
--  Status
--    mandatory
--  Descr
--    A branch for the backplane port resource types for the new
--    Work Group chassis.

ctATMVirtual  OBJECT IDENTIFIER ::= { ctResourceType 11 }
-- OBJECT-IDENTITY
--  Status
--    mandatory
--  Descr
--    ATM Virtual types.

ctATMVirtualLec  OBJECT IDENTIFIER ::= { ctATMVirtual 1 }
--  Status
--    mandatory
--  Descr
--    Defines this Virtual LAN Emulation Client.

ctATMVirtualPvc  OBJECT IDENTIFIER ::= { ctATMVirtual 2 }
--  Status
--    mandatory
--  Descr
--    Defines this Virtual Permanent Virtual Circuit.

ctATMVirtualClip  OBJECT IDENTIFIER ::= { ctATMVirtual 3 }
--  Status
--    mandatory
--  Descr
--    Defines this Virtual Classic IP Circuit.

ctATMVirtualSvc OBJECT IDENTIFIER ::= { ctATMVirtual 4 }
-- Status
--   mandatory
-- Descr
--   Defines this Virtual Switched Virtual Circuit.

ctIfSpecific OBJECT IDENTIFIER ::= { ctResourceType 12 }
--  Status
--    mandatory
--  Descr
--    Returning this value will result in a non-display of the port on all
--  NMS screens.

ctSmartTrunkVirtual OBJECT IDENTIFIER ::= { ctResourceType 13 }
--  Status
--    mandatory
--  Descr
--     Defines this interface as a Cabletron SmartTrunk (HuntGroup)
--     Virtual Interface.


ctMMACPlusBPport OBJECT IDENTIFIER ::= { ctResourceType 14 }
 -- OBJECT-IDENTITY
 --  Status
 --    mandatory
 --  Descr
 --    A branch for the backplane port resource types for the
 --    MMAC Plus chassis.  Initially, the types in this branch are only
 --    used for the new 9x5xx-xx boards.

ctMMACPlusBPport1 OBJECT IDENTIFIER ::= { ctMMACPlusBPport 1 }
 -- OBJECT-IDENTITY
 --  Status
 --    mandatory
 --  Descr
 --    The resource type for the backplane port connection
 --    to slot 1 of the MMAC Plus chassis.

 ctMMACPlusBPport2 OBJECT IDENTIFIER ::= { ctMMACPlusBPport 2 }
 -- OBJECT-IDENTITY
 --  Status
 --    mandatory
 --  Descr
 --    The resource type for the backplane port connection
 --    to slot 2 of the MMAC Plus chassis.

 ctMMACPlusBPport3 OBJECT IDENTIFIER ::= { ctMMACPlusBPport 3 }
 -- OBJECT-IDENTITY
 --  Status
 --    mandatory
 --  Descr
 --    The resource type for the backplane port connection
 --    to slot 3 of the MMAC Plus chassis.

 ctMMACPlusBPport4 OBJECT IDENTIFIER ::= { ctMMACPlusBPport 4 }
 -- OBJECT-IDENTITY
 --  Status
 --    mandatory
 --  Descr
 --    The resource type for the backplane port connection
 --    to slot 4 of the MMAC Plus chassis.

 ctMMACPlusBPport5 OBJECT IDENTIFIER ::= { ctMMACPlusBPport 5 }
 -- OBJECT-IDENTITY
 --  Status
 --    mandatory
 --  Descr
 --    The resource type for the backplane port connection
 --    to slot 5 of the MMAC Plus chassis.

 ctMMACPlusBPport6 OBJECT IDENTIFIER ::= { ctMMACPlusBPport 6 }
 -- OBJECT-IDENTITY
 --  Status
 --    mandatory
 --  Descr
 --    The resource type for the backplane port connection
 --    to slot 6 of the MMAC Plus chassis.

 ctMMACPlusBPport7 OBJECT IDENTIFIER ::= { ctMMACPlusBPport 7 }
 -- OBJECT-IDENTITY
 --  Status
 --    mandatory
 --  Descr
 --    The resource type for the backplane port connection
 --    to slot 7 of the MMAC Plus chassis.

 ctMMACPlusBPport8 OBJECT IDENTIFIER ::= { ctMMACPlusBPport 8 }
 -- OBJECT-IDENTITY
 --  Status
 --    mandatory
 --  Descr
 --    The resource type for the backplane port connection
 --    to slot 8 of the MMAC Plus chassis.

 ctMMACPlusBPport9 OBJECT IDENTIFIER ::= { ctMMACPlusBPport 9 }
 -- OBJECT-IDENTITY
 --  Status
 --    mandatory
 --  Descr
 --    The resource type for the backplane port connection
 --    to slot 9 of the MMAC Plus chassis.

 ctMMACPlusBPport10 OBJECT IDENTIFIER ::= { ctMMACPlusBPport 10 }
 -- OBJECT-IDENTITY
 --  Status
 --    mandatory
 --  Descr
 --    The resource type for the backplane port connection
 --    to slot 10 of the MMAC Plus chassis.

 ctMMACPlusBPport11 OBJECT IDENTIFIER ::= { ctMMACPlusBPport 11 }
 -- OBJECT-IDENTITY
 --  Status
 --    mandatory
 --  Descr
 --    The resource type for the backplane port connection
 --    to slot 11 of the MMAC Plus chassis.

 ctMMACPlusBPport12 OBJECT IDENTIFIER ::= { ctMMACPlusBPport 12 }
 -- OBJECT-IDENTITY
 --  Status
 --    mandatory
 --  Descr
 --    The resource type for the backplane port connection
 --    to slot 12 of the MMAC Plus chassis.

 ctMMACPlusBPport13 OBJECT IDENTIFIER ::= { ctMMACPlusBPport 13 }
 -- OBJECT-IDENTITY
 --  Status
 --    mandatory
 --  Descr
 --    The resource type for the backplane port connection
 --    to slot 13 of the MMAC Plus chassis.

 ctMMACPlusBPport14 OBJECT IDENTIFIER ::= { ctMMACPlusBPport 14 }
 -- OBJECT-IDENTITY
 --  Status
 --    mandatory
 --  Descr
 --    The resource type for the backplane port connection
 --    to slot 14 of the MMAC Plus chassis.


ctWorkGroupBPport1 OBJECT IDENTIFIER ::= { ctWorkGroupBPport 1 }
-- OBJECT-IDENTITY
--  Status
--    mandatory
--  Descr
--    The resource type for the backplane port connection in slot 1
--    of the new Work Group chassis.

ctWorkGroupBPport2 OBJECT IDENTIFIER ::= { ctWorkGroupBPport 2 }
-- OBJECT-IDENTITY
--  Status
--    mandatory
--  Descr
--    The resource type for the backplane port connection in slot
--    2 of the new Work Group chassis.

ctWorkGroupBPport3 OBJECT IDENTIFIER ::= { ctWorkGroupBPport 3 }
-- OBJECT-IDENTITY
--  Status
--    mandatory
--  Descr
--    The resource type for the backplane port connection in slot 3
--    of the new Work Group chassis.

ctWorkGroupBPport4 OBJECT IDENTIFIER ::= { ctWorkGroupBPport 4 }
-- OBJECT-IDENTITY
--  Status
--    mandatory
--  Descr
--    The resource type for the backplane port connection in slot 4
--    of the new Work Group chassis.

ctWorkGroupBPport5 OBJECT IDENTIFIER ::= { ctWorkGroupBPport 5 }
-- OBJECT-IDENTITY
--  Status
--    mandatory
--  Descr
--    The resource type for the backplane port connection in slot 5
--    of the new Work Group chassis.

ctFDDIFrontPanel OBJECT IDENTIFIER ::= { ctFrontPanel 1 }
-- OBJECT-IDENTITY
--  Status
--    mandatory
--  Descr
--    Defines FDDI front panel connections.

ctFDDIFrontPanel1 OBJECT IDENTIFIER ::= { ctFDDIFrontPanel 1 }
-- OBJECT-IDENTITY
--  Status
--    mandatory
--  Descr
--    Defines the FDDI front panel 1 connection.

ctFDDIFrontPanel2 OBJECT IDENTIFIER ::= { ctFDDIFrontPanel 2 }
-- OBJECT-IDENTITY
--  Status
--    mandatory
--  Descr
--    Defines the FDDI front panel 2 connection.

ctFDDIFrontPanel3 OBJECT IDENTIFIER ::= { ctFDDIFrontPanel 3 }
-- OBJECT-IDENTITY
--  Status
--    mandatory
--  Descr
--    Defines the FDDI front panel 3 connection.

ctFDDIFrontPanel4 OBJECT IDENTIFIER ::= { ctFDDIFrontPanel 4 }
-- OBJECT-IDENTITY
--  Status
--    mandatory
--  Descr
--    Defines the FDDI front panel 4 connection.

ctFDDIFrontPanel5 OBJECT IDENTIFIER ::= { ctFDDIFrontPanel 5 }
-- OBJECT-IDENTITY
--  Status
--    mandatory
--  Descr
--    Defines the FDDI front panel 5 connection.

ctFDDIFrontPanel6 OBJECT IDENTIFIER ::= { ctFDDIFrontPanel 6 }
-- OBJECT-IDENTITY
--  Status
--    mandatory
--  Descr
--    Defines the FDDI front panel 6 connection.

ctFDDIFrontPanel7 OBJECT IDENTIFIER ::= { ctFDDIFrontPanel 7 }
-- OBJECT-IDENTITY
--  Status
--    mandatory
--  Descr
--    Defines the FDDI front panel 7 connection.

ctFDDIFrontPanel8 OBJECT IDENTIFIER ::= { ctFDDIFrontPanel 8 }
-- OBJECT-IDENTITY
--  Status
--    mandatory
--  Descr
--    Defines the FDDI front panel 8 connection.

ctFDDIFrontPanel9 OBJECT IDENTIFIER ::= { ctFDDIFrontPanel 9 }
-- OBJECT-IDENTITY
--  Status
--    mandatory
--  Descr
--    Defines the FDDI front panel 9 connection.

ctFDDIFrontPanel10 OBJECT IDENTIFIER ::= { ctFDDIFrontPanel 10 }
-- OBJECT-IDENTITY
--  Status
--    mandatory
--  Descr
--    Defines the FDDI front panel 10 connection.

ctFDDIFrontPanel11 OBJECT IDENTIFIER ::= { ctFDDIFrontPanel 11 }
-- OBJECT-IDENTITY
--  Status
--    mandatory
--  Descr
--    Defines the FDDI front panel 11 connection.

ctFDDIFrontPanel12 OBJECT IDENTIFIER ::= { ctFDDIFrontPanel 12 }
-- OBJECT-IDENTITY
--  Status
--    mandatory
--  Descr
--    Defines the FDDI front panel 12 connection.

ctEthernetFrontPanel OBJECT IDENTIFIER ::= { ctFrontPanel 2 }
-- OBJECT-IDENTITY
--  Status
--    mandatory
--  Descr
--    Defines Ethernet front panel connections.

ctFrontPanelATM OBJECT IDENTIFIER ::= { ctFrontPanel 3 }
-- OBJECT-IDENTITY
--  Status
--    mandatory
--  Descr
--    Defines ATM front panel connections.

ctFrontPanelATM1  OBJECT IDENTIFIER ::= { ctFrontPanelATM 1 }
--  Status
--    mandatory
--  Descr
--   Defines this ATM interface as having one physical
--   interface. Not capable of port redundency.

ctFrontPanelATM2  OBJECT IDENTIFIER ::= { ctFrontPanelATM 2 }
--  Status
--    mandatory
--  Descr
--   Defines this ATM interface as having two physical
--   interfaces.  Capable of port redundency.

ctFrontPanelTokenRing OBJECT IDENTIFIER ::= { ctFrontPanel 4 }
-- OBJECT-IDENTITY
--  Status
--    mandatory
--  Descr
--    Defines Token Ring front panel connections.

ctFrontPanelWAN OBJECT IDENTIFIER ::= { ctFrontPanel 5 }
-- OBJECT-IDENTITY
--  Status
--    mandatory
--  Descr
--    Defines WAN front panel connections.

ctFrontPanelComport OBJECT IDENTIFIER ::= { ctFrontPanel 6 }
-- OBJECT-IDENTITY
--  Status
--    mandatory
--  Descr
--    Defines Comport front panel connections.

ctFrontPanelComport1 OBJECT IDENTIFIER ::= { ctFrontPanelComport 1 }
-- OBJECT-IDENTITY
--  Status
--    mandatory
--  Descr
--    Defines Comport front panel connection 1.

ctFrontPanelComport2 OBJECT IDENTIFIER ::= { ctFrontPanelComport 2 }
-- OBJECT-IDENTITY
--  Status
--    mandatory
--  Descr
--    Defines Comport front panel connection 2.

ctSFPSTypes OBJECT IDENTIFIER ::= { namingTree 12 }
-- OBJECT-IDENTITY
--  Status
--    mandatory
--  Descr
--    Defines a naming tree for SFPS entities.

ctVLANS OBJECT IDENTIFIER ::= { namingTree 13 }
-- OBJECT-IDENTITY
--  Status
--    mandatory
--  Descr
--    Defines a naming tree for all virtual lan entities.

ctLaneServices OBJECT IDENTIFIER ::= { namingTree 14 }
-- OBJECT-IDENTITY
--  Status
--    mandatory
--  Descr
--    Defines a naming tree for Lane Services applications.

lsSFpSMARTLANE OBJECT IDENTIFIER ::= { ctLaneServices 1 }
-- OBJECT-IDENTITY
--  Status
--    mandatory

ctTrapsV1 OBJECT IDENTIFIER ::= { trapDefinitions 1 }
-- OBJECT-IDENTITY
--  Status
--    mandatory
--  Descr
--    This branch is reserved for all Cabletron traps that exist within
--    the context of both SNMPv1 and SNMPv2.

END
